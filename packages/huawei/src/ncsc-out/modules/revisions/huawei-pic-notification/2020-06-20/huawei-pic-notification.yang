module huawei-pic-notification {
  // Generated by yanger -t ncs
  tailf:mount-id "huawei-nc-1.0:huawei-nc-1.0";
  tailf:ncs-device-type "netconf";

  yang-version 1;
  namespace "urn:huawei:yang:huawei-pic-notification";
  prefix pic-notification;

  import huawei-extension {
    prefix ext;
  }
  import huawei-devm {
    prefix devm;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Notification of sub-card module.";

  revision 2020-06-20 {
    description
      "Add port notification alarms.";
    reference "Huawei private.";
  }
  revision 2020-05-08 {
    description
      "Add four notification alarms.";
    reference "Huawei private.";
  }
  revision 2020-03-20 {
    description
      "Initial revision.";
    reference "Huawei private.";
  }
  ext:task-name "device-mgr";

  typedef ncs_template_loop-type {
    type string;
    description
      "This object indicates the current interface status.";
  }

  typedef ncs_template_exception-type {
    type string;
    description
      "The abnormal type for temperature, voltage, humidity.";
  }

  typedef ncs_rpc_notif_loop-type {
    type enumeration {
      enum "no-loopback" {
        value 0;
        description
          "No loopback.";
      }
      enum "local" {
        value 1;
        description
          "Local loopback.";
      }
      enum "remote" {
        value 2;
        description
          "Remote loopback.";
      }
    }
    description
      "This object indicates the current interface status.";
  }

  typedef ncs_rpc_notif_exception-type {
    type enumeration {
      enum "rise-over" {
        value 1;
        description
          "Rise over threshold.";
      }
      enum "fall-below" {
        value 2;
        description
          "Fall below threshold.";
      }
    }
    description
      "The abnormal type for temperature, voltage, humidity.";
  }

  typedef live_ncs_loop-type {
    type enumeration {
      enum "no-loopback" {
        value 0;
        description
          "No loopback.";
      }
      enum "local" {
        value 1;
        description
          "Local loopback.";
      }
      enum "remote" {
        value 2;
        description
          "Remote loopback.";
      }
    }
    description
      "This object indicates the current interface status.";
  }

  typedef live_ncs_exception-type {
    type enumeration {
      enum "rise-over" {
        value 1;
        description
          "Rise over threshold.";
      }
      enum "fall-below" {
        value 2;
        description
          "Fall below threshold.";
      }
    }
    description
      "The abnormal type for temperature, voltage, humidity.";
  }

  typedef loop-type {
    type enumeration {
      enum "no-loopback" {
        value 0;
        description
          "No loopback.";
      }
      enum "local" {
        value 1;
        description
          "Local loopback.";
      }
      enum "remote" {
        value 2;
        description
          "Remote loopback.";
      }
    }
    description
      "This object indicates the current interface status.";
  }

  typedef exception-type {
    type enumeration {
      enum "rise-over" {
        value 1;
        description
          "Rise over threshold.";
      }
      enum "fall-below" {
        value 2;
        description
          "Fall below threshold.";
      }
    }
    description
      "The abnormal type for temperature, voltage, humidity.";
  }

  augment "/ncs:devices/ncs:device/ncs:notifications/ncs:received-notifications/ncs:notification/ncs:data" {
    container tim-trace-mismatch-resume {
      presence "";
      config false;
      description
        "This object indicates that a clear alarm is generated when TIM trace identifiers between the local and remote ends match.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container tim-trace-mismatch {
      presence "";
      config false;
      description
        "This object indicates that an alarm is generated when TIM trace identifiers between the local and remote ends mismatch.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container section-alignment-resume {
      presence "";
      config false;
      description
        "This object indicates that a clear alarm is generated when the section frame alignment error between the local and remote ends is corrected.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container section-alignment {
      presence "";
      config false;
      description
        "This object indicates that an alarm is generated when the section frame alignment between the local and remote ends is incorrect.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container ms-b2-degrade-resume {
      presence "";
      config false;
      description
        "This object indicates that the alarm for the signal degrade in the multiplex section B2 is cleared.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container ms-b2-degrade {
      presence "";
      config false;
      description
        "This object indicates the signal degrade in the multiplex section B2.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container remote-fault-resume {
      presence "";
      config false;
      description
        "This object indicates that a clear alarm is generated when the transmit link from the remote device to the local device recovers.";
      leaf physical-port-index {
        type uint32;
        description
          "Indicates the physical port index.";
      }
      leaf port-name {
        type string {
          length "1..32";
        }
        description
          "Indicates the physical port name.";
      }
    }
  }
  augment "/ncs:devices/ncs:device/ncs:notifications/ncs:received-notifications/ncs:notification/ncs:data" {
    container remote-fault {
      presence "";
      config false;
      description
        "This object indicates that an alarm is generated when the transmit link from the remote device to the local device fails.";
      leaf physical-port-index {
        type uint32;
        description
          "Indicates the physical port index.";
      }
      leaf port-name {
        type string {
          length "1..32";
        }
        description
          "Indicates the physical port name.";
      }
    }
  }
  augment "/ncs:devices/ncs:device/ncs:notifications/ncs:received-notifications/ncs:notification/ncs:data" {
    container remote-defect-resume {
      presence "";
      config false;
      description
        "The peer end recovered from faults.";
      leaf physical-port-index {
        type uint32;
        description
          "Indicates the physical port index.";
      }
      leaf port-name {
        type string {
          length "1..32";
        }
        description
          "Indicates the physical port name.";
      }
    }
  }
  augment "/ncs:devices/ncs:device/ncs:notifications/ncs:received-notifications/ncs:notification/ncs:data" {
    container remote-defect {
      presence "";
      config false;
      description
        "The peer end was faulty.";
      leaf physical-port-index {
        type uint32;
        description
          "Indicates the physical port index.";
      }
      leaf port-name {
        type string {
          length "1..32";
        }
        description
          "Indicates the physical port name.";
      }
    }
  }
  augment "/ncs:devices/ncs:device/ncs:notifications/ncs:received-notifications/ncs:notification/ncs:data" {
    container unequipped-hp-resume {
      presence "";
      config false;
      description
        "This object indicates that a clear alarm is generated when the higher order path (HP) is equipped.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container unequipped-hp {
      presence "";
      config false;
      description
        "This object indicates that an alarm is generated when the higher order path (HP) is unequipped.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container trace-mismatch-hp-resume {
      presence "";
      config false;
      description
        "This object indicates that a clear alarm is generated when the higher order path (HP) trace identifier becomes stable.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container trace-mismatch-hp {
      presence "";
      config false;
      description
        "This object indicates that an alarm is generated when the higher order path (HP) trace identifier is unstable.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container prefec-tca-resume {
      presence "";
      config false;
      description
        "This object indicates that a clear is generated for forward error correction (FEC) bit errors threshold-crossing.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container pre-fec-tca {
      presence "";
      config false;
      description
        "This object indicates that an alarm is generated for forward error correction (FEC) bit errors threshold-crossing.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container remote-defect-hp-resume {
      presence "";
      config false;
      description
        "This object indicates the higher order path (HP) Remote Default Indication (HPRDI) alarm is cleared.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container remote-defect-hp {
      presence "";
      config false;
      description
        "This object indicates the higher order path (HP) Remote Default Indication (HPRDI) alarm.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container payload-mismatch-hp-resume {
      presence "";
      config false;
      description
        "This object indicates that the higher order path (HP) signal identifier mismatch is rectified.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container payload-mismatch-hp {
      presence "";
      config false;
      description
        "This object indicates the higher order path (HP) signal identifier mismatch.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container port-type-change {
      presence "";
      config false;
      description
        "The mode of combo port is changed.";
      leaf physical-port-index {
        type uint32;
        description
          "Indicates the physical port index.";
      }
      leaf port-name {
        type string {
          length "1..32";
        }
        description
          "Indicates the physical port name.";
      }
      leaf physical-port-mode {
        type uint32;
        description
          "The current state of port type in port.";
      }
    }
  }
  augment "/ncs:devices/ncs:device/ncs:notifications/ncs:received-notifications/ncs:notification/ncs:data" {
    container traffic-fall-receive-resume {
      presence "";
      config false;
      description
        "Traffic fall clear alarm in the receive direction of an Ethernet interface.";
      leaf physical-port-index {
        type uint32;
        description
          "Indicates the physical port index.";
      }
    }
  }
  augment "/ncs:devices/ncs:device/ncs:notifications/ncs:received-notifications/ncs:notification/ncs:data" {
    container traffic-fall-receive {
      presence "";
      config false;
      description
        "Traffic fall alarm in the receive direction of an Ethernet interface.";
      leaf physical-port-index {
        type uint32;
        description
          "Indicates the physical port index.";
      }
    }
  }
  augment "/ncs:devices/ncs:device/ncs:notifications/ncs:received-notifications/ncs:notification/ncs:data" {
    container physical-rate-degrade-resume {
      presence "";
      config false;
      description
        "This object indicates that a clear alarm is generated when the negotiation rate on an electrical interface falls sharply.";
      leaf physical-port-index {
        type uint32;
        description
          "Indicates the physical port index.";
      }
    }
  }
  augment "/ncs:devices/ncs:device/ncs:notifications/ncs:received-notifications/ncs:notification/ncs:data" {
    container physical-rate-degrade {
      presence "";
      config false;
      description
        "This object indicates that an alarm is generated when the negotiation rate on an electrical interface falls sharply.";
      leaf physical-port-index {
        type uint32;
        description
          "Indicates the physical port index.";
      }
    }
  }
  augment "/ncs:devices/ncs:device/ncs:notifications/ncs:received-notifications/ncs:notification/ncs:data" {
    container port-physical-up {
      presence "";
      config false;
      description
        "One of the port physical connect up.";
      leaf base-trap-severity {
        type uint32;
        description
          "To describe the level of trap.";
      }
      leaf base-trap-probable-cause {
        type uint32;
        description
          "To describe the probable cause of trap.";
      }
      leaf base-trap-event-type {
        type uint32;
        description
          "To describe the type of trap.";
      }
      leaf port-name {
        type string {
          length "1..32";
        }
        description
          "Entity physical name.";
      }
    }
  }
  augment "/ncs:devices/ncs:device/ncs:notifications/ncs:received-notifications/ncs:notification/ncs:data" {
    container port-physical-down {
      presence "";
      config false;
      description
        "One of the port physical connect down.";
      leaf base-trap-severity {
        type uint32;
        description
          "To describe the level of trap.";
      }
      leaf base-trap-probable-cause {
        type uint32;
        description
          "To describe the probable cause of trap.";
      }
      leaf base-trap-event-type {
        type uint32;
        description
          "To describe the type of trap.";
      }
      leaf port-name {
        type string {
          length "1..32";
        }
        description
          "Entity physical name.";
      }
      leaf port-physical-down-reason {
        type string {
          length "1..32";
        }
        description
          "Port physical down reason.";
      }
    }
  }
  augment "/ncs:devices/ncs:device/ncs:notifications/ncs:received-notifications/ncs:notification/ncs:data" {
    container port-mode-change {
      presence "";
      config false;
      description
        "This object indicates that the port rate type is changed.";
      leaf physical-port-index {
        type uint32;
        description
          "Indicates the physical port index.";
      }
      leaf port-name {
        type string {
          length "1..32";
        }
        description
          "Indicates the physical port name.";
      }
      leaf physical-port-mode {
        type uint32;
        description
          "The current state of port type in port.";
      }
    }
  }
  augment "/ncs:devices/ncs:device/ncs:notifications/ncs:received-notifications/ncs:notification/ncs:data" {
    container trans-mode-inconsistent-resume {
      presence "";
      config false;
      description
        "The transmission modes of the group of interfaces are consistent now.";
      leaf card-id {
        type uint32;
        description
          "Indicates the card ID.";
      }
      leaf physical-port-groupid {
        type string {
          length "1..32";
        }
        description
          "Indicates the physical port group id.";
      }
      leaf port-trans-mode-reason {
        type string {
          length "1..32";
        }
        description
          "Indicates the physical port transmission mode different reason.";
      }
      leaf slot-id {
        type uint32;
        description
          "Indicates the slot ID.";
      }
    }
  }
  augment "/ncs:devices/ncs:device/ncs:notifications/ncs:received-notifications/ncs:notification/ncs:data" {
    container trans-mode-inconsistent {
      presence "";
      config false;
      description
        "The transmission modes of the group of interfaces are inconsistent.";
      leaf card-id {
        type uint32;
        description
          "Indicates the card ID.";
      }
      leaf physical-port-groupid {
        type string {
          length "1..32";
        }
        description
          "Indicates the physical port group id.";
      }
      leaf port-trans-mode-reason {
        type string {
          length "1..32";
        }
        description
          "Indicates the physical port transmission mode different reason.";
      }
      leaf slot-id {
        type uint32;
        description
          "Indicates the slot ID.";
      }
    }
  }
  augment "/ncs:devices/ncs:device/ncs:notifications/ncs:received-notifications/ncs:notification/ncs:data" {
    container path-trace-mismatch-resume {
      presence "";
      config false;
      description
        "This object indicates that a clear alarm is generated when path trace identifiers between the local and remote ends match.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container path-trace-mismatch {
      presence "";
      config false;
      description
        "This object indicates that an alarm is generated when path trace identifiers between the local and remote ends mismatch.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container crc-mac-fcs-sd-resume {
      presence "";
      config false;
      description
        "This object indicates that a clear alarm when port FCS signal degrade at the MAC layer.";
      leaf physical-port-index {
        type uint32;
        description
          "This object indicates the index of a physical port.";
      }
      leaf port-name {
        type string {
          length "1..64";
        }
        description
          "This object indicates the name of a physical port.";
      }
      leaf current-crc-packet-error-ratio {
        type string {
          length "1..32";
        }
        description
          "This object indicates that the thresholds for CRC error packet ratio alarms on a physical port are sent to the NMS in the character string format.";
      }
      leaf physical-port-crc-sd-alarm-threshold {
        type string {
          length "1..32";
        }
        description
          "The alarm threshold of MAC_FCS_SD.";
      }
      leaf physical-port-crc-sd-resume-threshold {
        type string {
          length "1..32";
        }
        description
          "The resume threshold of MAC_FCS_SD.";
      }
    }
  }
  augment "/ncs:devices/ncs:device/ncs:notifications/ncs:received-notifications/ncs:notification/ncs:data" {
    container crc-mac-fcs-sd {
      presence "";
      config false;
      description
        "This object indicates that an alarm when port FCS signal degrade at the MAC layer.";
      leaf physical-port-index {
        type uint32;
        description
          "This object indicates the index of a physical port.";
      }
      leaf port-name {
        type string {
          length "1..64";
        }
        description
          "This object indicates the name of a physical port.";
      }
      leaf current-crc-packet-error-ratio {
        type string {
          length "1..32";
        }
        description
          "This object indicates that the thresholds for CRC error packet ratio alarms on a physical port are sent to the NMS in the character string format.";
      }
      leaf physical-port-crc-sd-alarm-threshold {
        type string {
          length "1..32";
        }
        description
          "The alarm threshold of MAC_FCS_SD.";
      }
      leaf physical-port-crc-sd-resume-threshold {
        type string {
          length "1..32";
        }
        description
          "The resume threshold of MAC_FCS_SD.";
      }
    }
  }
  augment "/ncs:devices/ncs:device/ncs:notifications/ncs:received-notifications/ncs:notification/ncs:data" {
    container crc-error-warning-resume {
      presence "";
      config false;
      description
        "This object indicates that a clear alarm is generated when the number of CRC errors on a physical port falls below the lower threshold. The host sends a trap message to the NMS.";
      leaf physical-port-index {
        type uint32;
        description
          "This object indicates the index of a physical port.";
      }
      leaf port-name {
        type string {
          length "1..64";
        }
        description
          "This object indicates the name of a physical port.";
      }
      leaf current-crc-packet-error-ratio {
        type string {
          length "1..32";
        }
        description
          "This object indicates that the thresholds for CRC error packet ratio alarms on a physical port are sent to the NMS in the character string format.";
      }
      leaf physical-port-crc-per-warning-threshold {
        type string {
          length "1..32";
        }
        description
          "The warning threshold of CRC-PER (Packet Error Ratio).";
      }
      leaf physical-port-crc-per-warning-resume-threshold {
        type string {
          length "1..32";
        }
        description
          "The warning resume threshold of CRC-PER (Packet Error Ratio).";
      }
    }
  }
  augment "/ncs:devices/ncs:device/ncs:notifications/ncs:received-notifications/ncs:notification/ncs:data" {
    container crc-error-warning {
      presence "";
      config false;
      description
        "This object indicates that an alarm is generated when the number of CRC errors on a physical port exceeds the lower threshold. The host sends a trap message to the NMS.";
      leaf physical-port-index {
        type uint32;
        description
          "This object indicates the index of a physical port.";
      }
      leaf port-name {
        type string {
          length "1..64";
        }
        description
          "This object indicates the name of a physical port.";
      }
      leaf current-crc-packet-error-ratio {
        type string {
          length "1..32";
        }
        description
          "This object indicates that the thresholds for CRC error packet ratio alarms on a physical port are sent to the NMS in the character string format.";
      }
      leaf crc-per-warning-threshold {
        type string {
          length "1..32";
        }
        description
          "The warning threshold of CRC-PER (Packet Error Ratio).";
      }
      leaf physical-port-crc-per-warning-resume-threshold {
        type string {
          length "1..32";
        }
        description
          "The warning resume threshold of CRC-PER (Packet Error Ratio).";
      }
    }
  }
  augment "/ncs:devices/ncs:device/ncs:notifications/ncs:received-notifications/ncs:notification/ncs:data" {
    container crc-packet-error-ratio-resume {
      presence "";
      config false;
      description
        "This object indicates that a clear alarm is generated when the number of CRC errors on a physical port falls below the upper threshold. The host sends a trap message to the NMS.";
      leaf physical-port-index {
        type uint32;
        description
          "This object indicates the index of a physical port.";
      }
      leaf port-name {
        type string {
          length "1..64";
        }
        description
          "This object indicates the name of a physical port.";
      }
      leaf current-crc-packet-error-ratio {
        type string {
          length "1..32";
        }
        description
          "This object indicates that the thresholds for CRC error packet ratio alarms on a physical port are sent to the NMS in the character string format.";
      }
      leaf alarm-threshold {
        type string {
          length "1..32";
        }
        description
          "This object indicates that the generation threshold for the CRC error packet ratio alarm on a physical port is sent to the NMS in the character string format.";
      }
      leaf resume-threshold {
        type string {
          length "1..32";
        }
        description
          "This object indicates that the clearing threshold for the CRC error packet ratio clear alarm on a physical port is sent to the NMS in the character string format.";
      }
    }
  }
  augment "/ncs:devices/ncs:device/ncs:notifications/ncs:received-notifications/ncs:notification/ncs:data" {
    container crc-packet-error-ratio {
      presence "";
      config false;
      description
        "This object indicates that an alarm is generated when the number of CRC errors on a physical port exceeds the upper threshold. The host sends a trap message to the NMS.";
      leaf physical-port-index {
        type uint32;
        description
          "This object indicates the index of a physical port.";
      }
      leaf port-name {
        type string {
          length "1..64";
        }
        description
          "This object indicates the name of a physical port.";
      }
      leaf current-crc-packet-error-ratio {
        type string {
          length "1..32";
        }
        description
          "This object indicates that the thresholds for CRC error packet ratio alarms on a physical port are sent to the NMS in the character string format.";
      }
      leaf alarm-threshold {
        type string {
          length "1..32";
        }
        description
          "This object indicates that the generation threshold for the CRC error packet ratio alarm on a physical port is sent to the NMS in the character string format.";
      }
      leaf resume-threshold {
        type string {
          length "1..32";
        }
        description
          "This object indicates that the clearing threshold for the CRC error packet ratio clear alarm on a physical port is sent to the NMS in the character string format.";
      }
    }
  }
  augment "/ncs:devices/ncs:device/ncs:notifications/ncs:received-notifications/ncs:notification/ncs:data" {
    container crc-fcs-exceed-resume {
      presence "";
      config false;
      description
        "Port MAC_FCS_EXC alarm resume.";
      leaf physical-port-index {
        type uint32;
        description
          "This object indicates the index of a physical port.";
      }
      leaf port-name {
        type string {
          length "1..64";
        }
        description
          "This object indicates the name of a physical port.";
      }
      leaf current-crc-packet-error-ratio {
        type string {
          length "1..32";
        }
        description
          "This object indicates that the thresholds for CRC error packet ratio alarms on a physical port are sent to the NMS in the character string format.";
      }
      leaf physical-port-crc-exc-alarm-threshold {
        type string {
          length "1..32";
        }
        description
          "The alarm threshold of MAC_FCS_EXC.";
      }
      leaf physical-port-crc-exc-resume-threshold {
        type string {
          length "1..32";
        }
        description
          "The resume threshold of MAC_FCS_EXC.";
      }
    }
  }
  augment "/ncs:devices/ncs:device/ncs:notifications/ncs:received-notifications/ncs:notification/ncs:data" {
    container crc-fcs-exceed {
      presence "";
      config false;
      description
        "Port MAC FCS EXC alarm.";
      leaf physical-port-index {
        type uint32;
        description
          "This object indicates the index of a physical port.";
      }
      leaf port-name {
        type string {
          length "1..64";
        }
        description
          "This object indicates the name of a physical port.";
      }
      leaf current-crc-packet-error-ratio {
        type string {
          length "1..32";
        }
        description
          "This object indicates that the thresholds for CRC error packet ratio alarms on a physical port are sent to the NMS in the character string format.";
      }
      leaf physical-port-crc-exc-alarm-threshold {
        type string {
          length "1..32";
        }
        description
          "The alarm threshold of MAC_FCS_EXC.";
      }
      leaf physical-port-crc-exc-resume-threshold {
        type string {
          length "1..32";
        }
        description
          "The resume threshold of MAC_FCS_EXC.";
      }
    }
  }
  augment "/ncs:devices/ncs:device/ncs:notifications/ncs:received-notifications/ncs:notification/ncs:data" {
    container crc-error-exceed-resume {
      presence "";
      config false;
      description
        "Port CRC error alarm resume.";
      leaf physical-port-index {
        type uint32;
        description
          "This object indicates the index of a physical port.";
      }
      leaf port-name {
        type string {
          length "1..64";
        }
        description
          "This object indicates the name of a physical port.";
      }
      leaf physical-port-crc-error-statistics {
        type uint64;
        description
          "This object indicates the CRC error statistics.";
      }
      leaf physical-port-crc-error-high-threshold {
        type uint32;
        description
          "This object indicates the upper threshold for the number of CRC errors. The default value is 1000 pps.";
      }
      leaf physical-port-crc-error-low-threshold {
        type uint32;
        description
          "This object indicates the lower threshold for the number of CRC errors. The default value is 100 pps.";
      }
      leaf physical-port-crc-error-interval {
        type uint32;
        description
          "This object indicates the time threshold for the CRC error alarm. The default value is 10s.";
      }
    }
  }
  augment "/ncs:devices/ncs:device/ncs:notifications/ncs:received-notifications/ncs:notification/ncs:data" {
    container crc-error-exceed {
      presence "";
      config false;
      description
        "Port CRC error alarm.";
      leaf physical-port-index {
        type uint32;
        description
          "This object indicates the index of a physical port.";
      }
      leaf port-name {
        type string {
          length "1..64";
        }
        description
          "This object indicates the name of a physical port.";
      }
      leaf physical-port-crc-error-statistics {
        type uint64;
        description
          "This object indicates the CRC error statistics.";
      }
      leaf physical-port-crc-error-high-threshold {
        type uint32;
        description
          "This object indicates the upper threshold for the number of CRC errors. The default value is 1000 pps.";
      }
      leaf physical-port-crc-error-low-threshold {
        type uint32;
        description
          "This object indicates the lower threshold for the number of CRC errors. The default value is 100 pps.";
      }
      leaf physical-port-crc-error-interval {
        type uint32;
        description
          "This object indicates the time threshold for the CRC error alarm. The default value is 10s.";
      }
    }
  }
  augment "/ncs:devices/ncs:device/ncs:notifications/ncs:received-notifications/ncs:notification/ncs:data" {
    container bip8-sd-error-resume {
      presence "";
      config false;
      description
        "This object indicates that the Output error alarm is cleared.";
      leaf physical-port-index {
        type uint32;
        description
          "This object indicates the index of a physical port.";
      }
      leaf port-name {
        type string {
          length "1..64";
        }
        description
          "This object indicates the name of a physical port.";
      }
      leaf physical-port-bip8-sd-error-threshold {
        type uint32;
        description
          "This object indicates the BIP8 SD alarm threshold. The default value is 6.";
      }
    }
  }
  augment "/ncs:devices/ncs:device/ncs:notifications/ncs:received-notifications/ncs:notification/ncs:data" {
    container bip8-sd-error {
      presence "";
      config false;
      description
        "This object indicates the output error alarm.";
      leaf physical-port-index {
        type uint32;
        description
          "This object indicates the index of a physical port.";
      }
      leaf port-name {
        type string {
          length "1..64";
        }
        description
          "This object indicates the name of a physical port.";
      }
      leaf physical-port-bip8-sd-error-threshold {
        type uint32;
        description
          "This object indicates the BIP8 SD alarm threshold. The default value is 6.";
      }
    }
  }
  augment "/ncs:devices/ncs:device/ncs:notifications/ncs:received-notifications/ncs:notification/ncs:data" {
    container signal-lp-resume {
      presence "";
      config false;
      description
        "This object indicates that a low path alarm indication signal is detected.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
      leaf hp-id {
        type uint32;
        description
          "Indicates the higher order path ID.";
      }
    }
  }
  augment "/ncs:devices/ncs:device/ncs:notifications/ncs:received-notifications/ncs:notification/ncs:data" {
    container signal-lp {
      presence "";
      config false;
      description
        "This object indicates that a low path alarm indication signal is detected.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
      leaf hp-id {
        type uint32;
        description
          "Indicates the higher order path ID.";
      }
    }
  }
  augment "/ncs:devices/ncs:device/ncs:notifications/ncs:received-notifications/ncs:notification/ncs:data" {
    container output-error-exceed-resume {
      presence "";
      config false;
      description
        "This object indicates that a clear alarm is generated when the number of output errors on an interface falls below the upper threshold.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container output-error-exceed {
      presence "";
      config false;
      description
        "This object indicates that an alarm is generated when the number of output errors on an interface exceeds the upper threshold.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container otu-signal-fail-resume {
      presence "";
      config false;
      description
        "This object indicates that the alarm for the OTU signal degrade is cleared.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container otu-signal-fail {
      presence "";
      config false;
      description
        "This object indicates that an alarm is generated for the OTU signal failure.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container otu-signal-degrade-resume {
      presence "";
      config false;
      description
        "This object indicates that the alarm for the OTU signal degrade is cleared.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container otu-signal-degrade {
      presence "";
      config false;
      description
        "This object indicates that an alarm is generated for the OTU signal degrade.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container otu-loss-of-multiframe-resume {
      presence "";
      config false;
      description
        "This object indicates that the OTU indication signal alarm is cleared.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container otu-loss-of-multiframe {
      presence "";
      config false;
      description
        "This object indicates the OTU indication signal alarm.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container otu-indication-signal-resume {
      presence "";
      config false;
      description
        "This object indicates that the OTU indication signal alarm is cleared.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container otu-indication-signal {
      presence "";
      config false;
      description
        "This object indicates the OTU indication signal alarm.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container optical-not-authorized-resume {
      presence "";
      config false;
      description
        "This object indicates that an alarm is generated when the inserted optical module is one not authenticated by Huawei.";
      leaf physical-port-index {
        type uint32;
        description
          "This object indicates the index of a physical port.";
      }
      leaf port-name {
        type string {
          length "1..32";
        }
        description
          "This object indicates the name of a physical port.";
      }
    }
  }
  augment "/ncs:devices/ncs:device/ncs:notifications/ncs:received-notifications/ncs:notification/ncs:data" {
    container optical-not-authorized {
      presence "";
      config false;
      description
        "This object indicates that an alarm is generated when the inserted optical module is one not authenticated by Huawei.";
      leaf physical-port-index {
        type uint32;
        description
          "This object indicates the index of a physical port.";
      }
      leaf port-name {
        type string {
          length "1..32";
        }
        description
          "This object indicates the name of a physical port.";
      }
    }
  }
  augment "/ncs:devices/ncs:device/ncs:notifications/ncs:received-notifications/ncs:notification/ncs:data" {
    container optical-fail-resume {
      presence "";
      config false;
      description
        "Optical Module resume from failure.";
      leaf entity-physical-index {
        type uint32;
        description
          "The index of physical.";
      }
      leaf port-name {
        type string {
          length "1..32";
        }
        description
          "Entity physical name.";
      }
      leaf fault-code {
        type devm:ncs_rpc_notif_notification-probable-cause-type;
        description
          "To describe the fault id of trap.";
      }
      leaf reason {
        type string {
          length "1..32";
        }
        description
          "Description of trap reason.";
      }
    }
  }
  augment "/ncs:devices/ncs:device/ncs:notifications/ncs:received-notifications/ncs:notification/ncs:data" {
    container optical-fail {
      presence "";
      config false;
      description
        "Optical Module become failure for some reason.";
      leaf entity-physical-index {
        type uint32;
        description
          "The index of physical.";
      }
      leaf port-name {
        type string {
          length "1..32";
        }
        description
          "Entity physical name.";
      }
      leaf fault-code {
        type devm:ncs_rpc_notif_notification-probable-cause-type;
        description
          "To describe the fault id of trap.";
      }
      leaf reason {
        type string {
          length "1..32";
        }
        description
          "Description of trap reason.";
      }
    }
  }
  augment "/ncs:devices/ncs:device/ncs:notifications/ncs:received-notifications/ncs:notification/ncs:data" {
    container optical-not-match-resume {
      presence "";
      config false;
      description
        "After the optical module was inserted, its configuration was not supported. The partial function of optical module failed.";
      leaf entity-physical-index {
        type uint32;
        description
          "The index of physical.";
      }
      leaf port-name {
        type string {
          length "1..32";
        }
        description
          "Entity physical name.";
      }
      leaf fault-code {
        type devm:ncs_rpc_notif_notification-probable-cause-type;
        description
          "To describe the fault id of trap.";
      }
      leaf reason {
        type string {
          length "1..32";
        }
        description
          "Description of trap reason.";
      }
    }
  }
  augment "/ncs:devices/ncs:device/ncs:notifications/ncs:received-notifications/ncs:notification/ncs:data" {
    container optical-not-match {
      presence "";
      config false;
      description
        "After the optical module was inserted, its configuration was not supported. The partial function of optical module failed.";
      leaf entity-physical-index {
        type uint32;
        description
          "The index of physical.";
      }
      leaf port-name {
        type string {
          length "1..32";
        }
        description
          "Entity physical name.";
      }
      leaf fault-code {
        type devm:ncs_rpc_notif_notification-probable-cause-type;
        description
          "To describe the fault id of trap.";
      }
      leaf reason {
        type string {
          length "1..32";
        }
        description
          "Description of trap reason.";
      }
    }
  }
  augment "/ncs:devices/ncs:device/ncs:notifications/ncs:received-notifications/ncs:notification/ncs:data" {
    container out-of-frame-resume {
      presence "";
      config false;
      description
        "This object indicates that the OOF alarm generated at the receive end is cleared.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container out-of-frame {
      presence "";
      config false;
      description
        "This object indicates that an out of frame (OOF) alarm is generated at the receive end.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container odu-signal-degrade-resume {
      presence "";
      config false;
      description
        "This object indicates that the alarm for the ODU signal degrade is cleared.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container odu-signal-degrade {
      presence "";
      config false;
      description
        "This object indicates that an alarm is generated for the ODU signal degrade.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container odu-open-connection-resume {
      presence "";
      config false;
      description
        "This object indicates that the indication defect alarm for the ODU open connection is cleared.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container odu-open-connection {
      presence "";
      config false;
      description
        "This object indicates that the indication defect alarm for the ODU open connection.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container odu-locked-signal-resume {
      presence "";
      config false;
      description
        "This object indicates that the ODU lock defect alarm is cleared.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container odu-locked-signal {
      presence "";
      config false;
      description
        "This object indicates the ODU lock defect alarm.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container odu-indication-signal-resume {
      presence "";
      config false;
      description
        "This object indicates that the ODU indication signal alarm is cleared.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container odu-indication-signal {
      presence "";
      config false;
      description
        "This object indicates the ODU indication signal alarm.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container negotiation-failed-resume {
      presence "";
      config false;
      description
        "Auto-negotiation failure alarm resume.";
      leaf physical-port-index {
        type uint32;
        description
          "Indicates the physical port index.";
      }
      leaf port-name {
        type string {
          length "1..32";
        }
        description
          "Indicates the physical port name.";
      }
    }
  }
  augment "/ncs:devices/ncs:device/ncs:notifications/ncs:received-notifications/ncs:notification/ncs:data" {
    container negotiation-failed {
      presence "";
      config false;
      description
        "Auto-negotiation failure alarm. Possible causes, including the local auto-negotiation configuration with the peer inconsistencies;
                the local ability is not compatible with the peer;
                the physical connection of the two sides is unstable.
                When the alarm occurs, the port can't be up.";
      leaf physical-port-index {
        type uint32;
        description
          "Indicates the physical port index.";
      }
      leaf port-name {
        type string {
          length "1..32";
        }
        description
          "Indicates the physical port name.";
      }
    }
  }
  augment "/ncs:devices/ncs:device/ncs:notifications/ncs:received-notifications/ncs:notification/ncs:data" {
    container remote-defect-ms-resume {
      presence "";
      config false;
      description
        "This object indicates that the LRDI alarm generated in the multiplex section (MS) at the remote end is cleared.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container remote-defect-ms {
      presence "";
      config false;
      description
        "This object indicates that a line remote defect indicator (LRDI) alarm is generated in the multiplex section (MS) at the remote end.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container signal-loss-resume {
      presence "";
      config false;
      description
        "This object indicates that the alarm for the interface loopback is cleared.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
      leaf physical-port-alarm-name {
        type string {
          length "1..32";
        }
        description
          "Indicates the physical port alarm name.";
      }
    }
  }
  augment "/ncs:devices/ncs:device/ncs:notifications/ncs:received-notifications/ncs:notification/ncs:data" {
    container signal-loss {
      presence "";
      config false;
      description
        "This object indicates that an alarm is generated due to signal loss at the receive end.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
      leaf physical-port-alarm-name {
        type string {
          length "1..32";
        }
        description
          "Indicates the physical port alarm name.";
      }
    }
  }
  augment "/ncs:devices/ncs:device/ncs:notifications/ncs:received-notifications/ncs:notification/ncs:data" {
    container port-loopback-resume {
      presence "";
      config false;
      description
        "This object indicates that the alarm for the interface loopback is cleared.";
      leaf physical-port-index {
        type uint32;
        description
          "Indicates the physical port index.";
      }
      leaf port-name {
        type string {
          length "1..32";
        }
        description
          "Indicates the physical port name.";
      }
      leaf loop-type {
        type ncs_rpc_notif_loop-type;
        description
          "Type of the notification loop. The value can be one -of the following: - 0: stop-loopback - 1: local - 2: remote.";
      }
    }
  }
  augment "/ncs:devices/ncs:device/ncs:notifications/ncs:received-notifications/ncs:notification/ncs:data" {
    container port-loopback {
      presence "";
      config false;
      description
        "This object indicates that an alarm is generated due to an interface loopback.";
      leaf physical-port-index {
        type uint32;
        description
          "Indicates the physical port index.";
      }
      leaf port-name {
        type string {
          length "1..32";
        }
        description
          "Indicates the physical port name.";
      }
      leaf loop-type {
        type ncs_rpc_notif_loop-type;
        description
          "Type of the notification loop. The value can be one -of the following: - 0: stop-loopback - 1: local - 2: remote.";
      }
    }
  }
  augment "/ncs:devices/ncs:device/ncs:notifications/ncs:received-notifications/ncs:notification/ncs:data" {
    container multi-loss-lp-resume {
      presence "";
      config false;
      description
        "This object indicates that the LOM on the higher order path (HP) is resolved.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container multi-loss-lp {
      presence "";
      config false;
      description
        "This object indicates the loss of multiframe (LOM) on the higher order path (HP).";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container local-fault-resume {
      presence "";
      config false;
      description
        "This object indicates that a clear alarm is generated when the receive link from the remote device to the local device recovers.";
      leaf physical-port-index {
        type uint32;
        description
          "Indicates the physical port index.";
      }
      leaf port-name {
        type string {
          length "1..32";
        }
        description
          "Indicates the physical port name.";
      }
    }
  }
  augment "/ncs:devices/ncs:device/ncs:notifications/ncs:received-notifications/ncs:notification/ncs:data" {
    container local-fault {
      presence "";
      config false;
      description
        "This object indicates that an alarm is generated when the receive link from the remote device to the local device fails.";
      leaf physical-port-index {
        type uint32;
        description
          "Indicates the physical port index.";
      }
      leaf port-name {
        type string {
          length "1..32";
        }
        description
          "Indicates the physical port name.";
      }
    }
  }
  augment "/ncs:devices/ncs:device/ncs:notifications/ncs:received-notifications/ncs:notification/ncs:data" {
    container license-resource-lack-resume {
      presence "";
      config false;
      description
        "The maximum number-exceed alarm was cleared.";
      leaf license-type {
        type string {
          length "1..32";
        }
        description
          "Indicates the type of interface function-controlled license.";
      }
      leaf max-port-num {
        type uint32;
        description
          "Indicates the maximum number of available interfaces.";
      }
      leaf used-port-num {
        type uint32;
        description
          "Indicates the number of interfaces in use.";
      }
    }
  }
  augment "/ncs:devices/ncs:device/ncs:notifications/ncs:received-notifications/ncs:notification/ncs:data" {
    container license-resource-lack {
      presence "";
      config false;
      description
        "Interfaces of this type in use exceeded the maximum number.";
      leaf license-type {
        type string {
          length "1..32";
        }
        description
          "Indicates the type of interface function-controlled license.";
      }
      leaf max-port-num {
        type uint32;
        description
          "Indicates the maximum number of available interfaces.";
      }
      leaf used-port-num {
        type uint32;
        description
          "Indicates the Number of interfaces in use.";
      }
    }
  }
  augment "/ncs:devices/ncs:device/ncs:notifications/ncs:received-notifications/ncs:notification/ncs:data" {
    container laser-shut-resume {
      presence "";
      config false;
      description
        "This object indicates that a clear alarm is generated when the optical laser on a board is opened.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container laser-shut {
      presence "";
      config false;
      description
        "This object indicates that an alarm is generated when the optical laser on a board is shut down.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container laser-no-fited-resume {
      presence "";
      config false;
      description
        "The laser not installed alarm resumed.";
      leaf entity-physical-index {
        type uint32;
        description
          "The index of physical.";
      }
      leaf port-name {
        type string {
          length "1..32";
        }
        description
          "Entity physical name.";
      }
    }
  }
  augment "/ncs:devices/ncs:device/ncs:notifications/ncs:received-notifications/ncs:notification/ncs:data" {
    container laser-no-fited {
      presence "";
      config false;
      description
        "The laser not installed alarm occured.";
      leaf entity-physical-index {
        type uint32;
        description
          "The index of physical.";
      }
      leaf port-name {
        type string {
          length "1..32";
        }
        description
          "Entity physical name.";
      }
    }
  }
  augment "/ncs:devices/ncs:device/ncs:notifications/ncs:received-notifications/ncs:notification/ncs:data" {
    container laser-auto-shut-resume {
      presence "";
      config false;
      description
        "This object indicates that the alarm for the automatic shutdown of the optical laser is cleared.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container laser-auto-shut {
      presence "";
      config false;
      description
        "This object indicates that an alarm is generated when the optical laser is shut down automatically.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container multi-section-resume {
      presence "";
      config false;
      description
        "This object indicates that the indication signal alarm in the MS is cleared.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container multi-section {
      presence "";
      config false;
      description
        "This object indicates the indication signal alarm in the MS.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container input-error-exceed-resume {
      presence "";
      config false;
      description
        "This object indicates that a clear alarm is generated when the number of input errors on an interface falls below the upper threshold.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container input-error-exceed {
      presence "";
      config false;
      description
        "This object indicates that an alarm is generated when the number of input errors on an interface exceeds the upper threshold.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container tx-pause-frame-exceed-resume {
      presence "";
      config false;
      description
        "The threshold exceed alert of TX PAUSE disappears.";
      leaf tx-pause-frame-statistics {
        type uint64;
        description
          "TX pause frame statistics value.";
      }
      leaf tx-pause-frame-high-threshold {
        type uint32;
        description
          "TX pause frame high threshold, and 0 is an invalid value.";
      }
      leaf tx-pause-frame-low-threshold {
        type uint32;
        description
          "TX pause frame low threshold, and 0 is an invalid value.";
      }
      leaf tx-pause-frame-interval {
        type uint32;
        description
          "TX pause frame alarm interval time (unit is second), and 0 is an invalid value.";
      }
      leaf port-name {
        type string {
          length "1..32";
        }
        description
          "Port name of alarm monitor table.";
      }
    }
  }
  augment "/ncs:devices/ncs:device/ncs:notifications/ncs:received-notifications/ncs:notification/ncs:data" {
    container tx-pause-frame-exceed {
      presence "";
      config false;
      description
        "The threshold exceed alert of TX PAUSE appears.";
      leaf tx-pause-frame-statistics {
        type uint64;
        description
          "TX pause frame statistics value.";
      }
      leaf tx-pause-frame-high-threshold {
        type uint32;
        description
          "TX pause frame high threshold, and 0 is an invalid value.";
      }
      leaf tx-pause-frame-low-threshold {
        type uint32;
        description
          "TX pause frame low threshold, and 0 is an invalid value.";
      }
      leaf tx-pause-frame-interval {
        type uint32;
        description
          "TX pause frame alarm interval time (unit is second), and 0 is an invalid value.";
      }
      leaf port-name {
        type string {
          length "1..32";
        }
        description
          "Port name of alarm monitor table.";
      }
    }
  }
  augment "/ncs:devices/ncs:device/ncs:notifications/ncs:received-notifications/ncs:notification/ncs:data" {
    container symbol-error-interval-resume {
      presence "";
      config false;
      description
        "CRC error alarm resume.";
      leaf symbol-error-statistics {
        type uint64;
        description
          "Symbol error statistics value.";
      }
      leaf symbol-error-threshold {
        type uint32;
        description
          "Symbol error alarm threshold,default value is 3.";
      }
      leaf symbol-error-interval {
        type uint32;
        description
          "Symbol error alarm interval time (unit is second), default value is 10s.";
      }
      leaf port-name {
        type string {
          length "1..32";
        }
        description
          "Port name of alarm monitor table.";
      }
    }
  }
  augment "/ncs:devices/ncs:device/ncs:notifications/ncs:received-notifications/ncs:notification/ncs:data" {
    container symbol-error-interval {
      presence "";
      config false;
      description
        "Symbol error alarm.";
      leaf symbol-error-statistics {
        type uint64;
        description
          "Symbol error statistics value.";
      }
      leaf symbol-error-threshold {
        type uint32;
        description
          "Symbol error alarm threshold,default value is 3.";
      }
      leaf symbol-error-interval {
        type uint32;
        description
          "Symbol error alarm interval time (unit is second), default value is 10s.";
      }
      leaf port-name {
        type string {
          length "1..32";
        }
        description
          "Port name of alarm monitor table.";
      }
    }
  }
  augment "/ncs:devices/ncs:device/ncs:notifications/ncs:received-notifications/ncs:notification/ncs:data" {
    container sdh-error-resume {
      presence "";
      config false;
      description
        "Sdh error alarm resume only for B3.";
      leaf sdh-error-statistics {
        type uint64;
        description
          "Sdh error statistics value only for B3.";
      }
      leaf sdh-error-threshold {
        type uint32;
        description
          "Sdh error alarm threshold,only for B3, default value is 3 and 0 is an invalid value.";
      }
      leaf sdh-error-interval {
        type uint32;
        description
          "Sdh error alarm interval time (unit is second),only for B3, default value is 10s and 0 is an invalid value.";
      }
      leaf port-name {
        type string {
          length "1..32";
        }
        description
          "Port name of alarm monitor table.";
      }
    }
  }
  augment "/ncs:devices/ncs:device/ncs:notifications/ncs:received-notifications/ncs:notification/ncs:data" {
    container sdh-error-rising {
      presence "";
      config false;
      description
        "Sdh error alarm only for B3.";
      leaf sdh-error-statistics {
        type uint64;
        description
          "Sdh error statistics value only for B3.";
      }
      leaf sdh-error-threshold {
        type uint32;
        description
          "Sdh error alarm threshold,only for B3,default value is 3 and 0 is an invalid value.";
      }
      leaf sdh-error-interval {
        type uint32;
        description
          "Sdh error alarm interval time (unit is second), only for B3,default value is 10s and 0 is an invalid value.";
      }
      leaf port-name {
        type string {
          length "1..32";
        }
        description
          "Port name of alarm monitor table.";
      }
    }
  }
  augment "/ncs:devices/ncs:device/ncs:notifications/ncs:received-notifications/ncs:notification/ncs:data" {
    container sdh-b2-error-resume {
      presence "";
      config false;
      description
        "Sdh B2 error alarm resume.";
      leaf sdh-b2-error-statistics {
        type uint64;
        description
          "Sdh B2 error statistics value.";
      }
      leaf sdh-b2-error-threshold {
        type uint32;
        description
          "Sdh error B2 alarm threshold,default value is 3.";
      }
      leaf sdh-b2-error-interval {
        type uint32;
        description
          "Sdh B2 error alarm interval time (unit is second),default value is 10s.";
      }
      leaf port-name {
        type string {
          length "1..32";
        }
        description
          "Port name of alarm monitor table.";
      }
    }
  }
  augment "/ncs:devices/ncs:device/ncs:notifications/ncs:received-notifications/ncs:notification/ncs:data" {
    container sdh-b2-error-rising {
      presence "";
      config false;
      description
        "Sdh B2 error alarm.";
      leaf sdh-b2-error-statistics {
        type uint64;
        description
          "Sdh B2 error statistics value.";
      }
      leaf sdh-b2-error-threshold {
        type uint32;
        description
          "Sdh error B2 alarm threshold,default value is 3.";
      }
      leaf sdh-b2-error-interval {
        type uint32;
        description
          "Sdh B2 error alarm interval time (unit is second),default value is 10s.";
      }
      leaf port-name {
        type string {
          length "1..32";
        }
        description
          "Port name of alarm monitor table.";
      }
    }
  }
  augment "/ncs:devices/ncs:device/ncs:notifications/ncs:received-notifications/ncs:notification/ncs:data" {
    container post-fec-error-resume {
      presence "";
      config false;
      description
        "The post fec error crooected alarm disappears.";
      leaf post-fec-error-statistics {
        type uint64;
        description
          "Indicates the post-FEC bit error statistics.";
      }
      leaf port-name {
        type string {
          length "1..32";
        }
        description
          "Port name of alarm monitor table.";
      }
    }
  }
  augment "/ncs:devices/ncs:device/ncs:notifications/ncs:received-notifications/ncs:notification/ncs:data" {
    container post-fec-error-rising {
      presence "";
      config false;
      description
        "The post fec error crooected alarm appears.";
      leaf post-fec-error-statistics {
        type uint64;
        description
          "Indicates the post-FEC bit error statistics.";
      }
      leaf port-name {
        type string {
          length "1..32";
        }
        description
          "Port name of alarm monitor table.";
      }
    }
  }
  augment "/ncs:devices/ncs:device/ncs:notifications/ncs:received-notifications/ncs:notification/ncs:data" {
    container pause-frame-resume {
      presence "";
      config false;
      description
        "Pause frame alarm resume.";
      leaf pause-frame-statistics {
        type uint64;
        description
          "Pause frame statistics value.";
      }
      leaf pause-frame-threshold {
        type uint32;
        description
          "Pause frame alarm threshold,and 0 is an invalid value.";
      }
      leaf pause-frame-interval {
        type uint32;
        description
          "Pause frame alarm interval time (unit is second),and 0 is an invalid value.";
      }
      leaf port-name {
        type string {
          length "1..32";
        }
        description
          "Port name of alarm monitor table.";
      }
    }
  }
  augment "/ncs:devices/ncs:device/ncs:notifications/ncs:received-notifications/ncs:notification/ncs:data" {
    container pause-frame-rising {
      presence "";
      config false;
      description
        "Pause frame alarm.";
      leaf pause-frame-statistics {
        type uint64;
        description
          "Pause frame statistics value.";
      }
      leaf pause-frame-threshold {
        type uint32;
        description
          "Pause frame alarm threshold,and 0 is an invalid value.";
      }
      leaf pause-frame-interval {
        type uint32;
        description
          "Pause frame alarm interval time (unit is second),and 0 is an invalid value.";
      }
      leaf port-name {
        type string {
          length "1..32";
        }
        description
          "Port name of alarm monitor table.";
      }
    }
  }
  augment "/ncs:devices/ncs:device/ncs:notifications/ncs:received-notifications/ncs:notification/ncs:data" {
    container crc-error-resume {
      presence "";
      config false;
      description
        "CRC error alarm resume.";
      leaf crc-error-statistics {
        type uint64;
        description
          "CRC error statistics value.";
      }
      leaf crc-error-threshold {
        type uint32;
        description
          "CRC error alarm threshold, default value is 3 and 0 is an invalid value.";
      }
      leaf crc-error-interval {
        type uint32;
        description
          "CRC error alarm interval time (unit is second), default value is 10s and 0 is an invalid value.";
      }
      leaf port-name {
        type string {
          length "1..32";
        }
        description
          "Port name of alarm monitor table.";
      }
    }
  }
  augment "/ncs:devices/ncs:device/ncs:notifications/ncs:received-notifications/ncs:notification/ncs:data" {
    container crc-error-rising {
      presence "";
      config false;
      description
        "CRC error alarm.";
      leaf crc-error-statistics {
        type uint64;
        description
          "CRC error statistics value.";
      }
      leaf crc-error-threshold {
        type uint32;
        description
          "CRC error alarm threshold, default value is 3 and 0 is an invalid value.";
      }
      leaf crc-error-interval {
        type uint32;
        description
          "CRC error alarm interval time (unit is second), default value is 10s and 0 is an invalid value.";
      }
      leaf port-name {
        type string {
          length "1..32";
        }
        description
          "Port name of alarm monitor table.";
      }
    }
  }
  augment "/ncs:devices/ncs:device/ncs:notifications/ncs:received-notifications/ncs:notification/ncs:data" {
    container bad-bytes-error-resume {
      presence "";
      config false;
      description
        "Port monitor bad bytes error resume.";
      leaf bad-bytes-error-statistics {
        type uint64;
        description
          "Port monitor bad bytes error statistics.";
      }
      leaf bad-bytes-error-threshold {
        type uint32;
        description
          "Port monitor bad bytes error threshold.";
      }
      leaf bad-bytes-error-interval {
        type uint32;
        description
          "Port monitor bad bytes error interval.";
      }
      leaf port-name {
        type string {
          length "1..32";
        }
        description
          "Port name of alarm monitor table.";
      }
    }
  }
  augment "/ncs:devices/ncs:device/ncs:notifications/ncs:received-notifications/ncs:notification/ncs:data" {
    container bad-bytes-error-rising {
      presence "";
      config false;
      description
        "Port monitor bad bytes error rising.";
      leaf bad-bytes-error-statistics {
        type uint64;
        description
          "Port monitor bad bytes error statistics.";
      }
      leaf bad-bytes-error-threshold {
        type uint32;
        description
          "Port monitor bad bytes error threshold.";
      }
      leaf bad-bytes-error-interval {
        type uint32;
        description
          "Port monitor bad bytes error interval.";
      }
      leaf port-name {
        type string {
          length "1..32";
        }
        description
          "Port name of alarm monitor table.";
      }
    }
  }
  augment "/ncs:devices/ncs:device/ncs:notifications/ncs:received-notifications/ncs:notification/ncs:data" {
    container humidity-abnormal-resume {
      presence "";
      config false;
      description
        "Humidity back to normal level.";
      leaf exception-type {
        type ncs_rpc_notif_exception-type;
        description
          "Type of the notification entity threshold.";
      }
      leaf threshold {
        type uint32;
        description
          "The threshold value of temperature, humidity, fog......";
      }
      leaf current {
        type uint32;
        description
          "The current value that been measured.";
      }
      leaf fault-code {
        type devm:ncs_rpc_notif_notification-probable-cause-type;
        description
          "To describe the fault id of trap.";
      }
    }
  }
  augment "/ncs:devices/ncs:device/ncs:notifications/ncs:received-notifications/ncs:notification/ncs:data" {
    container humidity-abnormal {
      presence "";
      config false;
      description
        "Humidity rise over or fall below the alarm threshold.";
      leaf exception-type {
        type ncs_rpc_notif_exception-type;
        description
          "Type of the notification entity threshold.";
      }
      leaf threshold {
        type uint32;
        description
          "The threshold value of temperature, humidity, fog......";
      }
      leaf current {
        type uint32;
        description
          "The current value that been measured.";
      }
      leaf fault-code {
        type devm:ncs_rpc_notif_notification-probable-cause-type;
        description
          "To describe the fault id of trap.";
      }
    }
  }
  augment "/ncs:devices/ncs:device/ncs:notifications/ncs:received-notifications/ncs:notification/ncs:data" {
    container trace-unstable-lp-resume {
      presence "";
      config false;
      description
        "This object indicates that a clear alarm is generated when the higher order path (HP) trace identifier becomes stable.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container trace-unstable-lp {
      presence "";
      config false;
      description
        "This object indicates that an alarm is generated when the higher order path (HP) trace identifier is unstable.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container gps-module-remove {
      presence "";
      config false;
      description
        "The gps module was removed.";
      leaf entity-physical-index {
        type uint32;
        description
          "The index of physical.";
      }
      leaf port-name {
        type string {
          length "1..32";
        }
        description
          "Entity physical name.";
      }
    }
  }
  augment "/ncs:devices/ncs:device/ncs:notifications/ncs:received-notifications/ncs:notification/ncs:data" {
    container gps-module-insert {
      presence "";
      config false;
      description
        "The gps module was inserted.";
      leaf entity-physical-index {
        type uint32;
        description
          "The index of physical.";
      }
      leaf port-name {
        type string {
          length "1..32";
        }
        description
          "Entity physical name.";
      }
    }
  }
  augment "/ncs:devices/ncs:device/ncs:notifications/ncs:received-notifications/ncs:notification/ncs:data" {
    container gate-abnormal-resume {
      presence "";
      config false;
      description
        "Gate switch to normal status.";
      leaf exception-type {
        type ncs_rpc_notif_exception-type;
        description
          "Type of the notification entity threshold.";
      }
      leaf threshold {
        type uint32;
        description
          "The threshold value of temperature, humidity, fog......";
      }
      leaf current {
        type uint32;
        description
          "The current value that been measured.";
      }
      leaf fault-code {
        type devm:ncs_rpc_notif_notification-probable-cause-type;
        description
          "To describe the fault id of trap.";
      }
    }
  }
  augment "/ncs:devices/ncs:device/ncs:notifications/ncs:received-notifications/ncs:notification/ncs:data" {
    container gate-abnormal {
      presence "";
      config false;
      description
        "Gate switch to the alarm status.";
      leaf exception-type {
        type ncs_rpc_notif_exception-type;
        description
          "Type of the notification entity threshold.";
      }
      leaf threshold {
        type uint32;
        description
          "The threshold value of temperature, humidity, fog......";
      }
      leaf current {
        type uint32;
        description
          "The current value that been measured.";
      }
      leaf fault-code {
        type devm:ncs_rpc_notif_notification-probable-cause-type;
        description
          "To describe the fault id of trap.";
      }
    }
  }
  augment "/ncs:devices/ncs:device/ncs:notifications/ncs:received-notifications/ncs:notification/ncs:data" {
    container fog-abnormal-resume {
      presence "";
      config false;
      description
        "Fog back to normal level.";
      leaf exception-type {
        type ncs_rpc_notif_exception-type;
        description
          "Type of the notification entity threshold.";
      }
      leaf threshold {
        type uint32;
        description
          "The threshold value of temperature, humidity, fog......";
      }
      leaf current {
        type uint32;
        description
          "The current value that been measured.";
      }
      leaf fault-code {
        type devm:ncs_rpc_notif_notification-probable-cause-type;
        description
          "To describe the fault id of trap.";
      }
    }
  }
  augment "/ncs:devices/ncs:device/ncs:notifications/ncs:received-notifications/ncs:notification/ncs:data" {
    container fog-abnormal {
      presence "";
      config false;
      description
        "Fog rise over alarm threshold.";
      leaf exception-type {
        type ncs_rpc_notif_exception-type;
        description
          "Type of the notification entity threshold.";
      }
      leaf threshold {
        type uint32;
        description
          "The threshold value of temperature, humidity, fog......";
      }
      leaf current {
        type uint32;
        description
          "The current value that been measured.";
      }
      leaf fault-code {
        type devm:ncs_rpc_notif_notification-probable-cause-type;
        description
          "To describe the fault id of trap.";
      }
    }
  }
  augment "/ncs:devices/ncs:device/ncs:notifications/ncs:received-notifications/ncs:notification/ncs:data" {
    container b3-configured-exceed-resume {
      presence "";
      config false;
      description
        "This object indicates that the number of bit errors on the B3 falls below the configured threshold.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
      leaf hp-id {
        type uint32;
        description
          "Indicates the higher order path ID.";
      }
    }
  }
  augment "/ncs:devices/ncs:device/ncs:notifications/ncs:received-notifications/ncs:notification/ncs:data" {
    container b3-configured-exceed {
      presence "";
      config false;
      description
        "This object indicates that the number of bit errors on the B3 exceeds the configured threshold.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
      leaf hp-id {
        type uint32;
        description
          "Indicates the higher order path ID.";
      }
    }
  }
  augment "/ncs:devices/ncs:device/ncs:notifications/ncs:received-notifications/ncs:notification/ncs:data" {
    container b2-configured-exceed-resume {
      presence "";
      config false;
      description
        "This object indicates that the number of error bits for the B2 falls below the configured threshold.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container b2-configured-exceed {
      presence "";
      config false;
      description
        "This object indicates that the number of error bits for the B2 exceeds a configured threshold.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container b1-configured-exceed-resume {
      presence "";
      config false;
      description
        "This object indicates that the number of error bits for the B1 RS falls below the configured threshold.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container b1-configured-exceed {
      presence "";
      config false;
      description
        "This object indicates that the number of error bits for the B1 RS exceeds a configured threshold.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container au-pointer-loss-lp-resume {
      presence "";
      config false;
      description
        "This object indicates the loss of the AU pointer in a higher order path (HP) indication signal alarm is cleard.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container au-pointer-loss-lp {
      presence "";
      config false;
      description
        "This object indicates the loss of the AU pointer in a higher order path (HP) indication signal alarm is generated.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container upstream-pcm-resume {
      presence "";
      config false;
      description
        "Upstream signals recovered.";
      leaf physical-port-index {
        type uint32;
        description
          "Indicates the physical port index.";
      }
      leaf port-name {
        type string {
          length "1..32";
        }
        description
          "Indicates the physical port name.";
      }
    }
  }
  augment "/ncs:devices/ncs:device/ncs:notifications/ncs:received-notifications/ncs:notification/ncs:data" {
    container upstream-pcm {
      presence "";
      config false;
      description
        "Upstream signals were abnormal.";
      leaf physical-port-index {
        type uint32;
        description
          "Indicates the physical port index.";
      }
      leaf port-name {
        type string {
          length "1..32";
        }
        description
          "Indicates the physical port name.";
      }
    }
  }
  augment "/ncs:devices/ncs:device/ncs:notifications/ncs:received-notifications/ncs:notification/ncs:data" {
    container resource-dead-line-resume {
      presence "";
      config false;
      description
        "Port authorization grace period alarm resume.";
      leaf gtl-remain-time {
        type uint32;
        units "d";
        description
          "Gtl remain time.";
      }
      leaf physical-index {
        type uint32;
        description
          "Indicates the physical port index.";
      }
      leaf port-name {
        type string {
          length "1..32";
        }
        description
          "Indicates the physical port name.";
      }
    }
  }
  augment "/ncs:devices/ncs:device/ncs:notifications/ncs:received-notifications/ncs:notification/ncs:data" {
    container resource-dead-line {
      presence "";
      config false;
      description
        "Port authorization grace period alarm.";
      leaf gtl-remain-time {
        type uint32;
        units "d";
        description
          "Gtl remain time.";
      }
      leaf physical-index {
        type uint32;
        description
          "Indicates the physical port index.";
      }
      leaf port-name {
        type string {
          length "1..32";
        }
        description
          "Indicates the physical port name.";
      }
    }
  }
  augment "/ncs:devices/ncs:device/ncs:notifications/ncs:received-notifications/ncs:notification/ncs:data" {
    container port-license-act-success {
      presence "";
      config false;
      description
        "This object indicates that the license for a physical port is successfully activated.";
      leaf item-name {
        type string {
          length "1..32";
        }
        description
          "Item name.";
      }
      leaf physical-index {
        type uint32;
        description
          "Indicates the physical port index.";
      }
      leaf port-name {
        type string {
          length "1..32";
        }
        description
          "Indicates the physical port name.";
      }
    }
  }
  augment "/ncs:devices/ncs:device/ncs:notifications/ncs:received-notifications/ncs:notification/ncs:data" {
    container port-license-act-fail {
      presence "";
      config false;
      description
        "This object indicates that the license for a physical port fails to be activated.";
      leaf item-name {
        type string {
          length "1..32";
        }
        description
          "Item name.";
      }
      leaf physical-index {
        type uint32;
        description
          "Indicates the physical port index.";
      }
      leaf port-name {
        type string {
          length "1..32";
        }
        description
          "Indicates the physical port name.";
      }
    }
  }
  augment "/ncs:devices/ncs:device/ncs:notifications/ncs:received-notifications/ncs:notification/ncs:data" {
    container remote-failure-lp-resume {
      presence "";
      config false;
      description
        "This object indicates that a clear alarm is generated when the lower order path (LP) remote failure indication (RFI) signal is cleared.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf lp-id {
        type uint32;
        description
          "Indicates the low order path ID.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container remote-failure-lp {
      presence "";
      config false;
      description
        "This object indicates that an alarm is generated when a lower order path (LP) remote failure indication (RFI) signal is detected.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf lp-id {
        type uint32;
        description
          "Indicates the low order path ID.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container remote-defect-lp-resume {
      presence "";
      config false;
      description
        "This object indicates that a lower order path (LP) remote defect indication (PRDI) alarm is cleared.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf lp-id {
        type uint32;
        description
          "Indicates the low order path ID.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container remote-defect-lp {
      presence "";
      config false;
      description
        "This object indicates that a lower order path (LP) remote defect indication (PRDI) alarm is generated.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf lp-id {
        type uint32;
        description
          "Indicates the low order path ID.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container loss-au-lp-resume {
      presence "";
      config false;
      description
        "This object indicates that the alarm generated due to the loss of the AU pointer in the lower order path (LP) is cleared.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf lp-id {
        type uint32;
        description
          "Indicates the low order path ID.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container loss-au-lp {
      presence "";
      config false;
      description
        "This object indicates that an alarm is generated when the administrative unit (AU) pointer in the lower order path (LP) is lost.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf lp-id {
        type uint32;
        description
          "Indicates the low order path ID.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container v5-virtual-container-resume {
      presence "";
      config false;
      description
        "This object indicates that the alarm indication signal generated in the virtual container is cleared.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf lp-id {
        type uint32;
        description
          "Indicates the low order path ID.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container v5-virtual-container {
      presence "";
      config false;
      description
        "This object indicates that an alarm indication signal is generated in the virtual container.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf lp-id {
        type uint32;
        description
          "Indicates the low order path ID.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container tributary-unit-lp-resume {
      presence "";
      config false;
      description
        "This object indicates that the lower order path (LP) tributary unit (TU) alarm is cleared.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf lp-id {
        type uint32;
        description
          "Indicates the low order path ID.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container tributary-unit-lp {
      presence "";
      config false;
      description
        "This object indicates the lower order path (LP) tributary unit (TU) alarm indication.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf lp-id {
        type uint32;
        description
          "Indicates the low order path ID.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container out-of-lock-clock-resume {
      presence "";
      config false;
      description
        "This object indicates that a clear alarm is generated when there is a clock on the receive line.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container out-of-lock-clock {
      presence "";
      config false;
      description
        "This object indicates that an alarm is generated when out of lock of received reference clock.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container unequipped-lp-resume {
      presence "";
      config false;
      description
        "This object indicates that a lower order path (LP) unequipped indication signal (PUNEQ) alarm is cleard.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf lp-id {
        type uint32;
        description
          "Indicates the low order path ID.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container unequipped-lp {
      presence "";
      config false;
      description
        "This object indicates that a lower order path (LP) unequipped indication signal (PUNEQ) alarm is generated.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf lp-id {
        type uint32;
        description
          "Indicates the low order path ID.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container trace-mismatch-lp-resume {
      presence "";
      config false;
      description
        "This object indicates that signal label mismatch alarm on VC12 lower order path alarm is cleared.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf lp-id {
        type uint32;
        description
          "Indicates the low order path ID.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container trace-mismatch-lp {
      presence "";
      config false;
      description
        "This object indicates that signal label mismatch alarm on VC12 lower order path alarm.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf lp-id {
        type uint32;
        description
          "Indicates the low order path ID.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container signal-mismatch-lp-resume {
      presence "";
      config false;
      description
        "This object indicates that the lower order path (LP) signal label mismatch alarm is cleared.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf lp-id {
        type uint32;
        description
          "Indicates the low order path ID.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container signal-mismatch-lp {
      presence "";
      config false;
      description
        "This object indicates a lower order path (LP) signal label mismatch alarm.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf lp-id {
        type uint32;
        description
          "Indicates the low order path ID.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container j0-trace-mismatch-resume {
      presence "";
      config false;
      description
        "This object indicates that the alarm for j0 trace identifier mismatch is cleared.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container j0-trace-mismatch {
      presence "";
      config false;
      description
        "This object indicates that an alarm for trace j0 identifier mismatch is generated.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container upstream-e3-resume {
      presence "";
      config false;
      description
        "Indicates the alarm is cleared.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container upstream-e3 {
      presence "";
      config false;
      description
        "Indicates the alarm is detected.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container remote-e3-resume {
      presence "";
      config false;
      description
        "Indicates the alarm is cleared.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container remote-e3 {
      presence "";
      config false;
      description
        "Indicates the alarm is detected.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container upstream-e1-resume {
      presence "";
      config false;
      description
        "This object indicates that the upstream alarm indication signal generated on an E1 interface is cleared.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container upstream-e1 {
      presence "";
      config false;
      description
        "This object indicates that an upstream alarm indication signal is generated on an E1 interface.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container loss-multiframe-e1-resume {
      presence "";
      config false;
      description
        "This object indicates that the LOM alarm on the framed E1 is cleared.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container loss-multiframe-e1 {
      presence "";
      config false;
      description
        "This object indicates an LOM alarm on the framed E1.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container errored-second-exceed-resume {
      presence "";
      config false;
      description
        "This object indicates that the number of errored seconds falls below a specified threshold.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container errored-second-exceed {
      presence "";
      config false;
      description
        "This object indicates that the number of errored seconds exceeds a specified threshold.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container downstream-e1-resume {
      presence "";
      config false;
      description
        "This object indicates that the downstream alarm indication signal generated on an E1 interface is cleared.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container downstream-e1 {
      presence "";
      config false;
      description
        "This object indicates that a downstream alarm indication signal is generated on an E1 interface.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container remote-indication-e1-resume {
      presence "";
      config false;
      description
        "This object indicates that the RAI signal generated on an E1 link is cleared.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container remote-indication-e1 {
      presence "";
      config false;
      description
        "This object indicates that a remote alarm indication (RAI) signal is generated on an E1 link.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container upstream-e1-cpos-resume {
      presence "";
      config false;
      description
        "This object indicates that an upstream alarm indication signal generated on an E1 link channelized from VC12 is cleared.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf lp-id {
        type uint32;
        description
          "Indicates the low order path ID.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container upstream-e1-cpos {
      presence "";
      config false;
      description
        "This object indicates that an upstream alarm indication signal is generated on an E1 link channelized from VC12.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf lp-id {
        type uint32;
        description
          "Indicates the low order path ID.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container loss-multiframe-e1-cpos-resume {
      presence "";
      config false;
      description
        "This object indicates that the OOM alarm generated on the framed E1 channelized from VC12 is cleared.";
      leaf card-id {
        type uint32;
        description
          "Indicates the card ID.";
      }
      leaf hp-id {
        type uint32;
        description
          "Indicates the higher order path ID.";
      }
      leaf lp-id {
        type uint32;
        description
          "Indicates the lower order path ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container loss-multiframe-e1-cpos {
      presence "";
      config false;
      description
        "This object indicates that an out of multiframe (OOM) alarm is generated on the framed E1 channelized from VC12.";
      leaf card-id {
        type uint32;
        description
          "Indicates the card ID.";
      }
      leaf hp-id {
        type uint32;
        description
          "Indicates the higher order path ID.";
      }
      leaf lp-id {
        type uint32;
        description
          "Indicates the lower order path ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container loss-of-frame-e1-cpos-resume {
      presence "";
      config false;
      description
        "This object indicates that the OOF alarm generated on the framed E1 channelized from VC12 is cleared.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf lp-id {
        type uint32;
        description
          "Indicates the low order path ID.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container loss-of-frame-e1-cpos {
      presence "";
      config false;
      description
        "This object indicates that an out of frame (OOF) alarm is generated on the framed E1 channelized from VC12.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf lp-id {
        type uint32;
        description
          "Indicates the low order path ID.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container downstream-e1-cpos-resume {
      presence "";
      config false;
      description
        "This object indicates that the downstream alarm indication signal generated on an E1 link channelized from VC12 is cleared.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf lp-id {
        type uint32;
        description
          "Indicates the low order path ID.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container downstream-e1-cpos {
      presence "";
      config false;
      description
        "This object indicates that a downstream alarm indication signal is generated on an E1 link channelized from VC12.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf lp-id {
        type uint32;
        description
          "Indicates the low order path ID.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container cpos-e1-rai-signal-resume {
      presence "";
      config false;
      description
        "This object indicates that the RAI signal generated on an E1 link channelized from VC12 is cleared.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf lp-id {
        type uint32;
        description
          "Indicates the low order path ID.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container cpos-e1-rai-signal {
      presence "";
      config false;
      description
        "This object indicates that an RAI signal is generated on an E1 link channelized from VC12.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf lp-id {
        type uint32;
        description
          "Indicates the low order path ID.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container channel-loopback-resume {
      presence "";
      config false;
      description
        "This object indicates that a clear alarm is generated when a channel no loopback.";
      leaf hp-id {
        type uint32;
        description
          "Indicates the higher order path ID.";
      }
      leaf index {
        type uint32;
        description
          "Indicates the physical port index.";
      }
      leaf port-name {
        type string {
          length "1..32";
        }
        description
          "Indicates the physical port name.";
      }
      leaf loop-type {
        type ncs_rpc_notif_loop-type;
        description
          "Type of the notification loop. The value can be one -of the following: - 0: stop-loopback - 1: local - 2: remote.";
      }
      leaf lp-id {
        type uint32;
        description
          "Indicates the lower order path ID.";
      }
    }
  }
  augment "/ncs:devices/ncs:device/ncs:notifications/ncs:received-notifications/ncs:notification/ncs:data" {
    container channel-loopback {
      presence "";
      config false;
      description
        "This object indicates that an alarm is generated when a channel loopback.";
      leaf hp-id {
        type uint32;
        description
          "Indicates the higher order path ID.";
      }
      leaf index {
        type uint32;
        description
          "Indicates the physical port index.";
      }
      leaf port-name {
        type string {
          length "1..32";
        }
        description
          "Indicates the physical port name.";
      }
      leaf loop-type {
        type ncs_rpc_notif_loop-type;
        description
          "Type of the notification loop. The value can be one -of the following: - 0: stop-loopback - 1: local - 2: remote.";
      }
      leaf lp-id {
        type uint32;
        description
          "Indicates the lower order path ID.";
      }
    }
  }
  augment "/ncs:devices/ncs:device/ncs:notifications/ncs:received-notifications/ncs:notification/ncs:data" {
    container b3-default-exceed-resume {
      presence "";
      config false;
      description
        "This object indicates that a clear alarm is generated when the number of B3 errors falls below a specified threshold.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container b3-default-exceed {
      presence "";
      config false;
      description
        "This object indicates that an alarm is generated when the number of B3 errors exceeds a specified threshold.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container bip2-default-exceed-resume {
      presence "";
      config false;
      description
        "This object indicates that a clear alarm is generated when the number of BIP2 errors falls below a specified threshold.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf lp-id {
        type uint32;
        description
          "Indicates the low order path ID.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container bip2-default-exceed {
      presence "";
      config false;
      description
        "This object indicates that an alarm is generated when the number of BIP2 errors exceeds a specified threshold.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf lp-id {
        type uint32;
        description
          "Indicates the low order path ID.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container b1-default-exceed-resume {
      presence "";
      config false;
      description
        "This object indicates that a clear alarm is generated when the number of B1 errors falls below a specified threshold.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container b1-default-exceed {
      presence "";
      config false;
      description
        "This object indicates that an alarm is generated when the number of B1 errors exceeds a specified threshold.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container au-hp-resume {
      presence "";
      config false;
      description
        "This object indicates that the administrative unit (AU) pointer in the higher order path (HP) indication signal alarm is cleared.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container au-hp {
      presence "";
      config false;
      description
        "This object indicates that the administrative unit (AU) pointer in a higher order path (HP) indication signal alarm is generated.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:notifications/ncs:received-notifications/ncs:notification/ncs:data" {
    container flow-control-pause-frame-abnormal-resume {
      presence "";
      config false;
      description
        "The port recovered and did not receive pause frames.";
      leaf entity-index {
        type uint32;
        description
          "Indicates the index of an entity.";
      }
      leaf entity-name {
        type string {
          length "0..255";
        }
        description
          "Indicates the name of an entity.";
      }
    }
  }
  augment "/ncs:devices/ncs:device/ncs:notifications/ncs:received-notifications/ncs:notification/ncs:data" {
    container flow-control-pause-frame-abnormal {
      presence "";
      config false;
      description
        "The port continuously received a large number of pause frames when it did not forward packets.";
      leaf entity-index {
        type uint32;
        description
          "Indicates the index of an entity.";
      }
      leaf entity-name {
        type string {
          length "0..255";
        }
        description
          "Indicates the name of an entity.";
      }
    }
  }
  augment "/ncs:devices/ncs:device/ncs:notifications/ncs:received-notifications/ncs:notification/ncs:data" {
    container card-fail-resume {
      presence "";
      config false;
      description
        "The card resumed from partial failure.";
      leaf entity-index {
        type uint32;
        description
          "Indicates the index of an entity.";
      }
      leaf entity-name {
        type string {
          length "0..255";
        }
        description
          "Indicates the name of an entity.";
      }
      leaf entity-type {
        type devm:ncs_rpc_notif_notification-entity-type;
        description
          "Type of the notification entity. The value can be one of the following: - 1: MPU - 2: LPU - 3: SFU - 4: PIC - 5: CF card - 6: OFC.";
      }
      leaf fault-id {
        type devm:ncs_rpc_notif_notification-probable-cause-type;
        description
          "Indicates the error code.";
      }
    }
  }
  augment "/ncs:devices/ncs:device/ncs:notifications/ncs:received-notifications/ncs:notification/ncs:data" {
    container card-fail {
      presence "";
      config false;
      description
        "The card partially failed.";
      leaf entity-index {
        type uint32;
        description
          "Indicates the index of an entity.";
      }
      leaf entity-name {
        type string {
          length "0..255";
        }
        description
          "Indicates the name of an entity.";
      }
      leaf entity-type {
        type devm:ncs_rpc_notif_notification-entity-type;
        description
          "Type of the notification entity. The value can be one of the following: - 1: MPU - 2: LPU - 3: SFU - 4: PIC - 5: CF card - 6: OFC.";
      }
      leaf fault-id {
        type devm:ncs_rpc_notif_notification-probable-cause-type;
        description
          "Indicates the error code.";
      }
    }
  }
  augment "/ncs:devices/ncs:device/ncs:notifications/ncs:received-notifications/ncs:notification/ncs:data" {
    container card-invalid-resume {
      presence "";
      config false;
      description
        "The card resumed from unavailable.";
      leaf entity-index {
        type uint32;
        description
          "Indicates the index of an entity.";
      }
      leaf entity-name {
        type string {
          length "0..255";
        }
        description
          "Indicates the name of an entity.";
      }
      leaf entity-type {
        type devm:ncs_rpc_notif_notification-entity-type;
        description
          "Type of the notification entity. The value can be one of the following: - 1: MPU - 2: LPU - 3: SFU - 4: PIC - 5: CF card - 6: OFC.";
      }
      leaf fault-id {
        type devm:ncs_rpc_notif_notification-probable-cause-type;
        description
          "Indicates the error code.";
      }
    }
  }
  augment "/ncs:devices/ncs:device/ncs:notifications/ncs:received-notifications/ncs:notification/ncs:data" {
    container card-invalid {
      presence "";
      config false;
      description
        "The card unavailable.";
      leaf entity-index {
        type uint32;
        description
          "Indicates the index of an entity.";
      }
      leaf entity-name {
        type string {
          length "0..255";
        }
        description
          "Indicates the name of an entity.";
      }
      leaf entity-type {
        type devm:ncs_rpc_notif_notification-entity-type;
        description
          "Type of the notification entity. The value can be one of the following: - 1: MPU - 2: LPU - 3: SFU - 4: PIC - 5: CF card - 6: OFC.";
      }
      leaf fault-id {
        type devm:ncs_rpc_notif_notification-probable-cause-type;
        description
          "Indicates the error code.";
      }
    }
  }
  augment "/ncs:devices/ncs:device/ncs:notifications/ncs:received-notifications/ncs:notification/ncs:data" {
    container card-insert {
      presence "";
      config false;
      description
        "The card was inserted.";
      leaf entity-index {
        type uint32;
        description
          "Indicates the index of an entity.";
      }
      leaf entity-name {
        type string {
          length "0..255";
        }
        description
          "Indicates the name of an entity.";
      }
      leaf entity-type {
        type devm:ncs_rpc_notif_notification-entity-type;
        description
          "Type of the notification entity. The value can be one of the following: - 1: MPU - 2: LPU - 3: SFU - 4: PIC - 5: CF card - 6: OFC.";
      }
      leaf fault-id {
        type devm:ncs_rpc_notif_notification-probable-cause-type;
        description
          "To describe the fault id of trap.";
      }
    }
  }
  augment "/ncs:devices/ncs:device/ncs:notifications/ncs:received-notifications/ncs:notification/ncs:data" {
    container card-remove {
      presence "";
      config false;
      description
        "The card was removed.";
      leaf entity-index {
        type uint32;
        description
          "Indicates the index of an entity.";
      }
      leaf entity-name {
        type string {
          length "0..255";
        }
        description
          "Indicates the name of an entity.";
      }
      leaf entity-type {
        type devm:ncs_rpc_notif_notification-entity-type;
        description
          "Type of the notification entity. The value can be one of the following: - 1: MPU - 2: LPU - 3: SFU - 4: PIC - 5: CF card - 6: OFC.";
      }
      leaf fault-id {
        type devm:ncs_rpc_notif_notification-probable-cause-type;
        description
          "To describe the fault id of trap.";
      }
    }
  }
  augment "/ncs:devices/ncs:device/ncs:notifications/ncs:received-notifications/ncs:notification/ncs:data" {
    container optical-invalid-resume {
      presence "";
      config false;
      description
        "Optical module resume from invalid situation.";
      leaf entity-index {
        type uint32;
        description
          "Indicates the index of an entity.";
      }
      leaf entity-name {
        type string {
          length "0..255";
        }
        description
          "Indicates the name of an entity.";
      }
      leaf fault-id {
        type devm:ncs_rpc_notif_notification-probable-cause-type;
        description
          "Indicates the error code.";
      }
    }
  }
  augment "/ncs:devices/ncs:device/ncs:notifications/ncs:received-notifications/ncs:notification/ncs:data" {
    container optical-invalid {
      presence "";
      config false;
      description
        "Optical module is invalid.";
      leaf entity-index {
        type uint32;
        description
          "Indicates the index of an entity.";
      }
      leaf entity-name {
        type string {
          length "0..255";
        }
        description
          "Indicates the name of an entity.";
      }
      leaf fault-id {
        type devm:ncs_rpc_notif_notification-probable-cause-type;
        description
          "Indicates the error code.";
      }
    }
  }
  augment "/ncs:devices/ncs:device/ncs:notifications/ncs:received-notifications/ncs:notification/ncs:data" {
    container optical-unauthorized-resume {
      presence "";
      config false;
      description
        "The alarm on optical module not certified by Ethernet Switch was cleared.";
      leaf entity-index {
        type uint32;
        description
          "Indicates the index of an entity.";
      }
      leaf entity-name {
        type string {
          length "0..255";
        }
        description
          "Indicates the name of an entity.";
      }
      leaf fault-id {
        type devm:ncs_rpc_notif_notification-probable-cause-type;
        description
          "Indicates the error code.";
      }
    }
  }
  augment "/ncs:devices/ncs:device/ncs:notifications/ncs:received-notifications/ncs:notification/ncs:data" {
    container optical-unauthorized {
      presence "";
      config false;
      description
        "The optical module was not certified by Ethernet Switch.";
      leaf entity-index {
        type uint32;
        description
          "Indicates the index of an entity.";
      }
      leaf entity-name {
        type string {
          length "0..255";
        }
        description
          "Indicates the name of an entity.";
      }
      leaf fault-id {
        type devm:ncs_rpc_notif_notification-probable-cause-type;
        description
          "Indicates the error code.";
      }
    }
  }
  augment "/ncs:devices/ncs:device/ncs:notifications/ncs:received-notifications/ncs:notification/ncs:data" {
    container optical-insert {
      presence "";
      config false;
      description
        "Optical module has been inserted.";
      leaf entity-index {
        type uint32;
        description
          "Indicates the index of an entity.";
      }
      leaf entity-name {
        type string {
          length "0..255";
        }
        description
          "Indicates the name of an entity.";
      }
      leaf fault-id {
        type devm:ncs_rpc_notif_notification-probable-cause-type;
        description
          "Indicates the error code.";
      }
    }
  }
  augment "/ncs:devices/ncs:device/ncs:notifications/ncs:received-notifications/ncs:notification/ncs:data" {
    container optical-remove {
      presence "";
      config false;
      description
        "Optical module has been removed.";
      leaf entity-index {
        type uint32;
        description
          "Indicates the index of an entity.";
      }
      leaf entity-name {
        type string {
          length "0..255";
        }
        description
          "Indicates the name of an entity.";
      }
      leaf fault-id {
        type devm:ncs_rpc_notif_notification-probable-cause-type;
        description
          "Indicates the error code.";
      }
    }
  }
  augment "/ncs:devices/ncs:device/ncs:netconf-notifications/ncs:received-notifications/ncs:notification/ncs:data" {
    container tim-trace-mismatch-resume {
      presence "";
      config false;
      description
        "This object indicates that a clear alarm is generated when TIM trace identifiers between the local and remote ends match.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container tim-trace-mismatch {
      presence "";
      config false;
      description
        "This object indicates that an alarm is generated when TIM trace identifiers between the local and remote ends mismatch.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container section-alignment-resume {
      presence "";
      config false;
      description
        "This object indicates that a clear alarm is generated when the section frame alignment error between the local and remote ends is corrected.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container section-alignment {
      presence "";
      config false;
      description
        "This object indicates that an alarm is generated when the section frame alignment between the local and remote ends is incorrect.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container ms-b2-degrade-resume {
      presence "";
      config false;
      description
        "This object indicates that the alarm for the signal degrade in the multiplex section B2 is cleared.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container ms-b2-degrade {
      presence "";
      config false;
      description
        "This object indicates the signal degrade in the multiplex section B2.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container remote-fault-resume {
      presence "";
      config false;
      description
        "This object indicates that a clear alarm is generated when the transmit link from the remote device to the local device recovers.";
      leaf physical-port-index {
        type uint32;
        description
          "Indicates the physical port index.";
      }
      leaf port-name {
        type string {
          length "1..32";
        }
        description
          "Indicates the physical port name.";
      }
    }
  }
  augment "/ncs:devices/ncs:device/ncs:netconf-notifications/ncs:received-notifications/ncs:notification/ncs:data" {
    container remote-fault {
      presence "";
      config false;
      description
        "This object indicates that an alarm is generated when the transmit link from the remote device to the local device fails.";
      leaf physical-port-index {
        type uint32;
        description
          "Indicates the physical port index.";
      }
      leaf port-name {
        type string {
          length "1..32";
        }
        description
          "Indicates the physical port name.";
      }
    }
  }
  augment "/ncs:devices/ncs:device/ncs:netconf-notifications/ncs:received-notifications/ncs:notification/ncs:data" {
    container remote-defect-resume {
      presence "";
      config false;
      description
        "The peer end recovered from faults.";
      leaf physical-port-index {
        type uint32;
        description
          "Indicates the physical port index.";
      }
      leaf port-name {
        type string {
          length "1..32";
        }
        description
          "Indicates the physical port name.";
      }
    }
  }
  augment "/ncs:devices/ncs:device/ncs:netconf-notifications/ncs:received-notifications/ncs:notification/ncs:data" {
    container remote-defect {
      presence "";
      config false;
      description
        "The peer end was faulty.";
      leaf physical-port-index {
        type uint32;
        description
          "Indicates the physical port index.";
      }
      leaf port-name {
        type string {
          length "1..32";
        }
        description
          "Indicates the physical port name.";
      }
    }
  }
  augment "/ncs:devices/ncs:device/ncs:netconf-notifications/ncs:received-notifications/ncs:notification/ncs:data" {
    container unequipped-hp-resume {
      presence "";
      config false;
      description
        "This object indicates that a clear alarm is generated when the higher order path (HP) is equipped.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container unequipped-hp {
      presence "";
      config false;
      description
        "This object indicates that an alarm is generated when the higher order path (HP) is unequipped.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container trace-mismatch-hp-resume {
      presence "";
      config false;
      description
        "This object indicates that a clear alarm is generated when the higher order path (HP) trace identifier becomes stable.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container trace-mismatch-hp {
      presence "";
      config false;
      description
        "This object indicates that an alarm is generated when the higher order path (HP) trace identifier is unstable.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container prefec-tca-resume {
      presence "";
      config false;
      description
        "This object indicates that a clear is generated for forward error correction (FEC) bit errors threshold-crossing.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container pre-fec-tca {
      presence "";
      config false;
      description
        "This object indicates that an alarm is generated for forward error correction (FEC) bit errors threshold-crossing.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container remote-defect-hp-resume {
      presence "";
      config false;
      description
        "This object indicates the higher order path (HP) Remote Default Indication (HPRDI) alarm is cleared.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container remote-defect-hp {
      presence "";
      config false;
      description
        "This object indicates the higher order path (HP) Remote Default Indication (HPRDI) alarm.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container payload-mismatch-hp-resume {
      presence "";
      config false;
      description
        "This object indicates that the higher order path (HP) signal identifier mismatch is rectified.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container payload-mismatch-hp {
      presence "";
      config false;
      description
        "This object indicates the higher order path (HP) signal identifier mismatch.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container port-type-change {
      presence "";
      config false;
      description
        "The mode of combo port is changed.";
      leaf physical-port-index {
        type uint32;
        description
          "Indicates the physical port index.";
      }
      leaf port-name {
        type string {
          length "1..32";
        }
        description
          "Indicates the physical port name.";
      }
      leaf physical-port-mode {
        type uint32;
        description
          "The current state of port type in port.";
      }
    }
  }
  augment "/ncs:devices/ncs:device/ncs:netconf-notifications/ncs:received-notifications/ncs:notification/ncs:data" {
    container traffic-fall-receive-resume {
      presence "";
      config false;
      description
        "Traffic fall clear alarm in the receive direction of an Ethernet interface.";
      leaf physical-port-index {
        type uint32;
        description
          "Indicates the physical port index.";
      }
    }
  }
  augment "/ncs:devices/ncs:device/ncs:netconf-notifications/ncs:received-notifications/ncs:notification/ncs:data" {
    container traffic-fall-receive {
      presence "";
      config false;
      description
        "Traffic fall alarm in the receive direction of an Ethernet interface.";
      leaf physical-port-index {
        type uint32;
        description
          "Indicates the physical port index.";
      }
    }
  }
  augment "/ncs:devices/ncs:device/ncs:netconf-notifications/ncs:received-notifications/ncs:notification/ncs:data" {
    container physical-rate-degrade-resume {
      presence "";
      config false;
      description
        "This object indicates that a clear alarm is generated when the negotiation rate on an electrical interface falls sharply.";
      leaf physical-port-index {
        type uint32;
        description
          "Indicates the physical port index.";
      }
    }
  }
  augment "/ncs:devices/ncs:device/ncs:netconf-notifications/ncs:received-notifications/ncs:notification/ncs:data" {
    container physical-rate-degrade {
      presence "";
      config false;
      description
        "This object indicates that an alarm is generated when the negotiation rate on an electrical interface falls sharply.";
      leaf physical-port-index {
        type uint32;
        description
          "Indicates the physical port index.";
      }
    }
  }
  augment "/ncs:devices/ncs:device/ncs:netconf-notifications/ncs:received-notifications/ncs:notification/ncs:data" {
    container port-physical-up {
      presence "";
      config false;
      description
        "One of the port physical connect up.";
      leaf base-trap-severity {
        type uint32;
        description
          "To describe the level of trap.";
      }
      leaf base-trap-probable-cause {
        type uint32;
        description
          "To describe the probable cause of trap.";
      }
      leaf base-trap-event-type {
        type uint32;
        description
          "To describe the type of trap.";
      }
      leaf port-name {
        type string {
          length "1..32";
        }
        description
          "Entity physical name.";
      }
    }
  }
  augment "/ncs:devices/ncs:device/ncs:netconf-notifications/ncs:received-notifications/ncs:notification/ncs:data" {
    container port-physical-down {
      presence "";
      config false;
      description
        "One of the port physical connect down.";
      leaf base-trap-severity {
        type uint32;
        description
          "To describe the level of trap.";
      }
      leaf base-trap-probable-cause {
        type uint32;
        description
          "To describe the probable cause of trap.";
      }
      leaf base-trap-event-type {
        type uint32;
        description
          "To describe the type of trap.";
      }
      leaf port-name {
        type string {
          length "1..32";
        }
        description
          "Entity physical name.";
      }
      leaf port-physical-down-reason {
        type string {
          length "1..32";
        }
        description
          "Port physical down reason.";
      }
    }
  }
  augment "/ncs:devices/ncs:device/ncs:netconf-notifications/ncs:received-notifications/ncs:notification/ncs:data" {
    container port-mode-change {
      presence "";
      config false;
      description
        "This object indicates that the port rate type is changed.";
      leaf physical-port-index {
        type uint32;
        description
          "Indicates the physical port index.";
      }
      leaf port-name {
        type string {
          length "1..32";
        }
        description
          "Indicates the physical port name.";
      }
      leaf physical-port-mode {
        type uint32;
        description
          "The current state of port type in port.";
      }
    }
  }
  augment "/ncs:devices/ncs:device/ncs:netconf-notifications/ncs:received-notifications/ncs:notification/ncs:data" {
    container trans-mode-inconsistent-resume {
      presence "";
      config false;
      description
        "The transmission modes of the group of interfaces are consistent now.";
      leaf card-id {
        type uint32;
        description
          "Indicates the card ID.";
      }
      leaf physical-port-groupid {
        type string {
          length "1..32";
        }
        description
          "Indicates the physical port group id.";
      }
      leaf port-trans-mode-reason {
        type string {
          length "1..32";
        }
        description
          "Indicates the physical port transmission mode different reason.";
      }
      leaf slot-id {
        type uint32;
        description
          "Indicates the slot ID.";
      }
    }
  }
  augment "/ncs:devices/ncs:device/ncs:netconf-notifications/ncs:received-notifications/ncs:notification/ncs:data" {
    container trans-mode-inconsistent {
      presence "";
      config false;
      description
        "The transmission modes of the group of interfaces are inconsistent.";
      leaf card-id {
        type uint32;
        description
          "Indicates the card ID.";
      }
      leaf physical-port-groupid {
        type string {
          length "1..32";
        }
        description
          "Indicates the physical port group id.";
      }
      leaf port-trans-mode-reason {
        type string {
          length "1..32";
        }
        description
          "Indicates the physical port transmission mode different reason.";
      }
      leaf slot-id {
        type uint32;
        description
          "Indicates the slot ID.";
      }
    }
  }
  augment "/ncs:devices/ncs:device/ncs:netconf-notifications/ncs:received-notifications/ncs:notification/ncs:data" {
    container path-trace-mismatch-resume {
      presence "";
      config false;
      description
        "This object indicates that a clear alarm is generated when path trace identifiers between the local and remote ends match.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container path-trace-mismatch {
      presence "";
      config false;
      description
        "This object indicates that an alarm is generated when path trace identifiers between the local and remote ends mismatch.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container crc-mac-fcs-sd-resume {
      presence "";
      config false;
      description
        "This object indicates that a clear alarm when port FCS signal degrade at the MAC layer.";
      leaf physical-port-index {
        type uint32;
        description
          "This object indicates the index of a physical port.";
      }
      leaf port-name {
        type string {
          length "1..64";
        }
        description
          "This object indicates the name of a physical port.";
      }
      leaf current-crc-packet-error-ratio {
        type string {
          length "1..32";
        }
        description
          "This object indicates that the thresholds for CRC error packet ratio alarms on a physical port are sent to the NMS in the character string format.";
      }
      leaf physical-port-crc-sd-alarm-threshold {
        type string {
          length "1..32";
        }
        description
          "The alarm threshold of MAC_FCS_SD.";
      }
      leaf physical-port-crc-sd-resume-threshold {
        type string {
          length "1..32";
        }
        description
          "The resume threshold of MAC_FCS_SD.";
      }
    }
  }
  augment "/ncs:devices/ncs:device/ncs:netconf-notifications/ncs:received-notifications/ncs:notification/ncs:data" {
    container crc-mac-fcs-sd {
      presence "";
      config false;
      description
        "This object indicates that an alarm when port FCS signal degrade at the MAC layer.";
      leaf physical-port-index {
        type uint32;
        description
          "This object indicates the index of a physical port.";
      }
      leaf port-name {
        type string {
          length "1..64";
        }
        description
          "This object indicates the name of a physical port.";
      }
      leaf current-crc-packet-error-ratio {
        type string {
          length "1..32";
        }
        description
          "This object indicates that the thresholds for CRC error packet ratio alarms on a physical port are sent to the NMS in the character string format.";
      }
      leaf physical-port-crc-sd-alarm-threshold {
        type string {
          length "1..32";
        }
        description
          "The alarm threshold of MAC_FCS_SD.";
      }
      leaf physical-port-crc-sd-resume-threshold {
        type string {
          length "1..32";
        }
        description
          "The resume threshold of MAC_FCS_SD.";
      }
    }
  }
  augment "/ncs:devices/ncs:device/ncs:netconf-notifications/ncs:received-notifications/ncs:notification/ncs:data" {
    container crc-error-warning-resume {
      presence "";
      config false;
      description
        "This object indicates that a clear alarm is generated when the number of CRC errors on a physical port falls below the lower threshold. The host sends a trap message to the NMS.";
      leaf physical-port-index {
        type uint32;
        description
          "This object indicates the index of a physical port.";
      }
      leaf port-name {
        type string {
          length "1..64";
        }
        description
          "This object indicates the name of a physical port.";
      }
      leaf current-crc-packet-error-ratio {
        type string {
          length "1..32";
        }
        description
          "This object indicates that the thresholds for CRC error packet ratio alarms on a physical port are sent to the NMS in the character string format.";
      }
      leaf physical-port-crc-per-warning-threshold {
        type string {
          length "1..32";
        }
        description
          "The warning threshold of CRC-PER (Packet Error Ratio).";
      }
      leaf physical-port-crc-per-warning-resume-threshold {
        type string {
          length "1..32";
        }
        description
          "The warning resume threshold of CRC-PER (Packet Error Ratio).";
      }
    }
  }
  augment "/ncs:devices/ncs:device/ncs:netconf-notifications/ncs:received-notifications/ncs:notification/ncs:data" {
    container crc-error-warning {
      presence "";
      config false;
      description
        "This object indicates that an alarm is generated when the number of CRC errors on a physical port exceeds the lower threshold. The host sends a trap message to the NMS.";
      leaf physical-port-index {
        type uint32;
        description
          "This object indicates the index of a physical port.";
      }
      leaf port-name {
        type string {
          length "1..64";
        }
        description
          "This object indicates the name of a physical port.";
      }
      leaf current-crc-packet-error-ratio {
        type string {
          length "1..32";
        }
        description
          "This object indicates that the thresholds for CRC error packet ratio alarms on a physical port are sent to the NMS in the character string format.";
      }
      leaf crc-per-warning-threshold {
        type string {
          length "1..32";
        }
        description
          "The warning threshold of CRC-PER (Packet Error Ratio).";
      }
      leaf physical-port-crc-per-warning-resume-threshold {
        type string {
          length "1..32";
        }
        description
          "The warning resume threshold of CRC-PER (Packet Error Ratio).";
      }
    }
  }
  augment "/ncs:devices/ncs:device/ncs:netconf-notifications/ncs:received-notifications/ncs:notification/ncs:data" {
    container crc-packet-error-ratio-resume {
      presence "";
      config false;
      description
        "This object indicates that a clear alarm is generated when the number of CRC errors on a physical port falls below the upper threshold. The host sends a trap message to the NMS.";
      leaf physical-port-index {
        type uint32;
        description
          "This object indicates the index of a physical port.";
      }
      leaf port-name {
        type string {
          length "1..64";
        }
        description
          "This object indicates the name of a physical port.";
      }
      leaf current-crc-packet-error-ratio {
        type string {
          length "1..32";
        }
        description
          "This object indicates that the thresholds for CRC error packet ratio alarms on a physical port are sent to the NMS in the character string format.";
      }
      leaf alarm-threshold {
        type string {
          length "1..32";
        }
        description
          "This object indicates that the generation threshold for the CRC error packet ratio alarm on a physical port is sent to the NMS in the character string format.";
      }
      leaf resume-threshold {
        type string {
          length "1..32";
        }
        description
          "This object indicates that the clearing threshold for the CRC error packet ratio clear alarm on a physical port is sent to the NMS in the character string format.";
      }
    }
  }
  augment "/ncs:devices/ncs:device/ncs:netconf-notifications/ncs:received-notifications/ncs:notification/ncs:data" {
    container crc-packet-error-ratio {
      presence "";
      config false;
      description
        "This object indicates that an alarm is generated when the number of CRC errors on a physical port exceeds the upper threshold. The host sends a trap message to the NMS.";
      leaf physical-port-index {
        type uint32;
        description
          "This object indicates the index of a physical port.";
      }
      leaf port-name {
        type string {
          length "1..64";
        }
        description
          "This object indicates the name of a physical port.";
      }
      leaf current-crc-packet-error-ratio {
        type string {
          length "1..32";
        }
        description
          "This object indicates that the thresholds for CRC error packet ratio alarms on a physical port are sent to the NMS in the character string format.";
      }
      leaf alarm-threshold {
        type string {
          length "1..32";
        }
        description
          "This object indicates that the generation threshold for the CRC error packet ratio alarm on a physical port is sent to the NMS in the character string format.";
      }
      leaf resume-threshold {
        type string {
          length "1..32";
        }
        description
          "This object indicates that the clearing threshold for the CRC error packet ratio clear alarm on a physical port is sent to the NMS in the character string format.";
      }
    }
  }
  augment "/ncs:devices/ncs:device/ncs:netconf-notifications/ncs:received-notifications/ncs:notification/ncs:data" {
    container crc-fcs-exceed-resume {
      presence "";
      config false;
      description
        "Port MAC_FCS_EXC alarm resume.";
      leaf physical-port-index {
        type uint32;
        description
          "This object indicates the index of a physical port.";
      }
      leaf port-name {
        type string {
          length "1..64";
        }
        description
          "This object indicates the name of a physical port.";
      }
      leaf current-crc-packet-error-ratio {
        type string {
          length "1..32";
        }
        description
          "This object indicates that the thresholds for CRC error packet ratio alarms on a physical port are sent to the NMS in the character string format.";
      }
      leaf physical-port-crc-exc-alarm-threshold {
        type string {
          length "1..32";
        }
        description
          "The alarm threshold of MAC_FCS_EXC.";
      }
      leaf physical-port-crc-exc-resume-threshold {
        type string {
          length "1..32";
        }
        description
          "The resume threshold of MAC_FCS_EXC.";
      }
    }
  }
  augment "/ncs:devices/ncs:device/ncs:netconf-notifications/ncs:received-notifications/ncs:notification/ncs:data" {
    container crc-fcs-exceed {
      presence "";
      config false;
      description
        "Port MAC FCS EXC alarm.";
      leaf physical-port-index {
        type uint32;
        description
          "This object indicates the index of a physical port.";
      }
      leaf port-name {
        type string {
          length "1..64";
        }
        description
          "This object indicates the name of a physical port.";
      }
      leaf current-crc-packet-error-ratio {
        type string {
          length "1..32";
        }
        description
          "This object indicates that the thresholds for CRC error packet ratio alarms on a physical port are sent to the NMS in the character string format.";
      }
      leaf physical-port-crc-exc-alarm-threshold {
        type string {
          length "1..32";
        }
        description
          "The alarm threshold of MAC_FCS_EXC.";
      }
      leaf physical-port-crc-exc-resume-threshold {
        type string {
          length "1..32";
        }
        description
          "The resume threshold of MAC_FCS_EXC.";
      }
    }
  }
  augment "/ncs:devices/ncs:device/ncs:netconf-notifications/ncs:received-notifications/ncs:notification/ncs:data" {
    container crc-error-exceed-resume {
      presence "";
      config false;
      description
        "Port CRC error alarm resume.";
      leaf physical-port-index {
        type uint32;
        description
          "This object indicates the index of a physical port.";
      }
      leaf port-name {
        type string {
          length "1..64";
        }
        description
          "This object indicates the name of a physical port.";
      }
      leaf physical-port-crc-error-statistics {
        type uint64;
        description
          "This object indicates the CRC error statistics.";
      }
      leaf physical-port-crc-error-high-threshold {
        type uint32;
        description
          "This object indicates the upper threshold for the number of CRC errors. The default value is 1000 pps.";
      }
      leaf physical-port-crc-error-low-threshold {
        type uint32;
        description
          "This object indicates the lower threshold for the number of CRC errors. The default value is 100 pps.";
      }
      leaf physical-port-crc-error-interval {
        type uint32;
        description
          "This object indicates the time threshold for the CRC error alarm. The default value is 10s.";
      }
    }
  }
  augment "/ncs:devices/ncs:device/ncs:netconf-notifications/ncs:received-notifications/ncs:notification/ncs:data" {
    container crc-error-exceed {
      presence "";
      config false;
      description
        "Port CRC error alarm.";
      leaf physical-port-index {
        type uint32;
        description
          "This object indicates the index of a physical port.";
      }
      leaf port-name {
        type string {
          length "1..64";
        }
        description
          "This object indicates the name of a physical port.";
      }
      leaf physical-port-crc-error-statistics {
        type uint64;
        description
          "This object indicates the CRC error statistics.";
      }
      leaf physical-port-crc-error-high-threshold {
        type uint32;
        description
          "This object indicates the upper threshold for the number of CRC errors. The default value is 1000 pps.";
      }
      leaf physical-port-crc-error-low-threshold {
        type uint32;
        description
          "This object indicates the lower threshold for the number of CRC errors. The default value is 100 pps.";
      }
      leaf physical-port-crc-error-interval {
        type uint32;
        description
          "This object indicates the time threshold for the CRC error alarm. The default value is 10s.";
      }
    }
  }
  augment "/ncs:devices/ncs:device/ncs:netconf-notifications/ncs:received-notifications/ncs:notification/ncs:data" {
    container bip8-sd-error-resume {
      presence "";
      config false;
      description
        "This object indicates that the Output error alarm is cleared.";
      leaf physical-port-index {
        type uint32;
        description
          "This object indicates the index of a physical port.";
      }
      leaf port-name {
        type string {
          length "1..64";
        }
        description
          "This object indicates the name of a physical port.";
      }
      leaf physical-port-bip8-sd-error-threshold {
        type uint32;
        description
          "This object indicates the BIP8 SD alarm threshold. The default value is 6.";
      }
    }
  }
  augment "/ncs:devices/ncs:device/ncs:netconf-notifications/ncs:received-notifications/ncs:notification/ncs:data" {
    container bip8-sd-error {
      presence "";
      config false;
      description
        "This object indicates the output error alarm.";
      leaf physical-port-index {
        type uint32;
        description
          "This object indicates the index of a physical port.";
      }
      leaf port-name {
        type string {
          length "1..64";
        }
        description
          "This object indicates the name of a physical port.";
      }
      leaf physical-port-bip8-sd-error-threshold {
        type uint32;
        description
          "This object indicates the BIP8 SD alarm threshold. The default value is 6.";
      }
    }
  }
  augment "/ncs:devices/ncs:device/ncs:netconf-notifications/ncs:received-notifications/ncs:notification/ncs:data" {
    container signal-lp-resume {
      presence "";
      config false;
      description
        "This object indicates that a low path alarm indication signal is detected.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
      leaf hp-id {
        type uint32;
        description
          "Indicates the higher order path ID.";
      }
    }
  }
  augment "/ncs:devices/ncs:device/ncs:netconf-notifications/ncs:received-notifications/ncs:notification/ncs:data" {
    container signal-lp {
      presence "";
      config false;
      description
        "This object indicates that a low path alarm indication signal is detected.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
      leaf hp-id {
        type uint32;
        description
          "Indicates the higher order path ID.";
      }
    }
  }
  augment "/ncs:devices/ncs:device/ncs:netconf-notifications/ncs:received-notifications/ncs:notification/ncs:data" {
    container output-error-exceed-resume {
      presence "";
      config false;
      description
        "This object indicates that a clear alarm is generated when the number of output errors on an interface falls below the upper threshold.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container output-error-exceed {
      presence "";
      config false;
      description
        "This object indicates that an alarm is generated when the number of output errors on an interface exceeds the upper threshold.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container otu-signal-fail-resume {
      presence "";
      config false;
      description
        "This object indicates that the alarm for the OTU signal degrade is cleared.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container otu-signal-fail {
      presence "";
      config false;
      description
        "This object indicates that an alarm is generated for the OTU signal failure.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container otu-signal-degrade-resume {
      presence "";
      config false;
      description
        "This object indicates that the alarm for the OTU signal degrade is cleared.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container otu-signal-degrade {
      presence "";
      config false;
      description
        "This object indicates that an alarm is generated for the OTU signal degrade.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container otu-loss-of-multiframe-resume {
      presence "";
      config false;
      description
        "This object indicates that the OTU indication signal alarm is cleared.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container otu-loss-of-multiframe {
      presence "";
      config false;
      description
        "This object indicates the OTU indication signal alarm.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container otu-indication-signal-resume {
      presence "";
      config false;
      description
        "This object indicates that the OTU indication signal alarm is cleared.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container otu-indication-signal {
      presence "";
      config false;
      description
        "This object indicates the OTU indication signal alarm.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container optical-not-authorized-resume {
      presence "";
      config false;
      description
        "This object indicates that an alarm is generated when the inserted optical module is one not authenticated by Huawei.";
      leaf physical-port-index {
        type uint32;
        description
          "This object indicates the index of a physical port.";
      }
      leaf port-name {
        type string {
          length "1..32";
        }
        description
          "This object indicates the name of a physical port.";
      }
    }
  }
  augment "/ncs:devices/ncs:device/ncs:netconf-notifications/ncs:received-notifications/ncs:notification/ncs:data" {
    container optical-not-authorized {
      presence "";
      config false;
      description
        "This object indicates that an alarm is generated when the inserted optical module is one not authenticated by Huawei.";
      leaf physical-port-index {
        type uint32;
        description
          "This object indicates the index of a physical port.";
      }
      leaf port-name {
        type string {
          length "1..32";
        }
        description
          "This object indicates the name of a physical port.";
      }
    }
  }
  augment "/ncs:devices/ncs:device/ncs:netconf-notifications/ncs:received-notifications/ncs:notification/ncs:data" {
    container optical-fail-resume {
      presence "";
      config false;
      description
        "Optical Module resume from failure.";
      leaf entity-physical-index {
        type uint32;
        description
          "The index of physical.";
      }
      leaf port-name {
        type string {
          length "1..32";
        }
        description
          "Entity physical name.";
      }
      leaf fault-code {
        type devm:ncs_rpc_notif_notification-probable-cause-type;
        description
          "To describe the fault id of trap.";
      }
      leaf reason {
        type string {
          length "1..32";
        }
        description
          "Description of trap reason.";
      }
    }
  }
  augment "/ncs:devices/ncs:device/ncs:netconf-notifications/ncs:received-notifications/ncs:notification/ncs:data" {
    container optical-fail {
      presence "";
      config false;
      description
        "Optical Module become failure for some reason.";
      leaf entity-physical-index {
        type uint32;
        description
          "The index of physical.";
      }
      leaf port-name {
        type string {
          length "1..32";
        }
        description
          "Entity physical name.";
      }
      leaf fault-code {
        type devm:ncs_rpc_notif_notification-probable-cause-type;
        description
          "To describe the fault id of trap.";
      }
      leaf reason {
        type string {
          length "1..32";
        }
        description
          "Description of trap reason.";
      }
    }
  }
  augment "/ncs:devices/ncs:device/ncs:netconf-notifications/ncs:received-notifications/ncs:notification/ncs:data" {
    container optical-not-match-resume {
      presence "";
      config false;
      description
        "After the optical module was inserted, its configuration was not supported. The partial function of optical module failed.";
      leaf entity-physical-index {
        type uint32;
        description
          "The index of physical.";
      }
      leaf port-name {
        type string {
          length "1..32";
        }
        description
          "Entity physical name.";
      }
      leaf fault-code {
        type devm:ncs_rpc_notif_notification-probable-cause-type;
        description
          "To describe the fault id of trap.";
      }
      leaf reason {
        type string {
          length "1..32";
        }
        description
          "Description of trap reason.";
      }
    }
  }
  augment "/ncs:devices/ncs:device/ncs:netconf-notifications/ncs:received-notifications/ncs:notification/ncs:data" {
    container optical-not-match {
      presence "";
      config false;
      description
        "After the optical module was inserted, its configuration was not supported. The partial function of optical module failed.";
      leaf entity-physical-index {
        type uint32;
        description
          "The index of physical.";
      }
      leaf port-name {
        type string {
          length "1..32";
        }
        description
          "Entity physical name.";
      }
      leaf fault-code {
        type devm:ncs_rpc_notif_notification-probable-cause-type;
        description
          "To describe the fault id of trap.";
      }
      leaf reason {
        type string {
          length "1..32";
        }
        description
          "Description of trap reason.";
      }
    }
  }
  augment "/ncs:devices/ncs:device/ncs:netconf-notifications/ncs:received-notifications/ncs:notification/ncs:data" {
    container out-of-frame-resume {
      presence "";
      config false;
      description
        "This object indicates that the OOF alarm generated at the receive end is cleared.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container out-of-frame {
      presence "";
      config false;
      description
        "This object indicates that an out of frame (OOF) alarm is generated at the receive end.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container odu-signal-degrade-resume {
      presence "";
      config false;
      description
        "This object indicates that the alarm for the ODU signal degrade is cleared.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container odu-signal-degrade {
      presence "";
      config false;
      description
        "This object indicates that an alarm is generated for the ODU signal degrade.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container odu-open-connection-resume {
      presence "";
      config false;
      description
        "This object indicates that the indication defect alarm for the ODU open connection is cleared.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container odu-open-connection {
      presence "";
      config false;
      description
        "This object indicates that the indication defect alarm for the ODU open connection.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container odu-locked-signal-resume {
      presence "";
      config false;
      description
        "This object indicates that the ODU lock defect alarm is cleared.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container odu-locked-signal {
      presence "";
      config false;
      description
        "This object indicates the ODU lock defect alarm.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container odu-indication-signal-resume {
      presence "";
      config false;
      description
        "This object indicates that the ODU indication signal alarm is cleared.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container odu-indication-signal {
      presence "";
      config false;
      description
        "This object indicates the ODU indication signal alarm.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container negotiation-failed-resume {
      presence "";
      config false;
      description
        "Auto-negotiation failure alarm resume.";
      leaf physical-port-index {
        type uint32;
        description
          "Indicates the physical port index.";
      }
      leaf port-name {
        type string {
          length "1..32";
        }
        description
          "Indicates the physical port name.";
      }
    }
  }
  augment "/ncs:devices/ncs:device/ncs:netconf-notifications/ncs:received-notifications/ncs:notification/ncs:data" {
    container negotiation-failed {
      presence "";
      config false;
      description
        "Auto-negotiation failure alarm. Possible causes, including the local auto-negotiation configuration with the peer inconsistencies;
                the local ability is not compatible with the peer;
                the physical connection of the two sides is unstable.
                When the alarm occurs, the port can't be up.";
      leaf physical-port-index {
        type uint32;
        description
          "Indicates the physical port index.";
      }
      leaf port-name {
        type string {
          length "1..32";
        }
        description
          "Indicates the physical port name.";
      }
    }
  }
  augment "/ncs:devices/ncs:device/ncs:netconf-notifications/ncs:received-notifications/ncs:notification/ncs:data" {
    container remote-defect-ms-resume {
      presence "";
      config false;
      description
        "This object indicates that the LRDI alarm generated in the multiplex section (MS) at the remote end is cleared.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container remote-defect-ms {
      presence "";
      config false;
      description
        "This object indicates that a line remote defect indicator (LRDI) alarm is generated in the multiplex section (MS) at the remote end.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container signal-loss-resume {
      presence "";
      config false;
      description
        "This object indicates that the alarm for the interface loopback is cleared.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
      leaf physical-port-alarm-name {
        type string {
          length "1..32";
        }
        description
          "Indicates the physical port alarm name.";
      }
    }
  }
  augment "/ncs:devices/ncs:device/ncs:netconf-notifications/ncs:received-notifications/ncs:notification/ncs:data" {
    container signal-loss {
      presence "";
      config false;
      description
        "This object indicates that an alarm is generated due to signal loss at the receive end.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
      leaf physical-port-alarm-name {
        type string {
          length "1..32";
        }
        description
          "Indicates the physical port alarm name.";
      }
    }
  }
  augment "/ncs:devices/ncs:device/ncs:netconf-notifications/ncs:received-notifications/ncs:notification/ncs:data" {
    container port-loopback-resume {
      presence "";
      config false;
      description
        "This object indicates that the alarm for the interface loopback is cleared.";
      leaf physical-port-index {
        type uint32;
        description
          "Indicates the physical port index.";
      }
      leaf port-name {
        type string {
          length "1..32";
        }
        description
          "Indicates the physical port name.";
      }
      leaf loop-type {
        type ncs_rpc_notif_loop-type;
        description
          "Type of the notification loop. The value can be one -of the following: - 0: stop-loopback - 1: local - 2: remote.";
      }
    }
  }
  augment "/ncs:devices/ncs:device/ncs:netconf-notifications/ncs:received-notifications/ncs:notification/ncs:data" {
    container port-loopback {
      presence "";
      config false;
      description
        "This object indicates that an alarm is generated due to an interface loopback.";
      leaf physical-port-index {
        type uint32;
        description
          "Indicates the physical port index.";
      }
      leaf port-name {
        type string {
          length "1..32";
        }
        description
          "Indicates the physical port name.";
      }
      leaf loop-type {
        type ncs_rpc_notif_loop-type;
        description
          "Type of the notification loop. The value can be one -of the following: - 0: stop-loopback - 1: local - 2: remote.";
      }
    }
  }
  augment "/ncs:devices/ncs:device/ncs:netconf-notifications/ncs:received-notifications/ncs:notification/ncs:data" {
    container multi-loss-lp-resume {
      presence "";
      config false;
      description
        "This object indicates that the LOM on the higher order path (HP) is resolved.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container multi-loss-lp {
      presence "";
      config false;
      description
        "This object indicates the loss of multiframe (LOM) on the higher order path (HP).";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container local-fault-resume {
      presence "";
      config false;
      description
        "This object indicates that a clear alarm is generated when the receive link from the remote device to the local device recovers.";
      leaf physical-port-index {
        type uint32;
        description
          "Indicates the physical port index.";
      }
      leaf port-name {
        type string {
          length "1..32";
        }
        description
          "Indicates the physical port name.";
      }
    }
  }
  augment "/ncs:devices/ncs:device/ncs:netconf-notifications/ncs:received-notifications/ncs:notification/ncs:data" {
    container local-fault {
      presence "";
      config false;
      description
        "This object indicates that an alarm is generated when the receive link from the remote device to the local device fails.";
      leaf physical-port-index {
        type uint32;
        description
          "Indicates the physical port index.";
      }
      leaf port-name {
        type string {
          length "1..32";
        }
        description
          "Indicates the physical port name.";
      }
    }
  }
  augment "/ncs:devices/ncs:device/ncs:netconf-notifications/ncs:received-notifications/ncs:notification/ncs:data" {
    container license-resource-lack-resume {
      presence "";
      config false;
      description
        "The maximum number-exceed alarm was cleared.";
      leaf license-type {
        type string {
          length "1..32";
        }
        description
          "Indicates the type of interface function-controlled license.";
      }
      leaf max-port-num {
        type uint32;
        description
          "Indicates the maximum number of available interfaces.";
      }
      leaf used-port-num {
        type uint32;
        description
          "Indicates the number of interfaces in use.";
      }
    }
  }
  augment "/ncs:devices/ncs:device/ncs:netconf-notifications/ncs:received-notifications/ncs:notification/ncs:data" {
    container license-resource-lack {
      presence "";
      config false;
      description
        "Interfaces of this type in use exceeded the maximum number.";
      leaf license-type {
        type string {
          length "1..32";
        }
        description
          "Indicates the type of interface function-controlled license.";
      }
      leaf max-port-num {
        type uint32;
        description
          "Indicates the maximum number of available interfaces.";
      }
      leaf used-port-num {
        type uint32;
        description
          "Indicates the Number of interfaces in use.";
      }
    }
  }
  augment "/ncs:devices/ncs:device/ncs:netconf-notifications/ncs:received-notifications/ncs:notification/ncs:data" {
    container laser-shut-resume {
      presence "";
      config false;
      description
        "This object indicates that a clear alarm is generated when the optical laser on a board is opened.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container laser-shut {
      presence "";
      config false;
      description
        "This object indicates that an alarm is generated when the optical laser on a board is shut down.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container laser-no-fited-resume {
      presence "";
      config false;
      description
        "The laser not installed alarm resumed.";
      leaf entity-physical-index {
        type uint32;
        description
          "The index of physical.";
      }
      leaf port-name {
        type string {
          length "1..32";
        }
        description
          "Entity physical name.";
      }
    }
  }
  augment "/ncs:devices/ncs:device/ncs:netconf-notifications/ncs:received-notifications/ncs:notification/ncs:data" {
    container laser-no-fited {
      presence "";
      config false;
      description
        "The laser not installed alarm occured.";
      leaf entity-physical-index {
        type uint32;
        description
          "The index of physical.";
      }
      leaf port-name {
        type string {
          length "1..32";
        }
        description
          "Entity physical name.";
      }
    }
  }
  augment "/ncs:devices/ncs:device/ncs:netconf-notifications/ncs:received-notifications/ncs:notification/ncs:data" {
    container laser-auto-shut-resume {
      presence "";
      config false;
      description
        "This object indicates that the alarm for the automatic shutdown of the optical laser is cleared.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container laser-auto-shut {
      presence "";
      config false;
      description
        "This object indicates that an alarm is generated when the optical laser is shut down automatically.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container multi-section-resume {
      presence "";
      config false;
      description
        "This object indicates that the indication signal alarm in the MS is cleared.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container multi-section {
      presence "";
      config false;
      description
        "This object indicates the indication signal alarm in the MS.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container input-error-exceed-resume {
      presence "";
      config false;
      description
        "This object indicates that a clear alarm is generated when the number of input errors on an interface falls below the upper threshold.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container input-error-exceed {
      presence "";
      config false;
      description
        "This object indicates that an alarm is generated when the number of input errors on an interface exceeds the upper threshold.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container tx-pause-frame-exceed-resume {
      presence "";
      config false;
      description
        "The threshold exceed alert of TX PAUSE disappears.";
      leaf tx-pause-frame-statistics {
        type uint64;
        description
          "TX pause frame statistics value.";
      }
      leaf tx-pause-frame-high-threshold {
        type uint32;
        description
          "TX pause frame high threshold, and 0 is an invalid value.";
      }
      leaf tx-pause-frame-low-threshold {
        type uint32;
        description
          "TX pause frame low threshold, and 0 is an invalid value.";
      }
      leaf tx-pause-frame-interval {
        type uint32;
        description
          "TX pause frame alarm interval time (unit is second), and 0 is an invalid value.";
      }
      leaf port-name {
        type string {
          length "1..32";
        }
        description
          "Port name of alarm monitor table.";
      }
    }
  }
  augment "/ncs:devices/ncs:device/ncs:netconf-notifications/ncs:received-notifications/ncs:notification/ncs:data" {
    container tx-pause-frame-exceed {
      presence "";
      config false;
      description
        "The threshold exceed alert of TX PAUSE appears.";
      leaf tx-pause-frame-statistics {
        type uint64;
        description
          "TX pause frame statistics value.";
      }
      leaf tx-pause-frame-high-threshold {
        type uint32;
        description
          "TX pause frame high threshold, and 0 is an invalid value.";
      }
      leaf tx-pause-frame-low-threshold {
        type uint32;
        description
          "TX pause frame low threshold, and 0 is an invalid value.";
      }
      leaf tx-pause-frame-interval {
        type uint32;
        description
          "TX pause frame alarm interval time (unit is second), and 0 is an invalid value.";
      }
      leaf port-name {
        type string {
          length "1..32";
        }
        description
          "Port name of alarm monitor table.";
      }
    }
  }
  augment "/ncs:devices/ncs:device/ncs:netconf-notifications/ncs:received-notifications/ncs:notification/ncs:data" {
    container symbol-error-interval-resume {
      presence "";
      config false;
      description
        "CRC error alarm resume.";
      leaf symbol-error-statistics {
        type uint64;
        description
          "Symbol error statistics value.";
      }
      leaf symbol-error-threshold {
        type uint32;
        description
          "Symbol error alarm threshold,default value is 3.";
      }
      leaf symbol-error-interval {
        type uint32;
        description
          "Symbol error alarm interval time (unit is second), default value is 10s.";
      }
      leaf port-name {
        type string {
          length "1..32";
        }
        description
          "Port name of alarm monitor table.";
      }
    }
  }
  augment "/ncs:devices/ncs:device/ncs:netconf-notifications/ncs:received-notifications/ncs:notification/ncs:data" {
    container symbol-error-interval {
      presence "";
      config false;
      description
        "Symbol error alarm.";
      leaf symbol-error-statistics {
        type uint64;
        description
          "Symbol error statistics value.";
      }
      leaf symbol-error-threshold {
        type uint32;
        description
          "Symbol error alarm threshold,default value is 3.";
      }
      leaf symbol-error-interval {
        type uint32;
        description
          "Symbol error alarm interval time (unit is second), default value is 10s.";
      }
      leaf port-name {
        type string {
          length "1..32";
        }
        description
          "Port name of alarm monitor table.";
      }
    }
  }
  augment "/ncs:devices/ncs:device/ncs:netconf-notifications/ncs:received-notifications/ncs:notification/ncs:data" {
    container sdh-error-resume {
      presence "";
      config false;
      description
        "Sdh error alarm resume only for B3.";
      leaf sdh-error-statistics {
        type uint64;
        description
          "Sdh error statistics value only for B3.";
      }
      leaf sdh-error-threshold {
        type uint32;
        description
          "Sdh error alarm threshold,only for B3, default value is 3 and 0 is an invalid value.";
      }
      leaf sdh-error-interval {
        type uint32;
        description
          "Sdh error alarm interval time (unit is second),only for B3, default value is 10s and 0 is an invalid value.";
      }
      leaf port-name {
        type string {
          length "1..32";
        }
        description
          "Port name of alarm monitor table.";
      }
    }
  }
  augment "/ncs:devices/ncs:device/ncs:netconf-notifications/ncs:received-notifications/ncs:notification/ncs:data" {
    container sdh-error-rising {
      presence "";
      config false;
      description
        "Sdh error alarm only for B3.";
      leaf sdh-error-statistics {
        type uint64;
        description
          "Sdh error statistics value only for B3.";
      }
      leaf sdh-error-threshold {
        type uint32;
        description
          "Sdh error alarm threshold,only for B3,default value is 3 and 0 is an invalid value.";
      }
      leaf sdh-error-interval {
        type uint32;
        description
          "Sdh error alarm interval time (unit is second), only for B3,default value is 10s and 0 is an invalid value.";
      }
      leaf port-name {
        type string {
          length "1..32";
        }
        description
          "Port name of alarm monitor table.";
      }
    }
  }
  augment "/ncs:devices/ncs:device/ncs:netconf-notifications/ncs:received-notifications/ncs:notification/ncs:data" {
    container sdh-b2-error-resume {
      presence "";
      config false;
      description
        "Sdh B2 error alarm resume.";
      leaf sdh-b2-error-statistics {
        type uint64;
        description
          "Sdh B2 error statistics value.";
      }
      leaf sdh-b2-error-threshold {
        type uint32;
        description
          "Sdh error B2 alarm threshold,default value is 3.";
      }
      leaf sdh-b2-error-interval {
        type uint32;
        description
          "Sdh B2 error alarm interval time (unit is second),default value is 10s.";
      }
      leaf port-name {
        type string {
          length "1..32";
        }
        description
          "Port name of alarm monitor table.";
      }
    }
  }
  augment "/ncs:devices/ncs:device/ncs:netconf-notifications/ncs:received-notifications/ncs:notification/ncs:data" {
    container sdh-b2-error-rising {
      presence "";
      config false;
      description
        "Sdh B2 error alarm.";
      leaf sdh-b2-error-statistics {
        type uint64;
        description
          "Sdh B2 error statistics value.";
      }
      leaf sdh-b2-error-threshold {
        type uint32;
        description
          "Sdh error B2 alarm threshold,default value is 3.";
      }
      leaf sdh-b2-error-interval {
        type uint32;
        description
          "Sdh B2 error alarm interval time (unit is second),default value is 10s.";
      }
      leaf port-name {
        type string {
          length "1..32";
        }
        description
          "Port name of alarm monitor table.";
      }
    }
  }
  augment "/ncs:devices/ncs:device/ncs:netconf-notifications/ncs:received-notifications/ncs:notification/ncs:data" {
    container post-fec-error-resume {
      presence "";
      config false;
      description
        "The post fec error crooected alarm disappears.";
      leaf post-fec-error-statistics {
        type uint64;
        description
          "Indicates the post-FEC bit error statistics.";
      }
      leaf port-name {
        type string {
          length "1..32";
        }
        description
          "Port name of alarm monitor table.";
      }
    }
  }
  augment "/ncs:devices/ncs:device/ncs:netconf-notifications/ncs:received-notifications/ncs:notification/ncs:data" {
    container post-fec-error-rising {
      presence "";
      config false;
      description
        "The post fec error crooected alarm appears.";
      leaf post-fec-error-statistics {
        type uint64;
        description
          "Indicates the post-FEC bit error statistics.";
      }
      leaf port-name {
        type string {
          length "1..32";
        }
        description
          "Port name of alarm monitor table.";
      }
    }
  }
  augment "/ncs:devices/ncs:device/ncs:netconf-notifications/ncs:received-notifications/ncs:notification/ncs:data" {
    container pause-frame-resume {
      presence "";
      config false;
      description
        "Pause frame alarm resume.";
      leaf pause-frame-statistics {
        type uint64;
        description
          "Pause frame statistics value.";
      }
      leaf pause-frame-threshold {
        type uint32;
        description
          "Pause frame alarm threshold,and 0 is an invalid value.";
      }
      leaf pause-frame-interval {
        type uint32;
        description
          "Pause frame alarm interval time (unit is second),and 0 is an invalid value.";
      }
      leaf port-name {
        type string {
          length "1..32";
        }
        description
          "Port name of alarm monitor table.";
      }
    }
  }
  augment "/ncs:devices/ncs:device/ncs:netconf-notifications/ncs:received-notifications/ncs:notification/ncs:data" {
    container pause-frame-rising {
      presence "";
      config false;
      description
        "Pause frame alarm.";
      leaf pause-frame-statistics {
        type uint64;
        description
          "Pause frame statistics value.";
      }
      leaf pause-frame-threshold {
        type uint32;
        description
          "Pause frame alarm threshold,and 0 is an invalid value.";
      }
      leaf pause-frame-interval {
        type uint32;
        description
          "Pause frame alarm interval time (unit is second),and 0 is an invalid value.";
      }
      leaf port-name {
        type string {
          length "1..32";
        }
        description
          "Port name of alarm monitor table.";
      }
    }
  }
  augment "/ncs:devices/ncs:device/ncs:netconf-notifications/ncs:received-notifications/ncs:notification/ncs:data" {
    container crc-error-resume {
      presence "";
      config false;
      description
        "CRC error alarm resume.";
      leaf crc-error-statistics {
        type uint64;
        description
          "CRC error statistics value.";
      }
      leaf crc-error-threshold {
        type uint32;
        description
          "CRC error alarm threshold, default value is 3 and 0 is an invalid value.";
      }
      leaf crc-error-interval {
        type uint32;
        description
          "CRC error alarm interval time (unit is second), default value is 10s and 0 is an invalid value.";
      }
      leaf port-name {
        type string {
          length "1..32";
        }
        description
          "Port name of alarm monitor table.";
      }
    }
  }
  augment "/ncs:devices/ncs:device/ncs:netconf-notifications/ncs:received-notifications/ncs:notification/ncs:data" {
    container crc-error-rising {
      presence "";
      config false;
      description
        "CRC error alarm.";
      leaf crc-error-statistics {
        type uint64;
        description
          "CRC error statistics value.";
      }
      leaf crc-error-threshold {
        type uint32;
        description
          "CRC error alarm threshold, default value is 3 and 0 is an invalid value.";
      }
      leaf crc-error-interval {
        type uint32;
        description
          "CRC error alarm interval time (unit is second), default value is 10s and 0 is an invalid value.";
      }
      leaf port-name {
        type string {
          length "1..32";
        }
        description
          "Port name of alarm monitor table.";
      }
    }
  }
  augment "/ncs:devices/ncs:device/ncs:netconf-notifications/ncs:received-notifications/ncs:notification/ncs:data" {
    container bad-bytes-error-resume {
      presence "";
      config false;
      description
        "Port monitor bad bytes error resume.";
      leaf bad-bytes-error-statistics {
        type uint64;
        description
          "Port monitor bad bytes error statistics.";
      }
      leaf bad-bytes-error-threshold {
        type uint32;
        description
          "Port monitor bad bytes error threshold.";
      }
      leaf bad-bytes-error-interval {
        type uint32;
        description
          "Port monitor bad bytes error interval.";
      }
      leaf port-name {
        type string {
          length "1..32";
        }
        description
          "Port name of alarm monitor table.";
      }
    }
  }
  augment "/ncs:devices/ncs:device/ncs:netconf-notifications/ncs:received-notifications/ncs:notification/ncs:data" {
    container bad-bytes-error-rising {
      presence "";
      config false;
      description
        "Port monitor bad bytes error rising.";
      leaf bad-bytes-error-statistics {
        type uint64;
        description
          "Port monitor bad bytes error statistics.";
      }
      leaf bad-bytes-error-threshold {
        type uint32;
        description
          "Port monitor bad bytes error threshold.";
      }
      leaf bad-bytes-error-interval {
        type uint32;
        description
          "Port monitor bad bytes error interval.";
      }
      leaf port-name {
        type string {
          length "1..32";
        }
        description
          "Port name of alarm monitor table.";
      }
    }
  }
  augment "/ncs:devices/ncs:device/ncs:netconf-notifications/ncs:received-notifications/ncs:notification/ncs:data" {
    container humidity-abnormal-resume {
      presence "";
      config false;
      description
        "Humidity back to normal level.";
      leaf exception-type {
        type ncs_rpc_notif_exception-type;
        description
          "Type of the notification entity threshold.";
      }
      leaf threshold {
        type uint32;
        description
          "The threshold value of temperature, humidity, fog......";
      }
      leaf current {
        type uint32;
        description
          "The current value that been measured.";
      }
      leaf fault-code {
        type devm:ncs_rpc_notif_notification-probable-cause-type;
        description
          "To describe the fault id of trap.";
      }
    }
  }
  augment "/ncs:devices/ncs:device/ncs:netconf-notifications/ncs:received-notifications/ncs:notification/ncs:data" {
    container humidity-abnormal {
      presence "";
      config false;
      description
        "Humidity rise over or fall below the alarm threshold.";
      leaf exception-type {
        type ncs_rpc_notif_exception-type;
        description
          "Type of the notification entity threshold.";
      }
      leaf threshold {
        type uint32;
        description
          "The threshold value of temperature, humidity, fog......";
      }
      leaf current {
        type uint32;
        description
          "The current value that been measured.";
      }
      leaf fault-code {
        type devm:ncs_rpc_notif_notification-probable-cause-type;
        description
          "To describe the fault id of trap.";
      }
    }
  }
  augment "/ncs:devices/ncs:device/ncs:netconf-notifications/ncs:received-notifications/ncs:notification/ncs:data" {
    container trace-unstable-lp-resume {
      presence "";
      config false;
      description
        "This object indicates that a clear alarm is generated when the higher order path (HP) trace identifier becomes stable.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container trace-unstable-lp {
      presence "";
      config false;
      description
        "This object indicates that an alarm is generated when the higher order path (HP) trace identifier is unstable.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container gps-module-remove {
      presence "";
      config false;
      description
        "The gps module was removed.";
      leaf entity-physical-index {
        type uint32;
        description
          "The index of physical.";
      }
      leaf port-name {
        type string {
          length "1..32";
        }
        description
          "Entity physical name.";
      }
    }
  }
  augment "/ncs:devices/ncs:device/ncs:netconf-notifications/ncs:received-notifications/ncs:notification/ncs:data" {
    container gps-module-insert {
      presence "";
      config false;
      description
        "The gps module was inserted.";
      leaf entity-physical-index {
        type uint32;
        description
          "The index of physical.";
      }
      leaf port-name {
        type string {
          length "1..32";
        }
        description
          "Entity physical name.";
      }
    }
  }
  augment "/ncs:devices/ncs:device/ncs:netconf-notifications/ncs:received-notifications/ncs:notification/ncs:data" {
    container gate-abnormal-resume {
      presence "";
      config false;
      description
        "Gate switch to normal status.";
      leaf exception-type {
        type ncs_rpc_notif_exception-type;
        description
          "Type of the notification entity threshold.";
      }
      leaf threshold {
        type uint32;
        description
          "The threshold value of temperature, humidity, fog......";
      }
      leaf current {
        type uint32;
        description
          "The current value that been measured.";
      }
      leaf fault-code {
        type devm:ncs_rpc_notif_notification-probable-cause-type;
        description
          "To describe the fault id of trap.";
      }
    }
  }
  augment "/ncs:devices/ncs:device/ncs:netconf-notifications/ncs:received-notifications/ncs:notification/ncs:data" {
    container gate-abnormal {
      presence "";
      config false;
      description
        "Gate switch to the alarm status.";
      leaf exception-type {
        type ncs_rpc_notif_exception-type;
        description
          "Type of the notification entity threshold.";
      }
      leaf threshold {
        type uint32;
        description
          "The threshold value of temperature, humidity, fog......";
      }
      leaf current {
        type uint32;
        description
          "The current value that been measured.";
      }
      leaf fault-code {
        type devm:ncs_rpc_notif_notification-probable-cause-type;
        description
          "To describe the fault id of trap.";
      }
    }
  }
  augment "/ncs:devices/ncs:device/ncs:netconf-notifications/ncs:received-notifications/ncs:notification/ncs:data" {
    container fog-abnormal-resume {
      presence "";
      config false;
      description
        "Fog back to normal level.";
      leaf exception-type {
        type ncs_rpc_notif_exception-type;
        description
          "Type of the notification entity threshold.";
      }
      leaf threshold {
        type uint32;
        description
          "The threshold value of temperature, humidity, fog......";
      }
      leaf current {
        type uint32;
        description
          "The current value that been measured.";
      }
      leaf fault-code {
        type devm:ncs_rpc_notif_notification-probable-cause-type;
        description
          "To describe the fault id of trap.";
      }
    }
  }
  augment "/ncs:devices/ncs:device/ncs:netconf-notifications/ncs:received-notifications/ncs:notification/ncs:data" {
    container fog-abnormal {
      presence "";
      config false;
      description
        "Fog rise over alarm threshold.";
      leaf exception-type {
        type ncs_rpc_notif_exception-type;
        description
          "Type of the notification entity threshold.";
      }
      leaf threshold {
        type uint32;
        description
          "The threshold value of temperature, humidity, fog......";
      }
      leaf current {
        type uint32;
        description
          "The current value that been measured.";
      }
      leaf fault-code {
        type devm:ncs_rpc_notif_notification-probable-cause-type;
        description
          "To describe the fault id of trap.";
      }
    }
  }
  augment "/ncs:devices/ncs:device/ncs:netconf-notifications/ncs:received-notifications/ncs:notification/ncs:data" {
    container b3-configured-exceed-resume {
      presence "";
      config false;
      description
        "This object indicates that the number of bit errors on the B3 falls below the configured threshold.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
      leaf hp-id {
        type uint32;
        description
          "Indicates the higher order path ID.";
      }
    }
  }
  augment "/ncs:devices/ncs:device/ncs:netconf-notifications/ncs:received-notifications/ncs:notification/ncs:data" {
    container b3-configured-exceed {
      presence "";
      config false;
      description
        "This object indicates that the number of bit errors on the B3 exceeds the configured threshold.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
      leaf hp-id {
        type uint32;
        description
          "Indicates the higher order path ID.";
      }
    }
  }
  augment "/ncs:devices/ncs:device/ncs:netconf-notifications/ncs:received-notifications/ncs:notification/ncs:data" {
    container b2-configured-exceed-resume {
      presence "";
      config false;
      description
        "This object indicates that the number of error bits for the B2 falls below the configured threshold.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container b2-configured-exceed {
      presence "";
      config false;
      description
        "This object indicates that the number of error bits for the B2 exceeds a configured threshold.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container b1-configured-exceed-resume {
      presence "";
      config false;
      description
        "This object indicates that the number of error bits for the B1 RS falls below the configured threshold.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container b1-configured-exceed {
      presence "";
      config false;
      description
        "This object indicates that the number of error bits for the B1 RS exceeds a configured threshold.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container au-pointer-loss-lp-resume {
      presence "";
      config false;
      description
        "This object indicates the loss of the AU pointer in a higher order path (HP) indication signal alarm is cleard.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container au-pointer-loss-lp {
      presence "";
      config false;
      description
        "This object indicates the loss of the AU pointer in a higher order path (HP) indication signal alarm is generated.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container upstream-pcm-resume {
      presence "";
      config false;
      description
        "Upstream signals recovered.";
      leaf physical-port-index {
        type uint32;
        description
          "Indicates the physical port index.";
      }
      leaf port-name {
        type string {
          length "1..32";
        }
        description
          "Indicates the physical port name.";
      }
    }
  }
  augment "/ncs:devices/ncs:device/ncs:netconf-notifications/ncs:received-notifications/ncs:notification/ncs:data" {
    container upstream-pcm {
      presence "";
      config false;
      description
        "Upstream signals were abnormal.";
      leaf physical-port-index {
        type uint32;
        description
          "Indicates the physical port index.";
      }
      leaf port-name {
        type string {
          length "1..32";
        }
        description
          "Indicates the physical port name.";
      }
    }
  }
  augment "/ncs:devices/ncs:device/ncs:netconf-notifications/ncs:received-notifications/ncs:notification/ncs:data" {
    container resource-dead-line-resume {
      presence "";
      config false;
      description
        "Port authorization grace period alarm resume.";
      leaf gtl-remain-time {
        type uint32;
        units "d";
        description
          "Gtl remain time.";
      }
      leaf physical-index {
        type uint32;
        description
          "Indicates the physical port index.";
      }
      leaf port-name {
        type string {
          length "1..32";
        }
        description
          "Indicates the physical port name.";
      }
    }
  }
  augment "/ncs:devices/ncs:device/ncs:netconf-notifications/ncs:received-notifications/ncs:notification/ncs:data" {
    container resource-dead-line {
      presence "";
      config false;
      description
        "Port authorization grace period alarm.";
      leaf gtl-remain-time {
        type uint32;
        units "d";
        description
          "Gtl remain time.";
      }
      leaf physical-index {
        type uint32;
        description
          "Indicates the physical port index.";
      }
      leaf port-name {
        type string {
          length "1..32";
        }
        description
          "Indicates the physical port name.";
      }
    }
  }
  augment "/ncs:devices/ncs:device/ncs:netconf-notifications/ncs:received-notifications/ncs:notification/ncs:data" {
    container port-license-act-success {
      presence "";
      config false;
      description
        "This object indicates that the license for a physical port is successfully activated.";
      leaf item-name {
        type string {
          length "1..32";
        }
        description
          "Item name.";
      }
      leaf physical-index {
        type uint32;
        description
          "Indicates the physical port index.";
      }
      leaf port-name {
        type string {
          length "1..32";
        }
        description
          "Indicates the physical port name.";
      }
    }
  }
  augment "/ncs:devices/ncs:device/ncs:netconf-notifications/ncs:received-notifications/ncs:notification/ncs:data" {
    container port-license-act-fail {
      presence "";
      config false;
      description
        "This object indicates that the license for a physical port fails to be activated.";
      leaf item-name {
        type string {
          length "1..32";
        }
        description
          "Item name.";
      }
      leaf physical-index {
        type uint32;
        description
          "Indicates the physical port index.";
      }
      leaf port-name {
        type string {
          length "1..32";
        }
        description
          "Indicates the physical port name.";
      }
    }
  }
  augment "/ncs:devices/ncs:device/ncs:netconf-notifications/ncs:received-notifications/ncs:notification/ncs:data" {
    container remote-failure-lp-resume {
      presence "";
      config false;
      description
        "This object indicates that a clear alarm is generated when the lower order path (LP) remote failure indication (RFI) signal is cleared.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf lp-id {
        type uint32;
        description
          "Indicates the low order path ID.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container remote-failure-lp {
      presence "";
      config false;
      description
        "This object indicates that an alarm is generated when a lower order path (LP) remote failure indication (RFI) signal is detected.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf lp-id {
        type uint32;
        description
          "Indicates the low order path ID.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container remote-defect-lp-resume {
      presence "";
      config false;
      description
        "This object indicates that a lower order path (LP) remote defect indication (PRDI) alarm is cleared.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf lp-id {
        type uint32;
        description
          "Indicates the low order path ID.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container remote-defect-lp {
      presence "";
      config false;
      description
        "This object indicates that a lower order path (LP) remote defect indication (PRDI) alarm is generated.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf lp-id {
        type uint32;
        description
          "Indicates the low order path ID.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container loss-au-lp-resume {
      presence "";
      config false;
      description
        "This object indicates that the alarm generated due to the loss of the AU pointer in the lower order path (LP) is cleared.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf lp-id {
        type uint32;
        description
          "Indicates the low order path ID.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container loss-au-lp {
      presence "";
      config false;
      description
        "This object indicates that an alarm is generated when the administrative unit (AU) pointer in the lower order path (LP) is lost.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf lp-id {
        type uint32;
        description
          "Indicates the low order path ID.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container v5-virtual-container-resume {
      presence "";
      config false;
      description
        "This object indicates that the alarm indication signal generated in the virtual container is cleared.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf lp-id {
        type uint32;
        description
          "Indicates the low order path ID.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container v5-virtual-container {
      presence "";
      config false;
      description
        "This object indicates that an alarm indication signal is generated in the virtual container.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf lp-id {
        type uint32;
        description
          "Indicates the low order path ID.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container tributary-unit-lp-resume {
      presence "";
      config false;
      description
        "This object indicates that the lower order path (LP) tributary unit (TU) alarm is cleared.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf lp-id {
        type uint32;
        description
          "Indicates the low order path ID.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container tributary-unit-lp {
      presence "";
      config false;
      description
        "This object indicates the lower order path (LP) tributary unit (TU) alarm indication.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf lp-id {
        type uint32;
        description
          "Indicates the low order path ID.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container out-of-lock-clock-resume {
      presence "";
      config false;
      description
        "This object indicates that a clear alarm is generated when there is a clock on the receive line.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container out-of-lock-clock {
      presence "";
      config false;
      description
        "This object indicates that an alarm is generated when out of lock of received reference clock.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container unequipped-lp-resume {
      presence "";
      config false;
      description
        "This object indicates that a lower order path (LP) unequipped indication signal (PUNEQ) alarm is cleard.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf lp-id {
        type uint32;
        description
          "Indicates the low order path ID.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container unequipped-lp {
      presence "";
      config false;
      description
        "This object indicates that a lower order path (LP) unequipped indication signal (PUNEQ) alarm is generated.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf lp-id {
        type uint32;
        description
          "Indicates the low order path ID.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container trace-mismatch-lp-resume {
      presence "";
      config false;
      description
        "This object indicates that signal label mismatch alarm on VC12 lower order path alarm is cleared.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf lp-id {
        type uint32;
        description
          "Indicates the low order path ID.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container trace-mismatch-lp {
      presence "";
      config false;
      description
        "This object indicates that signal label mismatch alarm on VC12 lower order path alarm.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf lp-id {
        type uint32;
        description
          "Indicates the low order path ID.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container signal-mismatch-lp-resume {
      presence "";
      config false;
      description
        "This object indicates that the lower order path (LP) signal label mismatch alarm is cleared.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf lp-id {
        type uint32;
        description
          "Indicates the low order path ID.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container signal-mismatch-lp {
      presence "";
      config false;
      description
        "This object indicates a lower order path (LP) signal label mismatch alarm.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf lp-id {
        type uint32;
        description
          "Indicates the low order path ID.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container j0-trace-mismatch-resume {
      presence "";
      config false;
      description
        "This object indicates that the alarm for j0 trace identifier mismatch is cleared.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container j0-trace-mismatch {
      presence "";
      config false;
      description
        "This object indicates that an alarm for trace j0 identifier mismatch is generated.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container upstream-e3-resume {
      presence "";
      config false;
      description
        "Indicates the alarm is cleared.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container upstream-e3 {
      presence "";
      config false;
      description
        "Indicates the alarm is detected.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container remote-e3-resume {
      presence "";
      config false;
      description
        "Indicates the alarm is cleared.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container remote-e3 {
      presence "";
      config false;
      description
        "Indicates the alarm is detected.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container upstream-e1-resume {
      presence "";
      config false;
      description
        "This object indicates that the upstream alarm indication signal generated on an E1 interface is cleared.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container upstream-e1 {
      presence "";
      config false;
      description
        "This object indicates that an upstream alarm indication signal is generated on an E1 interface.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container loss-multiframe-e1-resume {
      presence "";
      config false;
      description
        "This object indicates that the LOM alarm on the framed E1 is cleared.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container loss-multiframe-e1 {
      presence "";
      config false;
      description
        "This object indicates an LOM alarm on the framed E1.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container errored-second-exceed-resume {
      presence "";
      config false;
      description
        "This object indicates that the number of errored seconds falls below a specified threshold.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container errored-second-exceed {
      presence "";
      config false;
      description
        "This object indicates that the number of errored seconds exceeds a specified threshold.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container downstream-e1-resume {
      presence "";
      config false;
      description
        "This object indicates that the downstream alarm indication signal generated on an E1 interface is cleared.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container downstream-e1 {
      presence "";
      config false;
      description
        "This object indicates that a downstream alarm indication signal is generated on an E1 interface.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container remote-indication-e1-resume {
      presence "";
      config false;
      description
        "This object indicates that the RAI signal generated on an E1 link is cleared.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container remote-indication-e1 {
      presence "";
      config false;
      description
        "This object indicates that a remote alarm indication (RAI) signal is generated on an E1 link.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container upstream-e1-cpos-resume {
      presence "";
      config false;
      description
        "This object indicates that an upstream alarm indication signal generated on an E1 link channelized from VC12 is cleared.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf lp-id {
        type uint32;
        description
          "Indicates the low order path ID.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container upstream-e1-cpos {
      presence "";
      config false;
      description
        "This object indicates that an upstream alarm indication signal is generated on an E1 link channelized from VC12.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf lp-id {
        type uint32;
        description
          "Indicates the low order path ID.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container loss-multiframe-e1-cpos-resume {
      presence "";
      config false;
      description
        "This object indicates that the OOM alarm generated on the framed E1 channelized from VC12 is cleared.";
      leaf card-id {
        type uint32;
        description
          "Indicates the card ID.";
      }
      leaf hp-id {
        type uint32;
        description
          "Indicates the higher order path ID.";
      }
      leaf lp-id {
        type uint32;
        description
          "Indicates the lower order path ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container loss-multiframe-e1-cpos {
      presence "";
      config false;
      description
        "This object indicates that an out of multiframe (OOM) alarm is generated on the framed E1 channelized from VC12.";
      leaf card-id {
        type uint32;
        description
          "Indicates the card ID.";
      }
      leaf hp-id {
        type uint32;
        description
          "Indicates the higher order path ID.";
      }
      leaf lp-id {
        type uint32;
        description
          "Indicates the lower order path ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container loss-of-frame-e1-cpos-resume {
      presence "";
      config false;
      description
        "This object indicates that the OOF alarm generated on the framed E1 channelized from VC12 is cleared.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf lp-id {
        type uint32;
        description
          "Indicates the low order path ID.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container loss-of-frame-e1-cpos {
      presence "";
      config false;
      description
        "This object indicates that an out of frame (OOF) alarm is generated on the framed E1 channelized from VC12.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf lp-id {
        type uint32;
        description
          "Indicates the low order path ID.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container downstream-e1-cpos-resume {
      presence "";
      config false;
      description
        "This object indicates that the downstream alarm indication signal generated on an E1 link channelized from VC12 is cleared.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf lp-id {
        type uint32;
        description
          "Indicates the low order path ID.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container downstream-e1-cpos {
      presence "";
      config false;
      description
        "This object indicates that a downstream alarm indication signal is generated on an E1 link channelized from VC12.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf lp-id {
        type uint32;
        description
          "Indicates the low order path ID.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container cpos-e1-rai-signal-resume {
      presence "";
      config false;
      description
        "This object indicates that the RAI signal generated on an E1 link channelized from VC12 is cleared.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf lp-id {
        type uint32;
        description
          "Indicates the low order path ID.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container cpos-e1-rai-signal {
      presence "";
      config false;
      description
        "This object indicates that an RAI signal is generated on an E1 link channelized from VC12.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf lp-id {
        type uint32;
        description
          "Indicates the low order path ID.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container channel-loopback-resume {
      presence "";
      config false;
      description
        "This object indicates that a clear alarm is generated when a channel no loopback.";
      leaf hp-id {
        type uint32;
        description
          "Indicates the higher order path ID.";
      }
      leaf index {
        type uint32;
        description
          "Indicates the physical port index.";
      }
      leaf port-name {
        type string {
          length "1..32";
        }
        description
          "Indicates the physical port name.";
      }
      leaf loop-type {
        type ncs_rpc_notif_loop-type;
        description
          "Type of the notification loop. The value can be one -of the following: - 0: stop-loopback - 1: local - 2: remote.";
      }
      leaf lp-id {
        type uint32;
        description
          "Indicates the lower order path ID.";
      }
    }
  }
  augment "/ncs:devices/ncs:device/ncs:netconf-notifications/ncs:received-notifications/ncs:notification/ncs:data" {
    container channel-loopback {
      presence "";
      config false;
      description
        "This object indicates that an alarm is generated when a channel loopback.";
      leaf hp-id {
        type uint32;
        description
          "Indicates the higher order path ID.";
      }
      leaf index {
        type uint32;
        description
          "Indicates the physical port index.";
      }
      leaf port-name {
        type string {
          length "1..32";
        }
        description
          "Indicates the physical port name.";
      }
      leaf loop-type {
        type ncs_rpc_notif_loop-type;
        description
          "Type of the notification loop. The value can be one -of the following: - 0: stop-loopback - 1: local - 2: remote.";
      }
      leaf lp-id {
        type uint32;
        description
          "Indicates the lower order path ID.";
      }
    }
  }
  augment "/ncs:devices/ncs:device/ncs:netconf-notifications/ncs:received-notifications/ncs:notification/ncs:data" {
    container b3-default-exceed-resume {
      presence "";
      config false;
      description
        "This object indicates that a clear alarm is generated when the number of B3 errors falls below a specified threshold.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container b3-default-exceed {
      presence "";
      config false;
      description
        "This object indicates that an alarm is generated when the number of B3 errors exceeds a specified threshold.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container bip2-default-exceed-resume {
      presence "";
      config false;
      description
        "This object indicates that a clear alarm is generated when the number of BIP2 errors falls below a specified threshold.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf lp-id {
        type uint32;
        description
          "Indicates the low order path ID.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container bip2-default-exceed {
      presence "";
      config false;
      description
        "This object indicates that an alarm is generated when the number of BIP2 errors exceeds a specified threshold.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf lp-id {
        type uint32;
        description
          "Indicates the low order path ID.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container b1-default-exceed-resume {
      presence "";
      config false;
      description
        "This object indicates that a clear alarm is generated when the number of B1 errors falls below a specified threshold.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container b1-default-exceed {
      presence "";
      config false;
      description
        "This object indicates that an alarm is generated when the number of B1 errors exceeds a specified threshold.";
      leaf card-id {
        type uint32;
        description
          "Indicates the card ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container au-hp-resume {
      presence "";
      config false;
      description
        "This object indicates that the administrative unit (AU) pointer in the higher order path (HP) indication signal alarm is cleared.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container au-hp {
      presence "";
      config false;
      description
        "This object indicates that the administrative unit (AU) pointer in a higher order path (HP) indication signal alarm is generated.";
      leaf card-id {
        type uint32;
        description
          "Indicates the card ID.";
      }
      leaf hp-id {
        type uint32;
        description
          "Indicates the higher order path ID.";
      }
      leaf port-name {
        type string {
          length "1..32";
        }
        description
          "Indicates the physical port name.";
      }
      leaf port-id {
        type uint32;
        description
          "Indicates the port ID.";
      }
      leaf slot-id {
        type uint32;
        description
          "Indicates the slot ID.";
      }
    }
  }
  augment "/ncs:devices/ncs:device/ncs:netconf-notifications/ncs:received-notifications/ncs:notification/ncs:data" {
    container flow-control-pause-frame-abnormal-resume {
      presence "";
      config false;
      description
        "The port recovered and did not receive pause frames.";
      leaf entity-index {
        type uint32;
        description
          "Indicates the index of an entity.";
      }
      leaf entity-name {
        type string {
          length "0..255";
        }
        description
          "Indicates the name of an entity.";
      }
    }
  }
  augment "/ncs:devices/ncs:device/ncs:netconf-notifications/ncs:received-notifications/ncs:notification/ncs:data" {
    container flow-control-pause-frame-abnormal {
      presence "";
      config false;
      description
        "The port continuously received a large number of pause frames when it did not forward packets.";
      leaf entity-index {
        type uint32;
        description
          "Indicates the index of an entity.";
      }
      leaf entity-name {
        type string {
          length "0..255";
        }
        description
          "Indicates the name of an entity.";
      }
    }
  }
  augment "/ncs:devices/ncs:device/ncs:netconf-notifications/ncs:received-notifications/ncs:notification/ncs:data" {
    container card-fail-resume {
      presence "";
      config false;
      description
        "The card resumed from partial failure.";
      leaf entity-index {
        type uint32;
        description
          "Indicates the index of an entity.";
      }
      leaf entity-name {
        type string {
          length "0..255";
        }
        description
          "Indicates the name of an entity.";
      }
      leaf entity-type {
        type devm:ncs_rpc_notif_notification-entity-type;
        description
          "Type of the notification entity. The value can be one of the following: - 1: MPU - 2: LPU - 3: SFU - 4: PIC - 5: CF card - 6: OFC.";
      }
      leaf fault-id {
        type devm:ncs_rpc_notif_notification-probable-cause-type;
        description
          "Indicates the error code.";
      }
    }
  }
  augment "/ncs:devices/ncs:device/ncs:netconf-notifications/ncs:received-notifications/ncs:notification/ncs:data" {
    container card-fail {
      presence "";
      config false;
      description
        "The card partially failed.";
      leaf entity-index {
        type uint32;
        description
          "Indicates the index of an entity.";
      }
      leaf entity-name {
        type string {
          length "0..255";
        }
        description
          "Indicates the name of an entity.";
      }
      leaf entity-type {
        type devm:ncs_rpc_notif_notification-entity-type;
        description
          "Type of the notification entity. The value can be one of the following: - 1: MPU - 2: LPU - 3: SFU - 4: PIC - 5: CF card - 6: OFC.";
      }
      leaf fault-id {
        type devm:ncs_rpc_notif_notification-probable-cause-type;
        description
          "Indicates the error code.";
      }
    }
  }
  augment "/ncs:devices/ncs:device/ncs:netconf-notifications/ncs:received-notifications/ncs:notification/ncs:data" {
    container card-invalid-resume {
      presence "";
      config false;
      description
        "The card resumed from unavailable.";
      leaf entity-index {
        type uint32;
        description
          "Indicates the index of an entity.";
      }
      leaf entity-name {
        type string {
          length "0..255";
        }
        description
          "Indicates the name of an entity.";
      }
      leaf entity-type {
        type devm:ncs_rpc_notif_notification-entity-type;
        description
          "Type of the notification entity. The value can be one of the following: - 1: MPU - 2: LPU - 3: SFU - 4: PIC - 5: CF card - 6: OFC.";
      }
      leaf fault-id {
        type devm:ncs_rpc_notif_notification-probable-cause-type;
        description
          "Indicates the error code.";
      }
    }
  }
  augment "/ncs:devices/ncs:device/ncs:netconf-notifications/ncs:received-notifications/ncs:notification/ncs:data" {
    container card-invalid {
      presence "";
      config false;
      description
        "The card unavailable.";
      leaf entity-index {
        type uint32;
        description
          "Indicates the index of an entity.";
      }
      leaf entity-name {
        type string {
          length "0..255";
        }
        description
          "Indicates the name of an entity.";
      }
      leaf entity-type {
        type devm:ncs_rpc_notif_notification-entity-type;
        description
          "Type of the notification entity. The value can be one of the following: - 1: MPU - 2: LPU - 3: SFU - 4: PIC - 5: CF card - 6: OFC.";
      }
      leaf fault-id {
        type devm:ncs_rpc_notif_notification-probable-cause-type;
        description
          "Indicates the error code.";
      }
    }
  }
  augment "/ncs:devices/ncs:device/ncs:netconf-notifications/ncs:received-notifications/ncs:notification/ncs:data" {
    container card-insert {
      presence "";
      config false;
      description
        "The card was inserted.";
      leaf entity-index {
        type uint32;
        description
          "Indicates the index of an entity.";
      }
      leaf entity-name {
        type string {
          length "0..255";
        }
        description
          "Indicates the name of an entity.";
      }
      leaf entity-type {
        type devm:ncs_rpc_notif_notification-entity-type;
        description
          "Type of the notification entity. The value can be one of the following: - 1: MPU - 2: LPU - 3: SFU - 4: PIC - 5: CF card - 6: OFC.";
      }
      leaf fault-id {
        type devm:ncs_rpc_notif_notification-probable-cause-type;
        description
          "To describe the fault id of trap.";
      }
    }
  }
  augment "/ncs:devices/ncs:device/ncs:netconf-notifications/ncs:received-notifications/ncs:notification/ncs:data" {
    container card-remove {
      presence "";
      config false;
      description
        "The card was removed.";
      leaf entity-index {
        type uint32;
        description
          "Indicates the index of an entity.";
      }
      leaf entity-name {
        type string {
          length "0..255";
        }
        description
          "Indicates the name of an entity.";
      }
      leaf entity-type {
        type devm:ncs_rpc_notif_notification-entity-type;
        description
          "Type of the notification entity. The value can be one of the following: - 1: MPU - 2: LPU - 3: SFU - 4: PIC - 5: CF card - 6: OFC.";
      }
      leaf fault-id {
        type devm:ncs_rpc_notif_notification-probable-cause-type;
        description
          "To describe the fault id of trap.";
      }
    }
  }
  augment "/ncs:devices/ncs:device/ncs:netconf-notifications/ncs:received-notifications/ncs:notification/ncs:data" {
    container optical-invalid-resume {
      presence "";
      config false;
      description
        "Optical module resume from invalid situation.";
      leaf entity-index {
        type uint32;
        description
          "Indicates the index of an entity.";
      }
      leaf entity-name {
        type string {
          length "0..255";
        }
        description
          "Indicates the name of an entity.";
      }
      leaf fault-id {
        type devm:ncs_rpc_notif_notification-probable-cause-type;
        description
          "Indicates the error code.";
      }
    }
  }
  augment "/ncs:devices/ncs:device/ncs:netconf-notifications/ncs:received-notifications/ncs:notification/ncs:data" {
    container optical-invalid {
      presence "";
      config false;
      description
        "Optical module is invalid.";
      leaf entity-index {
        type uint32;
        description
          "Indicates the index of an entity.";
      }
      leaf entity-name {
        type string {
          length "0..255";
        }
        description
          "Indicates the name of an entity.";
      }
      leaf fault-id {
        type devm:ncs_rpc_notif_notification-probable-cause-type;
        description
          "Indicates the error code.";
      }
    }
  }
  augment "/ncs:devices/ncs:device/ncs:netconf-notifications/ncs:received-notifications/ncs:notification/ncs:data" {
    container optical-unauthorized-resume {
      presence "";
      config false;
      description
        "The alarm on optical module not certified by Ethernet Switch was cleared.";
      leaf entity-index {
        type uint32;
        description
          "Indicates the index of an entity.";
      }
      leaf entity-name {
        type string {
          length "0..255";
        }
        description
          "Indicates the name of an entity.";
      }
      leaf fault-id {
        type devm:ncs_rpc_notif_notification-probable-cause-type;
        description
          "Indicates the error code.";
      }
    }
  }
  augment "/ncs:devices/ncs:device/ncs:netconf-notifications/ncs:received-notifications/ncs:notification/ncs:data" {
    container optical-unauthorized {
      presence "";
      config false;
      description
        "The optical module was not certified by Ethernet Switch.";
      leaf entity-index {
        type uint32;
        description
          "Indicates the index of an entity.";
      }
      leaf entity-name {
        type string {
          length "0..255";
        }
        description
          "Indicates the name of an entity.";
      }
      leaf fault-id {
        type devm:ncs_rpc_notif_notification-probable-cause-type;
        description
          "Indicates the error code.";
      }
    }
  }
  augment "/ncs:devices/ncs:device/ncs:netconf-notifications/ncs:received-notifications/ncs:notification/ncs:data" {
    container optical-insert {
      presence "";
      config false;
      description
        "Optical module has been inserted.";
      leaf entity-index {
        type uint32;
        description
          "Indicates the index of an entity.";
      }
      leaf entity-name {
        type string {
          length "0..255";
        }
        description
          "Indicates the name of an entity.";
      }
      leaf fault-id {
        type devm:ncs_rpc_notif_notification-probable-cause-type;
        description
          "Indicates the error code.";
      }
    }
  }
  augment "/ncs:devices/ncs:device/ncs:netconf-notifications/ncs:received-notifications/ncs:notification/ncs:data" {
    container optical-remove {
      presence "";
      config false;
      description
        "Optical module has been removed.";
      leaf entity-index {
        type uint32;
        description
          "Indicates the index of an entity.";
      }
      leaf entity-name {
        type string {
          length "0..255";
        }
        description
          "Indicates the name of an entity.";
      }
      leaf fault-id {
        type devm:ncs_rpc_notif_notification-probable-cause-type;
        description
          "Indicates the error code.";
      }
    }
  }
}
