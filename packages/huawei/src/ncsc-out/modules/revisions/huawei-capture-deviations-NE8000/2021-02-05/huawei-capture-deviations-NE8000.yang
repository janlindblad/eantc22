module huawei-capture-deviations-NE8000 {
  // Generated by yanger -t ncs
  tailf:mount-id "huawei-nc-1.0:huawei-nc-1.0";
  tailf:ncs-device-type "netconf";

  namespace "urn:huawei:yang:huawei-capture-deviations-NE8000";
  prefix capture-devs-NE8000;

  import huawei-capture {
    prefix capture;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "This module defines deviation statements for huawei-capture module.";

  revision 2021-02-05 {
    description
      "Initial revision.";
    reference "Huawei private.";
  }

  deviation "/ncs:devices/ncs:device/ncs:rpc/capture:rpc-capture-packet/capture:capture-packet/capture:input/capture:packet-number" {
    deviate replace {
      type uint32 {
        range "1..6000";
      }
      default "10";
    }
  }
  deviation "/ncs:devices/ncs:device/ncs:rpc/capture:rpc-capture-packet/capture:capture-packet/capture:input/capture:packet-length" {
    deviate replace {
      default "20";
    }
  }
  deviation "/ncs:devices/ncs:device/ncs:rpc/capture:rpc-capture-packet/capture:capture-packet/capture:input/capture:timeout" {
    deviate replace {
      default "15";
    }
  }
  deviation "/ncs:devices/ncs:device/ncs:rpc/capture:rpc-capture-packet/capture:capture-packet/capture:input/capture:file-name" {
    deviate delete {
      default "capture.cap";
    }
  }
  deviation "/ncs:devices/ncs:device/ncs:rpc/capture:rpc-capture-packet/capture:capture-packet/capture:input/capture:interface-name" {
    deviate add {
      min-elements 1;
      max-elements 8;
    }
  }
  deviation "/ncs:devices/ncs:device/ncs:rpc/capture:rpc-capture-packet/capture:capture-packet/capture:input/capture:local-host" {
    deviate not-supported;
  }
  deviation "/ncs:devices/ncs:device/ncs:rpc/capture:rpc-capture-packet/capture:capture-packet/capture:input/capture:tunnel" {
    deviate not-supported;
  }
  deviation "/ncs:devices/ncs:device/ncs:rpc/capture:rpc-capture-packet/capture:capture-packet/capture:input/capture:clear-payload" {
    deviate not-supported;
  }
  deviation "/ncs:devices/ncs:device/ncs:rpc/capture:rpc-capture-packet/capture:capture-packet/capture:output/capture:capture-index" {
    deviate not-supported;
  }
  deviation "/ncs:devices/ncs:device/ncs:rpc/capture:rpc-stop-capture/capture:stop-capture/capture:input/capture:mode/capture:all" {
    deviate not-supported;
  }
  deviation "/ncs:devices/ncs:device/ncs:rpc/capture:rpc-stop-capture/capture:stop-capture/capture:input/capture:mode/capture:index" {
    deviate not-supported;
  }
  deviation "/ncs:devices/ncs:device/ncs:notifications/ncs:received-notifications/ncs:notification/ncs:data/capture:capture-end-notification" {
    deviate not-supported;
  }
  deviation "/ncs:devices/ncs:device/ncs:netconf-notifications/ncs:received-notifications/ncs:notification/ncs:data/capture:capture-end-notification" {
    deviate not-supported;
  }
}
