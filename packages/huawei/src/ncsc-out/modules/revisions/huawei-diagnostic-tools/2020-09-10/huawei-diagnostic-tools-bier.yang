submodule huawei-diagnostic-tools-bier {
  // Generated by yanger -t ncs
  tailf:mount-id "huawei-nc-1.0:huawei-nc-1.0";

  yang-version 1;
  belongs-to huawei-diagnostic-tools {
    prefix diagnostic-tools;
  }

  import huawei-pub-type {
    prefix pub-type;
  }
  import ietf-inet-types {
    prefix inet;
  }
  import huawei-extension {
    prefix ext;
  }
  include huawei-diagnostic-tools-common;
  include huawei-diagnostic-tools-type;
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "BIER diagnosis tool.";

  revision 2020-08-24 {
    description
      "Modify description.";
    reference "Huawei private.";
  }
  revision 2020-07-04 {
    description
      "Initial revision.";
    reference "Huawei private.";
  }

  grouping ncs_template_bier-ping-trace-result-type {
    description
      "BIER test result.";
    // NCS drop config false container 'ipv6-ping-results'
  }

  grouping ncs_rpc_notif_bier-ping-trace-result-type {
    description
      "BIER test result.";
    container ipv6-ping-results {
      config false;
      description
        "List of BIER IPv6 ping test results.";
      list ipv6-ping-result {
        key "test-name bfr-id";
        config false;
        description
          "Statistics of BIER IPv6 ping test result.";
        leaf test-name {
          type string {
            length "1..32";
          }
          config false;
          description
            "Test name.";
        }
        leaf bfr-id {
          type uint16 {
            range "1..65535";
          }
          config false;
          description
            "BFR-ID of the replier.";
        }
        leaf dest-ip-addr {
          type inet:ipv6-address-no-zone;
          config false;
          description
            "Destination address of the related hop in a test.";
        }
        leaf packet-send {
          type uint32 {
            range "0..4294967295";
          }
          config false;
          description
            "Total number of sent packets.";
        }
        leaf packet-recv {
          type uint32 {
            range "0..4294967295";
          }
          config false;
          description
            "Total number of received packets.";
        }
        leaf loss-ratio {
          type pub-type:ncs_rpc_notif_percent;
          units "%";
          config false;
          description
            "Packet loss ratio of a test.";
        }
        leaf rtt-min {
          type uint32 {
            range "0..4294967295";
          }
          units "ms";
          config false;
          description
            "Minimum RTT of all test packets.";
        }
        leaf rtt-max {
          type uint32 {
            range "0..4294967295";
          }
          units "ms";
          config false;
          description
            "Maximum RTT of all test packets.";
        }
        leaf average-rtt {
          type uint32 {
            range "0..4294967295";
          }
          units "ms";
          config false;
          description
            "Average RTT of all test packets.";
        }
        leaf status {
          type ncs_rpc_notif_dgntl-test-status-type;
          config false;
          description
            "Test status.";
        }
        leaf error-type {
          type ncs_rpc_notif_dgntl-error-type;
          config false;
          description
            "Test operation status.";
        }
        container details {
          config false;
          description
            "List of packet results.";
          list detail {
            key "index";
            config false;
            description
              "Statistics of probe result.";
            leaf index {
              type uint32 {
                range "0..4294967295";
              }
              config false;
              description
                "Serial number of a test packet received.";
            }
            leaf packet-size {
              type uint32 {
                range "0..4294967295";
              }
              config false;
              description
                "Number of bytes in a received response packet.";
            }
            leaf ttl {
              type uint8 {
                range "1..255";
              }
              config false;
              description
                "Hop limit of received response packets.";
            }
            leaf rtt {
              type uint32 {
                range "0..4294967295";
              }
              units "ms";
              config false;
              description
                "RTT of test packets.";
            }
            leaf result-type {
              type ncs_rpc_notif_detail-result-type;
              config false;
              description
                "Result of packets sending, which is either success or timeout.";
            }
            leaf is-delete {
              type boolean;
              config false;
              description
                "Enable/disable the function of deleting test results.";
            }
          }
        }
      }
    }
  }

  grouping live_ncs_bier-ping-trace-result-type {
    description
      "BIER test result.";
    container ipv6-ping-results {
      description
        "List of BIER IPv6 ping test results.";
      list ipv6-ping-result {
        key "test-name bfr-id";
        description
          "Statistics of BIER IPv6 ping test result.";
        leaf test-name {
          type string {
            length "1..32";
          }
          description
            "Test name.";
        }
        leaf bfr-id {
          type uint16 {
            range "1..65535";
          }
          description
            "BFR-ID of the replier.";
        }
        leaf dest-ip-addr {
          type inet:ipv6-address-no-zone;
          description
            "Destination address of the related hop in a test.";
        }
        leaf packet-send {
          type uint32 {
            range "0..4294967295";
          }
          description
            "Total number of sent packets.";
        }
        leaf packet-recv {
          type uint32 {
            range "0..4294967295";
          }
          description
            "Total number of received packets.";
        }
        leaf loss-ratio {
          type pub-type:live_ncs_percent;
          units "%";
          description
            "Packet loss ratio of a test.";
        }
        leaf rtt-min {
          type uint32 {
            range "0..4294967295";
          }
          units "ms";
          description
            "Minimum RTT of all test packets.";
        }
        leaf rtt-max {
          type uint32 {
            range "0..4294967295";
          }
          units "ms";
          description
            "Maximum RTT of all test packets.";
        }
        leaf average-rtt {
          type uint32 {
            range "0..4294967295";
          }
          units "ms";
          description
            "Average RTT of all test packets.";
        }
        leaf status {
          type live_ncs_dgntl-test-status-type;
          description
            "Test status.";
        }
        leaf error-type {
          type live_ncs_dgntl-error-type;
          description
            "Test operation status.";
        }
        container details {
          description
            "List of packet results.";
          list detail {
            key "index";
            description
              "Statistics of probe result.";
            leaf index {
              type uint32 {
                range "0..4294967295";
              }
              description
                "Serial number of a test packet received.";
            }
            leaf packet-size {
              type uint32 {
                range "0..4294967295";
              }
              description
                "Number of bytes in a received response packet.";
            }
            leaf ttl {
              type uint8 {
                range "1..255";
              }
              description
                "Hop limit of received response packets.";
            }
            leaf rtt {
              type uint32 {
                range "0..4294967295";
              }
              units "ms";
              description
                "RTT of test packets.";
            }
            leaf result-type {
              type live_ncs_detail-result-type;
              description
                "Result of packets sending, which is either success or timeout.";
            }
            leaf is-delete {
              type boolean;
              description
                "Enable/disable the function of deleting test results.";
            }
          }
        }
      }
    }
  }

  grouping bier-ping-trace-result-type {
    description
      "BIER test result.";
    // NCS drop config false container 'ipv6-ping-results'
  }

  augment "/ncs:devices/ncs:device/ncs:rpc" {
    container rpc-bier-delete-ipv6-ping {
      tailf:ncs-device-type "netconf";
      tailf:display-when "not(../../ncs:module) or ../../ncs:module[ncs:name='huawei-diagnostic-tools']";
      tailf:action bier-delete-ipv6-ping {
        tailf:actionpoint ncsproxy {
          tailf:internal;
        }
        ext:node-ref "/diagnostic-tools:diagnostic-tools/diagnostic-tools:bier/diagnostic-tools:ipv6-ping-results";
        description
          "Delete BIER IPv6 ping test.";
        input {
          leaf test-name {
            type string;
            mandatory true;
            description
              "Test name.";
          }
        }
      }
    }
  }
  augment "/ncs:devices/ncs:device-group/ncs:ned-id/ncs:rpc" {
    container rpc-bier-delete-ipv6-ping {
      tailf:ncs-device-type "netconf";
      tailf:display-when "/ncs:devices/ncs:device[ncs:name=current()/../../../ncs:member]/ncs:module[ncs:name='huawei-diagnostic-tools']";
      tailf:action bier-delete-ipv6-ping {
        tailf:actionpoint ncsproxy {
          tailf:internal;
        }
        ext:node-ref "/diagnostic-tools:diagnostic-tools/diagnostic-tools:bier/diagnostic-tools:ipv6-ping-results";
        description
          "Delete BIER IPv6 ping test.";
        input {
          leaf test-name {
            type string;
            mandatory true;
            description
              "Test name.";
          }
        }
      }
    }
  }
  augment "/ncs:devices/ncs:device/ncs:rpc" {
    container rpc-bier-stop-ipv6-ping {
      tailf:ncs-device-type "netconf";
      tailf:display-when "not(../../ncs:module) or ../../ncs:module[ncs:name='huawei-diagnostic-tools']";
      tailf:action bier-stop-ipv6-ping {
        tailf:actionpoint ncsproxy {
          tailf:internal;
        }
        ext:node-ref "/diagnostic-tools:diagnostic-tools/diagnostic-tools:bier/diagnostic-tools:ipv6-ping-results";
        description
          "Stop BIER IPv6 ping test.";
        input {
          leaf test-name {
            type string;
            mandatory true;
            description
              "Test name.";
          }
        }
      }
    }
  }
  augment "/ncs:devices/ncs:device-group/ncs:ned-id/ncs:rpc" {
    container rpc-bier-stop-ipv6-ping {
      tailf:ncs-device-type "netconf";
      tailf:display-when "/ncs:devices/ncs:device[ncs:name=current()/../../../ncs:member]/ncs:module[ncs:name='huawei-diagnostic-tools']";
      tailf:action bier-stop-ipv6-ping {
        tailf:actionpoint ncsproxy {
          tailf:internal;
        }
        ext:node-ref "/diagnostic-tools:diagnostic-tools/diagnostic-tools:bier/diagnostic-tools:ipv6-ping-results";
        description
          "Stop BIER IPv6 ping test.";
        input {
          leaf test-name {
            type string;
            mandatory true;
            description
              "Test name.";
          }
        }
      }
    }
  }
  augment "/ncs:devices/ncs:device/ncs:rpc" {
    container rpc-bier-start-ipv6-ping {
      tailf:ncs-device-type "netconf";
      tailf:display-when "not(../../ncs:module) or ../../ncs:module[ncs:name='huawei-diagnostic-tools']";
      tailf:action bier-start-ipv6-ping {
        tailf:actionpoint ncsproxy {
          tailf:internal;
        }
        description
          "Start BIER IPv6 ping test.";
        input {
          leaf test-name {
            type string {
              length "1..32";
            }
            mandatory true;
            description
              "Test name.";
          }
          leaf sub-domain-id {
            type uint8 {
              range "0..255";
            }
            mandatory true;
            description
              "Bit Index Explicit Replication (BIER) subdomain.";
          }
          leaf bit-string-len {
            type ncs_rpc_notif_bit-string-len-type;
            mandatory true;
            description
              "BFR bit string length.";
          }
          choice target-bfr {
            description
              "Specify the target BFR.";
            case single-bfrid {
              description
                "Specify a single BFR-ID.";
              leaf bfr-id {
                type uint16 {
                  range "1..65535";
                }
                mandatory true;
                description
                  "Specify the BFR-ID of the target router.";
              }
            }
            case bfrid-range {
              description
                "Specify the target BFR-ID range.";
              leaf start-bfr-id {
                type uint16 {
                  range "1..65535";
                }
                mandatory true;
                description
                  "Specify the minimum BFR-ID of the target routers.";
              }
              leaf end-bfr-id {
                type uint16 {
                  range "1..65535";
                }
                must '(../end-bfr-id >= ../start-bfr-id)' {
                  tailf:xpath-root 3;
                }
                mandatory true;
                description
                  "Specify the maximum BFR-ID of the target routers.";
              }
            }
          }
          leaf timeout {
            type uint32 {
              range "100..65535";
            }
            units "ms";
            default "2000";
            description
              "Time to wait for a response packet after a test packet is sent.";
          }
          leaf pkt-count {
            type uint32 {
              range "1..65535";
            }
            default "5";
            description
              "Number of sent test packets.";
          }
          leaf interval {
            type uint32 {
              range "100..10000";
            }
            units "ms";
            default "2000";
            description
              "Interval for sending test packets.";
          }
          leaf ttl {
            type uint8 {
              range "1..255";
            }
            default "255";
            description
              "Time to live.";
          }
          leaf source-address {
            type inet:ipv6-address-no-zone;
            description
              "Source address.";
          }
          leaf dest-udp-port {
            type uint16 {
              range "1..65535";
            }
            default "49100";
            description
              "Destination UDP port of echo request.";
          }
        }
      }
    }
  }
  augment "/ncs:devices/ncs:device-group/ncs:ned-id/ncs:rpc" {
    container rpc-bier-start-ipv6-ping {
      tailf:ncs-device-type "netconf";
      tailf:display-when "/ncs:devices/ncs:device[ncs:name=current()/../../../ncs:member]/ncs:module[ncs:name='huawei-diagnostic-tools']";
      tailf:action bier-start-ipv6-ping {
        tailf:actionpoint ncsproxy {
          tailf:internal;
        }
        description
          "Start BIER IPv6 ping test.";
        input {
          leaf test-name {
            type string {
              length "1..32";
            }
            mandatory true;
            description
              "Test name.";
          }
          leaf sub-domain-id {
            type uint8 {
              range "0..255";
            }
            mandatory true;
            description
              "Bit Index Explicit Replication (BIER) subdomain.";
          }
          leaf bit-string-len {
            type ncs_rpc_notif_bit-string-len-type;
            mandatory true;
            description
              "BFR bit string length.";
          }
          choice target-bfr {
            description
              "Specify the target BFR.";
            case single-bfrid {
              description
                "Specify a single BFR-ID.";
              leaf bfr-id {
                type uint16 {
                  range "1..65535";
                }
                mandatory true;
                description
                  "Specify the BFR-ID of the target router.";
              }
            }
            case bfrid-range {
              description
                "Specify the target BFR-ID range.";
              leaf start-bfr-id {
                type uint16 {
                  range "1..65535";
                }
                mandatory true;
                description
                  "Specify the minimum BFR-ID of the target routers.";
              }
              leaf end-bfr-id {
                type uint16 {
                  range "1..65535";
                }
                must '(../end-bfr-id >= ../start-bfr-id)' {
                  tailf:xpath-root 4;
                }
                mandatory true;
                description
                  "Specify the maximum BFR-ID of the target routers.";
              }
            }
          }
          leaf timeout {
            type uint32 {
              range "100..65535";
            }
            units "ms";
            default "2000";
            description
              "Time to wait for a response packet after a test packet is sent.";
          }
          leaf pkt-count {
            type uint32 {
              range "1..65535";
            }
            default "5";
            description
              "Number of sent test packets.";
          }
          leaf interval {
            type uint32 {
              range "100..10000";
            }
            units "ms";
            default "2000";
            description
              "Interval for sending test packets.";
          }
          leaf ttl {
            type uint8 {
              range "1..255";
            }
            default "255";
            description
              "Time to live.";
          }
          leaf source-address {
            type inet:ipv6-address-no-zone;
            description
              "Source address.";
          }
          leaf dest-udp-port {
            type uint16 {
              range "1..65535";
            }
            default "49100";
            description
              "Destination UDP port of echo request.";
          }
        }
      }
    }
  }
  augment "/ncs:devices/ncs:device/ncs:live-status/diagnostic-tools:diagnostic-tools" {
    description
      "List of BIER ping and trace tests.";
    container bier {
      tailf:ncs-device-type "netconf";
      tailf:display-when "not(../../../ncs:module) or ../../../ncs:module[ncs:name='huawei-diagnostic-tools'] or (../../../ncs:live-status-protocol[not(ncs:capability)]) or (../../../ncs:live-status-protocol/ncs:capability/ncs:module[.='huawei-diagnostic-tools'])";
      description
        "Statistics of BIER ping and trace tests.";
      uses diagnostic-tools:live_ncs_bier-ping-trace-result-type;
    }
  }
}
