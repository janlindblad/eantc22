module huawei-ztp {
  // Generated by yanger -t ncs
  tailf:mount-id "huawei-nc-1.0:huawei-nc-1.0";
  tailf:ncs-device-type "netconf";

  namespace "urn:huawei:yang:huawei-ztp";
  prefix ztp;

  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "ZTP (Zero Touch Provisioning) refers to the function of an automatically loading of version file (including system software, configuration files and patch files) used for powering on a new factory device or an empty configuration device.";

  revision 2019-09-29 {
    description
      "Init revision.";
    reference "Huawei private.";
  }
  ext:task-name "ztp";

  augment "/ncs:devices/ncs:device/ncs:rpc" {
    container rpc-reset-pre-configuration {
      tailf:ncs-device-type "netconf";
      tailf:display-when "not(../../ncs:module) or ../../ncs:module[ncs:name='huawei-ztp']";
      tailf:action reset-pre-configuration {
        tailf:actionpoint ncsproxy {
          tailf:internal;
        }
        description
          "Reset ZTP previous configuration file name.";
        input {
          leaf confirm {
            type boolean;
            description
              "Confirm reset.";
          }
        }
      }
    }
  }
  augment "/ncs:devices/ncs:device-group/ncs:ned-id/ncs:rpc" {
    container rpc-reset-pre-configuration {
      tailf:ncs-device-type "netconf";
      tailf:display-when "/ncs:devices/ncs:device[ncs:name=current()/../../../ncs:member]/ncs:module[ncs:name='huawei-ztp']";
      tailf:action reset-pre-configuration {
        tailf:actionpoint ncsproxy {
          tailf:internal;
        }
        description
          "Reset ZTP previous configuration file name.";
        input {
          leaf confirm {
            type boolean;
            description
              "Confirm reset.";
          }
        }
      }
    }
  }
  augment "/ncs:devices/ncs:device/ncs:rpc" {
    container rpc-set-pre-configuration {
      tailf:ncs-device-type "netconf";
      tailf:display-when "not(../../ncs:module) or ../../ncs:module[ncs:name='huawei-ztp']";
      tailf:action set-pre-configuration {
        tailf:actionpoint ncsproxy {
          tailf:internal;
        }
        description
          "Set ZTP previous configuration file name.";
        input {
          leaf file-name {
            type string {
              length "1..65";
            }
            description
              "Previous configuration file name.";
          }
        }
      }
    }
  }
  augment "/ncs:devices/ncs:device-group/ncs:ned-id/ncs:rpc" {
    container rpc-set-pre-configuration {
      tailf:ncs-device-type "netconf";
      tailf:display-when "/ncs:devices/ncs:device[ncs:name=current()/../../../ncs:member]/ncs:module[ncs:name='huawei-ztp']";
      tailf:action set-pre-configuration {
        tailf:actionpoint ncsproxy {
          tailf:internal;
        }
        description
          "Set ZTP previous configuration file name.";
        input {
          leaf file-name {
            type string {
              length "1..65";
            }
            description
              "Previous configuration file name.";
          }
        }
      }
    }
  }
  augment "/ncs:devices/ncs:device/ncs:rpc" {
    container rpc-set-enable-status {
      tailf:ncs-device-type "netconf";
      tailf:display-when "not(../../ncs:module) or ../../ncs:module[ncs:name='huawei-ztp']";
      tailf:action set-enable-status {
        tailf:actionpoint ncsproxy {
          tailf:internal;
        }
        description
          "Set ZTP enable status.";
        input {
          leaf enable {
            type boolean;
            description
              "Enable status.";
          }
        }
      }
    }
  }
  augment "/ncs:devices/ncs:device-group/ncs:ned-id/ncs:rpc" {
    container rpc-set-enable-status {
      tailf:ncs-device-type "netconf";
      tailf:display-when "/ncs:devices/ncs:device[ncs:name=current()/../../../ncs:member]/ncs:module[ncs:name='huawei-ztp']";
      tailf:action set-enable-status {
        tailf:actionpoint ncsproxy {
          tailf:internal;
        }
        description
          "Set ZTP enable status.";
        input {
          leaf enable {
            type boolean;
            description
              "Enable status.";
          }
        }
      }
    }
  }
  augment "/ncs:devices/ncs:device/ncs:config" {
    container ztp {
      tailf:ncs-device-type "netconf";
      tailf:display-when "not(../../ncs:module) or ../../ncs:module[ncs:name='huawei-ztp']";
      description
        "ZTP (Zero Touch Provisioning) refers to the function of an automatically loading of version file (including system software, configuration files and patch files) used for powering on a new factory device or an empty configuration device.";
      // NCS drop config false container status
    }
  }
  augment "/ncs:devices/ncs:device/ncs:live-status" {
    container ztp {
      tailf:ncs-device-type "netconf";
      tailf:display-when "not(../../ncs:module) or ../../ncs:module[ncs:name='huawei-ztp'] or (../../ncs:live-status-protocol[not(ncs:capability)]) or (../../ncs:live-status-protocol/ncs:capability/ncs:module[.='huawei-ztp'])";
      description
        "ZTP (Zero Touch Provisioning) refers to the function of an automatically loading of version file (including system software, configuration files and patch files) used for powering on a new factory device or an empty configuration device.";
      container status {
        description
          "ZTP function status, the ZTP function for used to query the enabled state and completion state.";
        leaf enable {
          type boolean;
          description
            "ZTP function enable or disable status.";
        }
        leaf last {
          type boolean;
          description
            "ZTP function completion status, used to record the completion of the last ZTP function.";
        }
        leaf pre-configuration-name {
          type string {
            length "1..65";
          }
          description
            "ZTP function previous configuration file name.";
        }
      }
    }
  }
  augment "/ncs:devices/ncs:template/ncs:ned-id/ncs:config" {
    container ztp {
      description
        "ZTP (Zero Touch Provisioning) refers to the function of an automatically loading of version file (including system software, configuration files and patch files) used for powering on a new factory device or an empty configuration device.";
      // NCS drop config false container status
    }
  }
}
