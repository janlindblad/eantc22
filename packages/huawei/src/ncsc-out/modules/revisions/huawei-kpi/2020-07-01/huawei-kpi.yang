module huawei-kpi {
  // Generated by yanger -t ncs
  tailf:mount-id "huawei-nc-1.0:huawei-nc-1.0";
  tailf:ncs-device-type "netconf";

  namespace "urn:huawei:yang:huawei-kpi";
  prefix kpi;

  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "KPI data management.";

  revision 2020-07-01 {
    description
      "Modify kpi.";
    reference "Huawei private.";
  }
  revision 2019-06-11 {
    description
      "Initial revision.";
    reference "Huawei private.";
  }
  ext:task-name "perf-mgr";

  augment "/ncs:devices/ncs:device/ncs:config" {
    // NCS drop config false container kpi
  }
  augment "/ncs:devices/ncs:device/ncs:live-status" {
    container kpi {
      tailf:ncs-device-type "netconf";
      tailf:display-when "not(../../ncs:module) or ../../ncs:module[ncs:name='huawei-kpi'] or (../../ncs:live-status-protocol[not(ncs:capability)]) or (../../ncs:live-status-protocol/ncs:capability/ncs:module[.='huawei-kpi'])";
      description
        "KPI data management.";
      container kpi-datas {
        description
          "List of KPI data.";
        list kpi-data {
          key "module-id sequence-id";
          description
            "Statistics of KPI data.";
          leaf module-id {
            type uint32;
            description
              "KPI module ID.";
          }
          leaf sequence-id {
            type uint32;
            description
              "KPI data sequence ID.";
          }
          leaf module-name {
            type string {
              length "1..32";
            }
            description
              "Name of a KPI module, it is case sensitive.";
          }
          leaf data {
            type binary {
              length "1..46080";
            }
            description
              "KPI data.";
          }
        }
      }
    }
  }
  augment "/ncs:devices/ncs:template/ncs:ned-id/ncs:config" {
    // NCS drop config false container kpi
  }
}
