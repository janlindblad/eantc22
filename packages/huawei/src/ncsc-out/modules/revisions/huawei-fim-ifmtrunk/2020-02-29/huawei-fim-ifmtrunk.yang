module huawei-fim-ifmtrunk {
  // Generated by yanger -t ncs
  tailf:mount-id "huawei-nc-1.0:huawei-nc-1.0";
  tailf:ncs-device-type "netconf";

  namespace "urn:huawei:yang:huawei-fim-ifmtrunk";
  prefix fim-ifmtrunk;

  import huawei-ifm {
    prefix ifm;
  }
  import huawei-ifm-trunk {
    prefix ifm-trunk;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Common interface management, which includes the public configuration of interfaces.";
  reference "Huawei private.";

  revision 2020-02-29 {
    description
      "Initial revision.";
    reference "Huawei private.";
  }
  ext:task-name "forwarding";

  typedef ncs_template_enable-type {
    type string;
    description
      "Enable type.";
  }

  typedef ncs_template_trunk-hash-type {
    type string;
    description
      "Trunk arith hash type.";
  }

  typedef ncs_rpc_notif_enable-type {
    type enumeration {
      enum "disable" {
        value 0;
        description
          "Disable.";
      }
      enum "enable" {
        value 1;
        description
          "Enable.";
      }
    }
    description
      "Enable type.";
  }

  typedef ncs_rpc_notif_trunk-hash-type {
    type enumeration {
      enum "CRC32-1" {
        value 0;
        description
          "CRC32-1.";
      }
      enum "CRC32-2" {
        value 1;
        description
          "CRC32-2.";
      }
      enum "XOR-16BIT" {
        value 2;
        description
          "16bit XOR.";
      }
      enum "XOR-8BIT" {
        value 3;
        description
          "8bit XOR.";
      }
    }
    description
      "Trunk arith hash type.";
  }

  typedef live_ncs_enable-type {
    type enumeration {
      enum "disable" {
        value 0;
        description
          "Disable.";
      }
      enum "enable" {
        value 1;
        description
          "Enable.";
      }
    }
    description
      "Enable type.";
  }

  typedef live_ncs_trunk-hash-type {
    type enumeration {
      enum "CRC32-1" {
        value 0;
        description
          "CRC32-1.";
      }
      enum "CRC32-2" {
        value 1;
        description
          "CRC32-2.";
      }
      enum "XOR-16BIT" {
        value 2;
        description
          "16bit XOR.";
      }
      enum "XOR-8BIT" {
        value 3;
        description
          "8bit XOR.";
      }
    }
    description
      "Trunk arith hash type.";
  }

  typedef enable-type {
    type enumeration {
      enum "disable" {
        value 0;
        description
          "Disable.";
      }
      enum "enable" {
        value 1;
        description
          "Enable.";
      }
    }
    description
      "Enable type.";
  }

  typedef trunk-hash-type {
    type enumeration {
      enum "CRC32-1" {
        value 0;
        description
          "CRC32-1.";
      }
      enum "CRC32-2" {
        value 1;
        description
          "CRC32-2.";
      }
      enum "XOR-16BIT" {
        value 2;
        description
          "16bit XOR.";
      }
      enum "XOR-8BIT" {
        value 3;
        description
          "8bit XOR.";
      }
    }
    description
      "Trunk arith hash type.";
  }

  augment "/ncs:devices/ncs:template/ncs:ned-id/ncs:config/ifm:ifm/ifm:interfaces/ifm:interface/ifm-trunk:trunk" {
    description
      "FIM configuration to the ifm module.";
    container fim-ifmtrunk {
      description
        "Configure the FIM configuration to Eth-Trunk interface.";
      leaf trunk-locality-flag {
        // NCS drop when statement
        type string;
        // NCS drop default statement
        description
          "Enable/disable virtual-cluster trunk localization.";
      }
      leaf trunk-hash-type {
        // NCS drop when statement
        type ncs_template_trunk-hash-type;
        // NCS drop default statement
        description
          "Configure the hash arithmetic type for a trunk interface.";
      }
      leaf dual-receive-enable {
        // NCS drop when statement
        type ncs_template_enable-type;
        // NCS drop default statement
        description
          "Enable the backup-dual-receiving function of the Eth-trunk interface.";
      }
    }
  }
  augment "/ncs:devices/ncs:device/ncs:live-status/ifm:ifm/ifm:interfaces/ifm:interface/ifm-trunk:trunk" {
    description
      "FIM configuration to the ifm module.";
    container fim-ifmtrunk {
      tailf:ncs-device-type "netconf";
      tailf:display-when "not(../../../../../../ncs:module) or ../../../../../../ncs:module[ncs:name='huawei-fim-ifmtrunk'] or (../../../../../../ncs:live-status-protocol[not(ncs:capability)]) or (../../../../../../ncs:live-status-protocol/ncs:capability/ncs:module[.='huawei-fim-ifmtrunk'])";
      description
        "Configure the FIM configuration to Eth-Trunk interface.";
      leaf trunk-locality-flag {
        // NCS drop when statement
        type boolean;
        // NCS drop default statement
        description
          "Enable/disable virtual-cluster trunk localization.";
      }
      leaf trunk-hash-type {
        // NCS drop when statement
        type live_ncs_trunk-hash-type;
        // NCS drop default statement
        description
          "Configure the hash arithmetic type for a trunk interface.";
      }
      leaf dual-receive-enable {
        // NCS drop when statement
        type live_ncs_enable-type;
        // NCS drop default statement
        description
          "Enable the backup-dual-receiving function of the Eth-trunk interface.";
      }
    }
  }
  augment "/ncs:devices/ncs:device/ncs:config/ifm:ifm/ifm:interfaces/ifm:interface/ifm-trunk:trunk" {
    description
      "FIM configuration to the ifm module.";
    container fim-ifmtrunk {
      tailf:ncs-device-type "netconf";
      tailf:display-when "not(../../../../../../ncs:module) or ../../../../../../ncs:module[ncs:name='huawei-fim-ifmtrunk']";
      description
        "Configure the FIM configuration to Eth-Trunk interface.";
      leaf trunk-locality-flag {
        when "../../ifm-trunk:type='eth-trunk' or ../../ifm-trunk:type='ip-trunk'" {
          tailf:xpath-root 3;
        }
        type boolean;
        default "true";
        description
          "Enable/disable virtual-cluster trunk localization.";
      }
      leaf trunk-hash-type {
        when "../../ifm-trunk:type='eth-trunk' and ../../ifm-trunk:work-mode!='backup'" {
          tailf:xpath-root 3;
        }
        type trunk-hash-type;
        default "CRC32-1";
        description
          "Configure the hash arithmetic type for a trunk interface.";
      }
      leaf dual-receive-enable {
        when "../../ifm-trunk:type='eth-trunk' and ../../ifm-trunk:work-mode='backup'" {
          tailf:xpath-root 3;
        }
        type enable-type;
        default "disable";
        description
          "Enable the backup-dual-receiving function of the Eth-trunk interface.";
      }
    }
  }
  augment "/ncs:devices/ncs:template/ncs:ned-id/ncs:config/ifm:ifm/ifm:interfaces/ifm:interface/ifm-trunk:trunk/ifm-trunk:members/ifm-trunk:member" {
    description
      "FIM configuration to the ifm module.";
    container fim-ifmtrunk-member {
      description
        "Configure the FIM configuration to trunk member interface.";
      leaf hash-index {
        // NCS drop when statement
        type string;
        description
          "Hash index.";
      }
    }
  }
  augment "/ncs:devices/ncs:device/ncs:live-status/ifm:ifm/ifm:interfaces/ifm:interface/ifm-trunk:trunk/ifm-trunk:members/ifm-trunk:member" {
    description
      "FIM configuration to the ifm module.";
    container fim-ifmtrunk-member {
      tailf:ncs-device-type "netconf";
      tailf:display-when "not(../../../../../../../../ncs:module) or ../../../../../../../../ncs:module[ncs:name='huawei-fim-ifmtrunk'] or (../../../../../../../../ncs:live-status-protocol[not(ncs:capability)]) or (../../../../../../../../ncs:live-status-protocol/ncs:capability/ncs:module[.='huawei-fim-ifmtrunk'])";
      description
        "Configure the FIM configuration to trunk member interface.";
      leaf hash-index {
        // NCS drop when statement
        type uint16 {
          range "1..64";
        }
        description
          "Hash index.";
      }
    }
  }
  augment "/ncs:devices/ncs:device/ncs:config/ifm:ifm/ifm:interfaces/ifm:interface/ifm-trunk:trunk/ifm-trunk:members/ifm-trunk:member" {
    description
      "FIM configuration to the ifm module.";
    container fim-ifmtrunk-member {
      tailf:ncs-device-type "netconf";
      tailf:display-when "not(../../../../../../../../ncs:module) or ../../../../../../../../ncs:module[ncs:name='huawei-fim-ifmtrunk']";
      description
        "Configure the FIM configuration to trunk member interface.";
      leaf hash-index {
        when "../../../../ifm-trunk:hash-type='symmetric' or ../../../../ifm-trunk:hash-type ='symmetric-complement'" {
          tailf:xpath-root 3;
        }
        type uint16 {
          range "1..64";
        }
        description
          "Hash index.";
      }
    }
  }
}
