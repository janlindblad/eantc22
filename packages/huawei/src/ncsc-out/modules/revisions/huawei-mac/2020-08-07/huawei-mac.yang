module huawei-mac {
  // Generated by yanger -t ncs
  tailf:mount-id "huawei-nc-1.0:huawei-nc-1.0";
  tailf:ncs-device-type "netconf";

  namespace "urn:huawei:yang:huawei-mac";
  prefix mac;

  import huawei-pub-type {
    prefix pub-type;
  }
  import ietf-inet-types {
    prefix inet;
  }
  import huawei-ifm {
    prefix ifm;
  }
  import huawei-vlan {
    prefix vlan;
  }
  import huawei-bd {
    prefix bd;
  }
  import huawei-ethernet {
    prefix ethernet;
  }
  import huawei-l2vpn {
    prefix l2vpn;
  }
  import ietf-yang-types {
    prefix yang;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "MAC address forwarding.";

  revision 2020-08-07 {
    description
      "Modify uni-suppressions condition.";
    reference "Huawei private.";
  }
  revision 2020-04-16 {
    description
      "Modify description.";
    reference "Huawei private.";
  }
  revision 2020-03-13 {
    description
      "Modify description.";
    reference "Huawei private.";
  }
  revision 2019-07-08 {
    description
      "Initial revision.";
    reference "Huawei private.";
  }
  ext:task-name "mac";

  typedef ncs_template_mac-type {
    type string;
    description
      "MAC type.";
  }

  typedef ncs_template_vsi-mac-out-type {
    type string;
    description
      "VSI MAC direction.";
  }

  typedef ncs_template_pw-role-type {
    type string;
    description
      "PW role type.";
  }

  typedef ncs_template_suppress-type {
    type string;
    description
      "Suppress type.";
  }

  typedef ncs_template_vsi-direction-type {
    type string;
    description
      "Direction type.";
  }

  typedef ncs_template_mac-limit-forward {
    type string;
    description
      "MAC limit forward type.";
  }

  typedef ncs_template_mac-enable-status {
    type string;
    description
      "MAC Enable type.";
  }

  typedef ncs_template_direction-type {
    type string;
    description
      "Direction type.";
  }

  typedef ncs_template_discard-type {
    type string;
    description
      "Discard type.";
  }

  typedef ncs_rpc_notif_mac-type {
    type enumeration {
      enum "static" {
        value 0;
        description
          "Static type.";
      }
      enum "black-hole" {
        value 1;
        description
          "Blackhole type.";
      }
      enum "dynamic" {
        value 2;
        description
          "Dynamic type.";
      }
      enum "sticky" {
        value 3;
        description
          "Sticky type.";
      }
      enum "mux" {
        value 4;
        description
          "Mux type.";
      }
      enum "security" {
        value 5;
        description
          "Security type.";
      }
      enum "snooping" {
        value 6;
        description
          "Snooping type.";
      }
      enum "tunnel" {
        value 7;
        description
          "Tunnel type.";
      }
      enum "evn" {
        value 9;
        description
          "EVN MAC address entry.";
      }
      enum "authen" {
        value 10;
        description
          "Authen MAC address entry.";
      }
      enum "dynamic-black-hole" {
        value 15;
        description
          "Dynamic blackhole MAC.";
      }
      enum "ovsdb" {
        value 14;
        description
          "Ovsdb MAC address entry.";
      }
    }
    description
      "MAC type.";
  }

  typedef ncs_rpc_notif_vsi-mac-out-type {
    type enumeration {
      enum "ac" {
        value 0;
        description
          "AC type.";
      }
      enum "pw" {
        value 1;
        description
          "PW type.";
      }
    }
    description
      "VSI MAC direction.";
  }

  typedef ncs_rpc_notif_pw-role-type {
    type enumeration {
      enum "master" {
        value 1;
        description
          "Master type.";
      }
      enum "slave" {
        value 2;
        description
          "Slave type.";
      }
      enum "null" {
        value 0;
        description
          "Null type.";
      }
    }
    description
      "PW role type.";
  }

  typedef ncs_rpc_notif_suppress-type {
    type enumeration {
      enum "broadcast" {
        value 0;
        description
          "Broadcast type.";
      }
      enum "multicast" {
        value 1;
        description
          "Multicast type.";
      }
      enum "unknown-unicast" {
        value 2;
        description
          "Unknown unicast type.";
      }
    }
    description
      "Suppress type.";
  }

  typedef ncs_rpc_notif_vsi-direction-type {
    type enumeration {
      enum "uni-inbound" {
        value 0;
        description
          "UNI inbound.";
      }
      enum "uni-outbound" {
        value 1;
        description
          "UNI outbound.";
      }
    }
    description
      "Direction type.";
  }

  typedef ncs_rpc_notif_mac-limit-forward {
    type enumeration {
      enum "discard" {
        value 0;
        description
          "Discard type.";
      }
      enum "forward" {
        value 1;
        description
          "Forward type.";
      }
    }
    description
      "MAC limit forward type.";
  }

  typedef ncs_rpc_notif_mac-enable-status {
    type enumeration {
      enum "disable" {
        value 0;
        description
          "Disable type.";
      }
      enum "enable" {
        value 1;
        description
          "Enable type.";
      }
    }
    description
      "MAC Enable type.";
  }

  typedef ncs_rpc_notif_direction-type {
    type enumeration {
      enum "inbound" {
        value 0;
        description
          "Inbound type.";
      }
      enum "outbound" {
        value 1;
        description
          "Outbound type.";
      }
    }
    description
      "Direction type.";
  }

  typedef ncs_rpc_notif_discard-type {
    type enumeration {
      enum "broadcast-discard" {
        value 0;
        description
          "Discard broadcast packets.";
      }
      enum "unknown-multicast-discard" {
        value 1;
        description
          "Discard unknown multicast packets.";
      }
      enum "unknown-unicast-discard" {
        value 2;
        description
          "Discard Unknown unicast packets.";
      }
    }
    description
      "Discard type.";
  }

  typedef live_ncs_mac-type {
    type enumeration {
      enum "static" {
        value 0;
        description
          "Static type.";
      }
      enum "black-hole" {
        value 1;
        description
          "Blackhole type.";
      }
      enum "dynamic" {
        value 2;
        description
          "Dynamic type.";
      }
      enum "sticky" {
        value 3;
        description
          "Sticky type.";
      }
      enum "mux" {
        value 4;
        description
          "Mux type.";
      }
      enum "security" {
        value 5;
        description
          "Security type.";
      }
      enum "snooping" {
        value 6;
        description
          "Snooping type.";
      }
      enum "tunnel" {
        value 7;
        description
          "Tunnel type.";
      }
      enum "evn" {
        value 9;
        description
          "EVN MAC address entry.";
      }
      enum "authen" {
        value 10;
        description
          "Authen MAC address entry.";
      }
      enum "dynamic-black-hole" {
        value 15;
        description
          "Dynamic blackhole MAC.";
      }
      enum "ovsdb" {
        value 14;
        description
          "Ovsdb MAC address entry.";
      }
    }
    description
      "MAC type.";
  }

  typedef live_ncs_vsi-mac-out-type {
    type enumeration {
      enum "ac" {
        value 0;
        description
          "AC type.";
      }
      enum "pw" {
        value 1;
        description
          "PW type.";
      }
    }
    description
      "VSI MAC direction.";
  }

  typedef live_ncs_pw-role-type {
    type enumeration {
      enum "master" {
        value 1;
        description
          "Master type.";
      }
      enum "slave" {
        value 2;
        description
          "Slave type.";
      }
      enum "null" {
        value 0;
        description
          "Null type.";
      }
    }
    description
      "PW role type.";
  }

  typedef live_ncs_suppress-type {
    type enumeration {
      enum "broadcast" {
        value 0;
        description
          "Broadcast type.";
      }
      enum "multicast" {
        value 1;
        description
          "Multicast type.";
      }
      enum "unknown-unicast" {
        value 2;
        description
          "Unknown unicast type.";
      }
    }
    description
      "Suppress type.";
  }

  typedef live_ncs_vsi-direction-type {
    type enumeration {
      enum "uni-inbound" {
        value 0;
        description
          "UNI inbound.";
      }
      enum "uni-outbound" {
        value 1;
        description
          "UNI outbound.";
      }
    }
    description
      "Direction type.";
  }

  typedef live_ncs_mac-limit-forward {
    type enumeration {
      enum "discard" {
        value 0;
        description
          "Discard type.";
      }
      enum "forward" {
        value 1;
        description
          "Forward type.";
      }
    }
    description
      "MAC limit forward type.";
  }

  typedef live_ncs_mac-enable-status {
    type enumeration {
      enum "disable" {
        value 0;
        description
          "Disable type.";
      }
      enum "enable" {
        value 1;
        description
          "Enable type.";
      }
    }
    description
      "MAC Enable type.";
  }

  typedef live_ncs_direction-type {
    type enumeration {
      enum "inbound" {
        value 0;
        description
          "Inbound type.";
      }
      enum "outbound" {
        value 1;
        description
          "Outbound type.";
      }
    }
    description
      "Direction type.";
  }

  typedef live_ncs_discard-type {
    type enumeration {
      enum "broadcast-discard" {
        value 0;
        description
          "Discard broadcast packets.";
      }
      enum "unknown-multicast-discard" {
        value 1;
        description
          "Discard unknown multicast packets.";
      }
      enum "unknown-unicast-discard" {
        value 2;
        description
          "Discard Unknown unicast packets.";
      }
    }
    description
      "Discard type.";
  }

  typedef mac-type {
    type enumeration {
      enum "static" {
        value 0;
        description
          "Static type.";
      }
      enum "black-hole" {
        value 1;
        description
          "Blackhole type.";
      }
      enum "dynamic" {
        value 2;
        description
          "Dynamic type.";
      }
      enum "sticky" {
        value 3;
        description
          "Sticky type.";
      }
      enum "mux" {
        value 4;
        description
          "Mux type.";
      }
      enum "security" {
        value 5;
        description
          "Security type.";
      }
      enum "snooping" {
        value 6;
        description
          "Snooping type.";
      }
      enum "tunnel" {
        value 7;
        description
          "Tunnel type.";
      }
      enum "evn" {
        value 9;
        description
          "EVN MAC address entry.";
      }
      enum "authen" {
        value 10;
        description
          "Authen MAC address entry.";
      }
      enum "dynamic-black-hole" {
        value 15;
        description
          "Dynamic blackhole MAC.";
      }
      enum "ovsdb" {
        value 14;
        description
          "Ovsdb MAC address entry.";
      }
    }
    description
      "MAC type.";
  }

  typedef vsi-mac-out-type {
    type enumeration {
      enum "ac" {
        value 0;
        description
          "AC type.";
      }
      enum "pw" {
        value 1;
        description
          "PW type.";
      }
    }
    description
      "VSI MAC direction.";
  }

  typedef pw-role-type {
    type enumeration {
      enum "master" {
        value 1;
        description
          "Master type.";
      }
      enum "slave" {
        value 2;
        description
          "Slave type.";
      }
      enum "null" {
        value 0;
        description
          "Null type.";
      }
    }
    description
      "PW role type.";
  }

  typedef suppress-type {
    type enumeration {
      enum "broadcast" {
        value 0;
        description
          "Broadcast type.";
      }
      enum "multicast" {
        value 1;
        description
          "Multicast type.";
      }
      enum "unknown-unicast" {
        value 2;
        description
          "Unknown unicast type.";
      }
    }
    description
      "Suppress type.";
  }

  typedef vsi-direction-type {
    type enumeration {
      enum "uni-inbound" {
        value 0;
        description
          "UNI inbound.";
      }
      enum "uni-outbound" {
        value 1;
        description
          "UNI outbound.";
      }
    }
    description
      "Direction type.";
  }

  typedef mac-limit-forward {
    type enumeration {
      enum "discard" {
        value 0;
        description
          "Discard type.";
      }
      enum "forward" {
        value 1;
        description
          "Forward type.";
      }
    }
    description
      "MAC limit forward type.";
  }

  typedef mac-enable-status {
    type enumeration {
      enum "disable" {
        value 0;
        description
          "Disable type.";
      }
      enum "enable" {
        value 1;
        description
          "Enable type.";
      }
    }
    description
      "MAC Enable type.";
  }

  typedef direction-type {
    type enumeration {
      enum "inbound" {
        value 0;
        description
          "Inbound type.";
      }
      enum "outbound" {
        value 1;
        description
          "Outbound type.";
      }
    }
    description
      "Direction type.";
  }

  typedef discard-type {
    type enumeration {
      enum "broadcast-discard" {
        value 0;
        description
          "Discard broadcast packets.";
      }
      enum "unknown-multicast-discard" {
        value 1;
        description
          "Discard unknown multicast packets.";
      }
      enum "unknown-unicast-discard" {
        value 2;
        description
          "Discard Unknown unicast packets.";
      }
    }
    description
      "Discard type.";
  }

  grouping ncs_template_pw-mac-suppression {
    description
      "PW MAC suppression.";
    list suppression {
      // NCS patched for predictable order
      ordered-by user;
      // NCS drop must statement
      key "type";
      description
        "Configure PW traffic suppression.";
      leaf type {
        type ncs_template_suppress-type;
        description
          "Traffic suppression type.";
      }
      leaf cir {
        type string;
        units "kbit/s";
        // NCS drop mandatory statement
        description
          "CIR value.";
      }
      leaf cbs {
        type string;
        units "Byte";
        ext:dynamic-default {
          ext:default-value "10000" {
            // NCS drop when statement
            description
              "When cir less than 10000kbit/s,the default value is 10000 Byte.";
          }
          ext:default-value "cir" {
            // NCS drop when statement
            description
              "When cir more than 10000kbit/s,the default value is the same as the value of cir.";
          }
        }
        description
          "CBS value. If user does not specify this value, the system will calc a value by CIR value.";
      }
    }
  }

  grouping ncs_rpc_notif_pw-mac-suppression {
    description
      "PW MAC suppression.";
    list suppression {
      must 'cir<=cbs' {
        tailf:xpath-root 3;
      }
      key "type";
      description
        "Configure PW traffic suppression.";
      leaf type {
        type ncs_rpc_notif_suppress-type;
        description
          "Traffic suppression type.";
      }
      leaf cir {
        type uint64 {
          range "100..4294967295";
        }
        units "kbit/s";
        mandatory true;
        description
          "CIR value.";
      }
      leaf cbs {
        type uint64 {
          range "100..4294967295";
        }
        units "Byte";
        ext:dynamic-default {
          ext:default-value "10000" {
            when '../cir <= 10000' {
              tailf:xpath-root 3;
            }
            description
              "When cir less than 10000kbit/s,the default value is 10000 Byte.";
          }
          ext:default-value "cir" {
            when '../cir > 10000' {
              tailf:xpath-root 3;
            }
            description
              "When cir more than 10000kbit/s,the default value is the same as the value of cir.";
          }
        }
        description
          "CBS value. If user does not specify this value, the system will calc a value by CIR value.";
      }
    }
  }

  grouping live_ncs_pw-mac-suppression {
    description
      "PW MAC suppression.";
    list suppression {
      // NCS drop must statement
      key "type";
      description
        "Configure PW traffic suppression.";
      leaf type {
        type live_ncs_suppress-type;
        description
          "Traffic suppression type.";
      }
      leaf cir {
        type uint64 {
          range "100..4294967295";
        }
        units "kbit/s";
        // NCS drop mandatory statement
        description
          "CIR value.";
      }
      leaf cbs {
        type uint64 {
          range "100..4294967295";
        }
        units "Byte";
        ext:dynamic-default {
          ext:default-value "10000" {
            // NCS drop when statement
            description
              "When cir less than 10000kbit/s,the default value is 10000 Byte.";
          }
          ext:default-value "cir" {
            // NCS drop when statement
            description
              "When cir more than 10000kbit/s,the default value is the same as the value of cir.";
          }
        }
        description
          "CBS value. If user does not specify this value, the system will calc a value by CIR value.";
      }
    }
  }

  grouping pw-mac-suppression {
    description
      "PW MAC suppression.";
    list suppression {
      must 'cir<=cbs' {
        tailf:xpath-root 3;
      }
      key "type";
      description
        "Configure PW traffic suppression.";
      leaf type {
        type suppress-type;
        description
          "Traffic suppression type.";
      }
      leaf cir {
        type uint64 {
          range "100..4294967295";
        }
        units "kbit/s";
        mandatory true;
        description
          "CIR value.";
      }
      leaf cbs {
        type uint64 {
          range "100..4294967295";
        }
        units "Byte";
        ext:dynamic-default {
          ext:default-value "10000" {
            when '../cir <= 10000' {
              tailf:xpath-root 3;
            }
            description
              "When cir less than 10000kbit/s,the default value is 10000 Byte.";
          }
          ext:default-value "cir" {
            when '../cir > 10000' {
              tailf:xpath-root 3;
            }
            description
              "When cir more than 10000kbit/s,the default value is the same as the value of cir.";
          }
        }
        description
          "CBS value. If user does not specify this value, the system will calc a value by CIR value.";
      }
    }
  }

  augment "/ncs:devices/ncs:device/ncs:config" {
    container mac {
      tailf:ncs-device-type "netconf";
      tailf:display-when "not(../../ncs:module) or ../../ncs:module[ncs:name='huawei-mac']";
      description
        "MAC address forwarding.";
      container global-attribute {
        description
          "Configure MAC global attribute.";
        leaf age-time-enable {
          type mac-enable-status;
          default "enable";
          description
            "Whether MAC address aging is enabled.";
        }
        leaf aging-time {
          when "../age-time-enable='enable'" {
            tailf:xpath-root 3;
          }
          type uint32 {
            range "60..1000000";
          }
          units "s";
          default "300";
          description
            "Aging time.";
        }
      }
      container mac-limit-rules {
        description
          "List of global MAC address learning limit rule.";
        list mac-limit-rule {
          key "name";
          description
            "Configure global MAC address learning limit.";
          leaf name {
            type string {
              length "1..31";
            }
            description
              "Global MAC address learning limit rule name.";
          }
          leaf maximum {
            type uint32 {
              range "0..131072";
            }
            must 'not(../rate=0) or (../rate=0 and ../maximum>0)' {
              tailf:xpath-root 3;
            }
            mandatory true;
            description
              "Maximum number of MAC addresses that can be learned. The value 0 means unlimited.";
          }
          leaf rate {
            type uint16 {
              range "0..1000";
            }
            units "ms";
            must 'not(../maximum=0) or (../maximum=0 and ../rate>0)' {
              tailf:xpath-root 3;
            }
            default "0";
            description
              "Interval at which MAC addresses are learned. The value 0 indicates that no rate limit is set.";
          }
          leaf action {
            type mac-limit-forward;
            default "discard";
            description
              "Discard or forward after the number of learned MAC addresses reaches the maximum number.";
          }
          leaf alarm {
            type mac-enable-status;
            default "enable";
            description
              "Whether an alarm is generated after the number of learned MAC addresses reaches the maximum number.";
          }
        }
      }
      // NCS drop config false container 'vlan-dynamic-macs'
      // NCS drop config false container 'bd-dynamic-macs'
      // NCS drop config false container 'vsi-dynamic-macs'
      // NCS drop config false container 'bd-mac-total-numbers'
      // NCS drop config false container 'mac-statistics'
    }
  }
  augment "/ncs:devices/ncs:device/ncs:live-status" {
    container mac {
      tailf:ncs-device-type "netconf";
      tailf:display-when "not(../../ncs:module) or ../../ncs:module[ncs:name='huawei-mac'] or (../../ncs:live-status-protocol[not(ncs:capability)]) or (../../ncs:live-status-protocol/ncs:capability/ncs:module[.='huawei-mac'])";
      description
        "MAC address forwarding.";
      container global-attribute {
        description
          "Configure MAC global attribute.";
        leaf age-time-enable {
          type live_ncs_mac-enable-status;
          // NCS drop default statement
          description
            "Whether MAC address aging is enabled.";
        }
        leaf aging-time {
          // NCS drop when statement
          type uint32 {
            range "60..1000000";
          }
          units "s";
          // NCS drop default statement
          description
            "Aging time.";
        }
      }
      container mac-limit-rules {
        description
          "List of global MAC address learning limit rule.";
        list mac-limit-rule {
          key "name";
          description
            "Configure global MAC address learning limit.";
          leaf name {
            type string {
              length "1..31";
            }
            description
              "Global MAC address learning limit rule name.";
          }
          leaf maximum {
            type uint32 {
              range "0..131072";
            }
            // NCS drop must statement
            // NCS drop mandatory statement
            description
              "Maximum number of MAC addresses that can be learned. The value 0 means unlimited.";
          }
          leaf rate {
            type uint16 {
              range "0..1000";
            }
            units "ms";
            // NCS drop must statement
            // NCS drop default statement
            description
              "Interval at which MAC addresses are learned. The value 0 indicates that no rate limit is set.";
          }
          leaf action {
            type live_ncs_mac-limit-forward;
            // NCS drop default statement
            description
              "Discard or forward after the number of learned MAC addresses reaches the maximum number.";
          }
          leaf alarm {
            type live_ncs_mac-enable-status;
            // NCS drop default statement
            description
              "Whether an alarm is generated after the number of learned MAC addresses reaches the maximum number.";
          }
        }
      }
      container vlan-dynamic-macs {
        description
          "List of displayed VLAN forwarding table.";
        list vlan-dynamic-mac {
          key "slot-id vlan-id address";
          description
            "Statistics of displayed VLAN forwarding entry.";
          leaf slot-id {
            type string {
              length "1..24";
            }
            description
              "Slot ID.";
          }
          leaf vlan-id {
            type uint16 {
              range "1..4094";
            }
            description
              "VLAN ID.";
          }
          leaf address {
            type pub-type:live_ncs_mac-address;
            description
              "MAC address.";
          }
          leaf type {
            type live_ncs_mac-type;
            description
              "MAC address type.";
          }
          leaf out-interface-name {
            type pub-type:live_ncs_if-name;
            description
              "Outbound interface name.";
          }
          leaf last-change-time {
            type yang:date-and-time;
            description
              "Dynamic MAC last change time.";
          }
        }
      }
      container bd-dynamic-macs {
        description
          "List of displayed BD forwarding table. The query result of dynamic MAC addresses is disordered.";
        list bd-dynamic-mac {
          key "slot-id address bd-id pw-role";
          description
            "Statistics of displayed BD forwarding entry.";
          leaf slot-id {
            type string {
              length "1..50";
            }
            description
              "Slot number.";
          }
          leaf address {
            type pub-type:live_ncs_mac-address;
            description
              "MAC address.";
          }
          leaf bd-id {
            type uint32 {
              range "1..16777215";
            }
            description
              "ID of a bridge domain.";
          }
          leaf pw-role {
            type live_ncs_pw-role-type;
            description
              "PW role type.";
          }
          leaf type {
            type live_ncs_mac-type;
            description
              "MAC address type of a bridge domain.";
          }
          leaf out-interface-name {
            type pub-type:live_ncs_if-name;
            description
              "Outbound interface name.";
          }
          leaf untag {
            type boolean;
            description
              "Packets without VLAN tags.";
          }
          leaf pe-default {
            type boolean;
            description
              "PE default VLAN.";
          }
          leaf ce-default {
            type boolean;
            description
              "CE default VLAN.";
          }
          leaf vid {
            type uint16 {
              range "1..4094";
            }
            description
              "Outer VLAN tag.";
          }
          leaf ce-vid {
            type uint16 {
              range "1..4094";
            }
            description
              "Inner VLAN tag.";
          }
          leaf learned-period {
            type uint32 {
              range "0..4294967294";
            }
            description
              "Dynamic MAC holding time.";
          }
          leaf peer-ip {
            type inet:ipv4-address-no-zone;
            ext:support-filter "true";
            description
              "Peer IP.";
          }
          leaf last-change-time {
            type yang:date-and-time;
            description
              "Dynamic MAC last change time.";
          }
          leaf peer-ipv6 {
            type inet:ipv6-address-no-zone;
            ext:support-filter "true";
            description
              "Peer IPv6 address.";
          }
          leaf vsi-name {
            type string {
              length "1..31";
            }
            description
              "VSI name.";
          }
          leaf account-enable {
            type boolean;
            description
              "MAC acounting state.";
          }
          leaf destination-packet-count {
            type uint64;
            description
              "Destination packet counts.";
          }
          leaf destination-byte-count {
            type uint64;
            description
              "Destination byte counts.";
          }
          leaf source-packet-count {
            type uint64;
            description
              "Source packet counts.";
          }
          leaf source-byte-count {
            type uint64;
            description
              "Source byte counts.";
          }
        }
      }
      container vsi-dynamic-macs {
        description
          "List of VSI forwarding table.";
        list vsi-dynamic-mac {
          key "slot-id vsi-name vlan-id address pw-role";
          description
            "Statistics of VSI forwarding entry.";
          leaf slot-id {
            type string {
              length "1..24";
            }
            description
              "Slot ID.";
          }
          leaf vsi-name {
            type string {
              length "1..31";
            }
            description
              "VSI name.";
          }
          leaf vlan-id {
            type uint16 {
              range "0..4094";
            }
            description
              "VLAN ID.";
          }
          leaf address {
            type pub-type:live_ncs_mac-address;
            description
              "MAC address.";
          }
          leaf pw-role {
            type live_ncs_pw-role-type;
            description
              "PW role type.";
          }
          leaf out-interface-name {
            type leafref {
              path "/ncs:devices/ncs:device/ncs:live-status/ifm:ifm/ifm:interfaces/ifm:interface/ifm:name" {
                tailf:xpath-root 3;
              }
            }
            description
              "Outbound interface name.";
          }
          leaf pe-vid {
            type uint16 {
              range "1..4094";
            }
            description
              "Outer VLAN tag.";
          }
          leaf ce-vid {
            type uint16 {
              range "1..4094";
            }
            description
              "Inner VLAN tag.";
          }
          leaf type {
            type live_ncs_mac-type;
            description
              "MAC type.";
          }
          leaf out-interface-type {
            type live_ncs_vsi-mac-out-type;
            description
              "Outbound interface type.";
          }
          leaf pw-id {
            type uint32 {
              range "1..4294967295";
            }
            description
              "PW ID.";
          }
          leaf peer-ip {
            type inet:ipv4-address-no-zone;
            description
              "Peer IP address.";
          }
          leaf pw-name {
            type string {
              length "1..31";
            }
            description
              "PW name.";
          }
          leaf is-ingress-mac {
            type boolean;
            description
              "Ingress MAC.";
          }
          leaf is-include-stacking-ce-vlan {
            type boolean;
            description
              "Is include stacking CE-VLAN.";
          }
          leaf last-change-time {
            type yang:date-and-time;
            description
              "Dynamic MAC last change time.";
          }
          leaf account-enable {
            type boolean;
            description
              "MAC acounting state.";
          }
          leaf destination-packet-count {
            type uint64;
            description
              "Destination packet counts.";
          }
          leaf destination-byte-count {
            type uint64;
            description
              "Destination byte counts.";
          }
          leaf source-packet-count {
            type uint64;
            description
              "Source packet counts.";
          }
          leaf source-byte-count {
            type uint64;
            description
              "Source byte counts.";
          }
        }
      }
      container bd-mac-total-numbers {
        description
          "List of MAC total number of bridge domain.";
        list bd-mac-total-number {
          key "bd-id";
          description
            "Statistics of MAC total number of bridge domain.";
          leaf bd-id {
            type uint32 {
              range "1..16777215";
            }
            description
              "ID of a bridge domain.";
          }
          leaf number {
            type uint32;
            description
              "Total MAC address number.";
          }
        }
      }
      container mac-statistics {
        description
          "List of MAC summary.";
        list mac-statistic {
          key "slot-id";
          description
            "Statistics of MAC summary.";
          leaf slot-id {
            type string {
              length "1..24";
            }
            description
              "Slot ID.";
          }
          leaf total {
            type uint32;
            description
              "Number of total MAC addresses.";
          }
          leaf black-hole {
            type uint32;
            description
              "Number of blackhole MAC addresses.";
          }
          leaf static {
            type uint32;
            description
              "Number of static MAC addresses.";
          }
          leaf dynamic {
            type uint32;
            description
              "Number of dynamic MAC addresses.";
          }
          leaf dynamic-local {
            type uint32;
            description
              "Number of dynamic local MAC addresses.";
          }
          leaf dynamic-remote {
            type uint32;
            description
              "Number of dynamic remote MAC addresses.";
          }
          leaf dynamic-trunk {
            type uint32;
            description
              "Number of dynamic trunk MAC addresses.";
          }
          leaf oam {
            type uint32;
            description
              "Number of OAM MAC addresses.";
          }
          leaf sticky {
            type uint32;
            description
              "Number of sticky MAC addresses.";
          }
          leaf security {
            type uint32;
            description
              "Number of security MAC addresses.";
          }
          leaf authen {
            type uint32;
            description
              "Number of authen MAC addresses.";
          }
          leaf guest {
            type uint32;
            description
              "Number of guest MAC addresses.";
          }
          leaf mux {
            type uint32;
            description
              "Number of MUX MAC addresses.";
          }
          leaf tunnel {
            type uint32;
            description
              "Number of tunnel MAC addresses.";
          }
          leaf snooping {
            type uint32;
            description
              "Number of snooping MAC addresses.";
          }
          leaf evn {
            type uint32;
            description
              "Number of EVN MAC addresses.";
          }
          leaf ovsdb {
            type uint32;
            description
              "Number of ovsdb MAC addresses.";
          }
          leaf capacity {
            type uint32;
            description
              "The capacity of MAC addresses.";
          }
        }
      }
    }
  }
  augment "/ncs:devices/ncs:template/ncs:ned-id/ncs:config" {
    container mac {
      description
        "MAC address forwarding.";
      container global-attribute {
        description
          "Configure MAC global attribute.";
        leaf age-time-enable {
          type ncs_template_mac-enable-status;
          // NCS drop default statement
          description
            "Whether MAC address aging is enabled.";
        }
        leaf aging-time {
          // NCS drop when statement
          type string;
          units "s";
          // NCS drop default statement
          description
            "Aging time.";
        }
      }
      container mac-limit-rules {
        description
          "List of global MAC address learning limit rule.";
        list mac-limit-rule {
          // NCS patched for predictable order
          ordered-by user;
          key "name";
          description
            "Configure global MAC address learning limit.";
          leaf name {
            type string;
            description
              "Global MAC address learning limit rule name.";
          }
          leaf maximum {
            type string;
            // NCS drop must statement
            // NCS drop mandatory statement
            description
              "Maximum number of MAC addresses that can be learned. The value 0 means unlimited.";
          }
          leaf rate {
            type string;
            units "ms";
            // NCS drop must statement
            // NCS drop default statement
            description
              "Interval at which MAC addresses are learned. The value 0 indicates that no rate limit is set.";
          }
          leaf action {
            type ncs_template_mac-limit-forward;
            // NCS drop default statement
            description
              "Discard or forward after the number of learned MAC addresses reaches the maximum number.";
          }
          leaf alarm {
            type ncs_template_mac-enable-status;
            // NCS drop default statement
            description
              "Whether an alarm is generated after the number of learned MAC addresses reaches the maximum number.";
          }
        }
      }
      // NCS drop config false container 'vlan-dynamic-macs'
      // NCS drop config false container 'bd-dynamic-macs'
      // NCS drop config false container 'vsi-dynamic-macs'
      // NCS drop config false container 'bd-mac-total-numbers'
      // NCS drop config false container 'mac-statistics'
    }
  }
  augment "/ncs:devices/ncs:template/ncs:ned-id/ncs:config/vlan:vlan/vlan:vlans/vlan:vlan" {
    description
      "MAC attribute of a VLAN.";
    container mac-addresss {
      description
        "List of VLAN forwarding table.";
      list mac-address {
        // NCS patched for predictable order
        ordered-by user;
        // NCS drop must statement
        key "address";
        description
          "Configure VLAN forwarding entry.";
        leaf address {
          type pub-type:ncs_template_mac-address;
          description
            "MAC address.";
        }
        choice mac-type {
          // NCS drop mandatory statement
          description
            "MAC type.";
          case black-hole {
            description
              "Blackhole type.";
            leaf black-hole {
              type empty;
              // NCS drop mandatory statement
              description
                "Blackhole type.";
            }
          }
          case static {
            description
              "Static type.";
            leaf out-interface-name {
              type string;
              // NCS drop must statement
              // NCS drop mandatory statement
              description
                "Outbound interface name. The to-be-delivered VLAN ID must be the default VLAN ID, the VLAN ID in the outer VLAN tag, the post-mapping VLAN ID, or a VLAN ID in the list of allowed VLANs on the specified interface.";
            }
            leaf ce-default {
              type empty;
              // NCS drop must statement
              description
                "CE default VLAN. If the to-be-delivered VLAN ID is neither the VLAN ID in the outer VLAN tag to be added to a tagged packet, nor the post-mapping VLAN ID, nor a VLAN ID in the list of allowed VLANs on the specified interface, ce-default is mandatory.";
            }
            leaf ce-vlan-id {
              type string;
              // NCS drop must statement
              description
                "CE VLAN ID. The CE VLAN ID must exist in the list of VLAN IDs that can be received by adding the outer VLAN tag carrying the to-be-delivered VLAN ID, or in the list of VLAN IDs that can be mapped to the to-be-delivered VLAN ID on the specified interface. If the to-be-delivered VLAN ID is neither the default VLAN ID, nor the VLAN ID in the outer VLAN tag to be added to an untagged packet, nor a VLAN ID in the list of allowed VLANs on the specified interface, CE VLAN ID is mandatory.";
            }
          }
        }
      }
    }
    container mac-limit {
      // NCS drop when statement
      presence "MAC address limit.";
      description
        "Configure MAC address limit.";
      leaf maximum {
        type string;
        // NCS drop must statement
        // NCS drop mandatory statement
        description
          "Maximum number of MAC addresses that can be learned. The value 0 means unlimited.";
      }
      leaf rate {
        type string;
        units "ms";
        // NCS drop must statement
        // NCS drop default statement
        description
          "Interval at which MAC addresses are learned. The value 0 indicates that no rate limit is set.";
      }
      leaf action {
        type ncs_template_mac-limit-forward;
        // NCS drop default statement
        description
          "Discard or forward after the number of learned MAC addresses reaches the maximum number.";
      }
      leaf alarm {
        type ncs_template_mac-enable-status;
        // NCS drop default statement
        description
          "Whether an alarm is generated after the number of learned MAC addresses reaches the maximum number.";
      }
      leaf up-threshold {
        // NCS drop when statement
        type string;
        // NCS drop must statement
        description
          "Upper limit for the number of MAC addresses.";
      }
      leaf down-threshold {
        // NCS drop when statement
        type string;
        // NCS drop must statement
        description
          "Lower limit for the number of MAC addresses.";
      }
    }
  }
  augment "/ncs:devices/ncs:device/ncs:live-status/vlan:vlan/vlan:vlans/vlan:vlan" {
    description
      "MAC attribute of a VLAN.";
    container mac-addresss {
      tailf:ncs-device-type "netconf";
      tailf:display-when "not(../../../../../ncs:module) or ../../../../../ncs:module[ncs:name='huawei-mac'] or (../../../../../ncs:live-status-protocol[not(ncs:capability)]) or (../../../../../ncs:live-status-protocol/ncs:capability/ncs:module[.='huawei-mac'])";
      description
        "List of VLAN forwarding table.";
      list mac-address {
        // NCS drop must statement
        key "address";
        description
          "Configure VLAN forwarding entry.";
        leaf address {
          type pub-type:live_ncs_mac-address;
          description
            "MAC address.";
        }
        choice mac-type {
          // NCS drop mandatory statement
          description
            "MAC type.";
          case black-hole {
            description
              "Blackhole type.";
            leaf black-hole {
              type empty;
              // NCS drop mandatory statement
              description
                "Blackhole type.";
            }
          }
          case static {
            description
              "Static type.";
            leaf out-interface-name {
              type leafref {
                path "/ncs:devices/ncs:device/ncs:live-status/ifm:ifm/ifm:interfaces/ifm:interface/ifm:name" {
                  tailf:xpath-root 3;
                }
              }
              // NCS drop must statement
              // NCS drop mandatory statement
              description
                "Outbound interface name. The to-be-delivered VLAN ID must be the default VLAN ID, the VLAN ID in the outer VLAN tag, the post-mapping VLAN ID, or a VLAN ID in the list of allowed VLANs on the specified interface.";
            }
            leaf ce-default {
              type empty;
              // NCS drop must statement
              description
                "CE default VLAN. If the to-be-delivered VLAN ID is neither the VLAN ID in the outer VLAN tag to be added to a tagged packet, nor the post-mapping VLAN ID, nor a VLAN ID in the list of allowed VLANs on the specified interface, ce-default is mandatory.";
            }
            leaf ce-vlan-id {
              type uint16 {
                range "1..4094";
              }
              // NCS drop must statement
              description
                "CE VLAN ID. The CE VLAN ID must exist in the list of VLAN IDs that can be received by adding the outer VLAN tag carrying the to-be-delivered VLAN ID, or in the list of VLAN IDs that can be mapped to the to-be-delivered VLAN ID on the specified interface. If the to-be-delivered VLAN ID is neither the default VLAN ID, nor the VLAN ID in the outer VLAN tag to be added to an untagged packet, nor a VLAN ID in the list of allowed VLANs on the specified interface, CE VLAN ID is mandatory.";
            }
          }
        }
      }
    }
    container mac-limit {
      tailf:ncs-device-type "netconf";
      tailf:display-when "not(../../../../../ncs:module) or ../../../../../ncs:module[ncs:name='huawei-mac'] or (../../../../../ncs:live-status-protocol[not(ncs:capability)]) or (../../../../../ncs:live-status-protocol/ncs:capability/ncs:module[.='huawei-mac'])";
      // NCS drop when statement
      presence "MAC address limit.";
      description
        "Configure MAC address limit.";
      leaf maximum {
        type uint32 {
          range "0..2048000";
        }
        // NCS drop must statement
        // NCS drop mandatory statement
        description
          "Maximum number of MAC addresses that can be learned. The value 0 means unlimited.";
      }
      leaf rate {
        type uint16 {
          range "0..1000";
        }
        units "ms";
        // NCS drop must statement
        // NCS drop default statement
        description
          "Interval at which MAC addresses are learned. The value 0 indicates that no rate limit is set.";
      }
      leaf action {
        type live_ncs_mac-limit-forward;
        // NCS drop default statement
        description
          "Discard or forward after the number of learned MAC addresses reaches the maximum number.";
      }
      leaf alarm {
        type live_ncs_mac-enable-status;
        // NCS drop default statement
        description
          "Whether an alarm is generated after the number of learned MAC addresses reaches the maximum number.";
      }
      leaf up-threshold {
        // NCS drop when statement
        type uint8 {
          range "1..100";
        }
        // NCS drop must statement
        description
          "Upper limit for the number of MAC addresses.";
      }
      leaf down-threshold {
        // NCS drop when statement
        type uint8 {
          range "1..100";
        }
        // NCS drop must statement
        description
          "Lower limit for the number of MAC addresses.";
      }
    }
  }
  augment "/ncs:devices/ncs:device/ncs:config/vlan:vlan/vlan:vlans/vlan:vlan" {
    description
      "MAC attribute of a VLAN.";
    container mac-addresss {
      tailf:ncs-device-type "netconf";
      tailf:display-when "not(../../../../../ncs:module) or ../../../../../ncs:module[ncs:name='huawei-mac']";
      description
        "List of VLAN forwarding table.";
      list mac-address {
        must 'not (mac:ce-default and mac:ce-vlan-id)' {
          tailf:xpath-root 3;
        }
        key "address";
        description
          "Configure VLAN forwarding entry.";
        leaf address {
          type pub-type:mac-address {
            pattern '[0-9a-f][0|2|4|6|8|a|c|e][0-9a-f]{2}(-[0-9a-f]{4}){2}';
          }
          description
            "MAC address.";
        }
        choice mac-type {
          mandatory true;
          description
            "MAC type.";
          case black-hole {
            description
              "Blackhole type.";
            leaf black-hole {
              type empty;
              mandatory true;
              description
                "Blackhole type.";
            }
          }
          case static {
            description
              "Static type.";
            leaf out-interface-name {
              type leafref {
                path "/ncs:devices/ncs:device/ncs:config/ifm:ifm/ifm:interfaces/ifm:interface/ifm:name" {
                  tailf:xpath-root 3;
                }
              }
              must '/ifm:ifm/ifm:interfaces/ifm:interface[ifm:name=current()]/ethernet:ethernet/ethernet:main-interface/ethernet:l2-attribute/ethernet:pvid=current()/../../../vlan:id or /ifm:ifm/ifm:interfaces/ifm:interface[ifm:name=current()]/ethernet:ethernet/ethernet:main-interface/ethernet:l2-attribute/ethernet:vlan-stackings/ethernet:vlan-stacking[ethernet:stacking-vlan=current()/../../../vlan:id] or /ifm:ifm/ifm:interfaces/ifm:interface[ifm:name=current()]/ethernet:ethernet/ethernet:main-interface/ethernet:l2-attribute/ethernet:vlan-mappings/ethernet:vlan-mapping[ethernet:mapping-vlan=current()/../../../vlan:id] or /ifm:ifm/ifm:interfaces/ifm:interface[ifm:name=current()]/ethernet:ethernet/ethernet:main-interface/ethernet:l2-attribute/ethernet:trunk-vlans' {
                tailf:xpath-root 3;
              }
              mandatory true;
              description
                "Outbound interface name. The to-be-delivered VLAN ID must be the default VLAN ID, the VLAN ID in the outer VLAN tag, the post-mapping VLAN ID, or a VLAN ID in the list of allowed VLANs on the specified interface.";
            }
            leaf ce-default {
              type empty;
              must '/ifm:ifm/ifm:interfaces/ifm:interface[ifm:name=current()/../out-interface-name]/ethernet:ethernet/ethernet:main-interface/ethernet:l2-attribute/ethernet:vlan-stackings/ethernet:vlan-stacking[ethernet:stacking-vlan=current()/../../../vlan:id]/ethernet:ce-default' {
                tailf:xpath-root 3;
              }
              description
                "CE default VLAN. If the to-be-delivered VLAN ID is neither the VLAN ID in the outer VLAN tag to be added to a tagged packet, nor the post-mapping VLAN ID, nor a VLAN ID in the list of allowed VLANs on the specified interface, ce-default is mandatory.";
            }
            leaf ce-vlan-id {
              type uint16 {
                range "1..4094";
              }
              must '/ifm:ifm/ifm:interfaces/ifm:interface[ifm:name=current()/../out-interface-name]/ethernet:ethernet/ethernet:main-interface/ethernet:l2-attribute/ethernet:vlan-stackings/ethernet:vlan-stacking[ethernet:stacking-vlan=current()/../../../vlan:id]/ethernet:trans-vlans or /ifm:ifm/ifm:interfaces/ifm:interface[ifm:name=current()/../out-interface-name]/ethernet:ethernet/ethernet:main-interface/ethernet:l2-attribute/ethernet:vlan-mappings/ethernet:vlan-mapping[ethernet:mapping-vlan=current()/../../../vlan:id]/ethernet:trans-vlans' {
                tailf:xpath-root 3;
              }
              description
                "CE VLAN ID. The CE VLAN ID must exist in the list of VLAN IDs that can be received by adding the outer VLAN tag carrying the to-be-delivered VLAN ID, or in the list of VLAN IDs that can be mapped to the to-be-delivered VLAN ID on the specified interface. If the to-be-delivered VLAN ID is neither the default VLAN ID, nor the VLAN ID in the outer VLAN tag to be added to an untagged packet, nor a VLAN ID in the list of allowed VLANs on the specified interface, CE VLAN ID is mandatory.";
            }
          }
        }
      }
    }
    container mac-limit {
      tailf:ncs-device-type "netconf";
      tailf:display-when "not(../../../../../ncs:module) or ../../../../../ncs:module[ncs:name='huawei-mac']";
      when "../vlan:type!='super'" {
        tailf:xpath-root 3;
      }
      presence "MAC address limit.";
      description
        "Configure MAC address limit.";
      leaf maximum {
        type uint32 {
          range "0..2048000";
        }
        must 'not(../rate=0) or (../rate=0 and ../maximum>0)' {
          tailf:xpath-root 3;
        }
        mandatory true;
        description
          "Maximum number of MAC addresses that can be learned. The value 0 means unlimited.";
      }
      leaf rate {
        type uint16 {
          range "0..1000";
        }
        units "ms";
        must 'not(../maximum=0) or (../maximum=0 and ../rate>0)' {
          tailf:xpath-root 3;
        }
        default "0";
        description
          "Interval at which MAC addresses are learned. The value 0 indicates that no rate limit is set.";
      }
      leaf action {
        type mac-limit-forward;
        default "discard";
        description
          "Discard or forward after the number of learned MAC addresses reaches the maximum number.";
      }
      leaf alarm {
        type mac-enable-status;
        default "enable";
        description
          "Whether an alarm is generated after the number of learned MAC addresses reaches the maximum number.";
      }
      leaf up-threshold {
        when '../maximum>0' {
          tailf:xpath-root 3;
        }
        type uint8 {
          range "1..100";
        }
        must '(not(../up-threshold) and not(../down-threshold)) or ((../up-threshold and ../down-threshold) and (../up-threshold>=../down-threshold))' {
          tailf:xpath-root 3;
        }
        description
          "Upper limit for the number of MAC addresses.";
      }
      leaf down-threshold {
        when '../maximum>0' {
          tailf:xpath-root 3;
        }
        type uint8 {
          range "1..100";
        }
        must '(not(../up-threshold) and not(../down-threshold)) or ((../up-threshold and ../down-threshold) and (../up-threshold>=../down-threshold))' {
          tailf:xpath-root 3;
        }
        description
          "Lower limit for the number of MAC addresses.";
      }
    }
  }
  augment "/ncs:devices/ncs:template/ncs:ned-id/ncs:config/bd:bd/bd:instances/bd:instance" {
    description
      "MAC attribute of a BD.";
    container mac-addresss {
      description
        "List of BD forwarding entries.";
      list mac-address {
        // NCS patched for predictable order
        ordered-by user;
        key "address";
        description
          "Configure BD forwarding entry.";
        leaf address {
          type pub-type:ncs_template_mac-address;
          description
            "MAC address. Only support unicast MAC address.";
        }
        choice mac-type {
          // NCS drop mandatory statement
          description
            "MAC type, black hole or static.";
          case black-hole {
            description
              "Blackhole type.";
            leaf black-hole {
              type empty;
              // NCS drop mandatory statement
              description
                "Blackhole type.";
            }
          }
          case static {
            description
              "Static type.";
            choice out-interface-type {
              // NCS drop mandatory statement
              description
                "Outbound type.";
              case ac {
                description
                  "AC type.";
                leaf out-interface-name {
                  type string;
                  // NCS drop must statement
                  // NCS drop mandatory statement
                  description
                    "Outbound interface name.";
                }
                leaf untag {
                  // NCS drop when statement
                  type empty;
                  // NCS drop mandatory statement
                  description
                    "Packets without VLAN tag.";
                }
                leaf pe-default {
                  // NCS drop when statement
                  type empty;
                  // NCS drop mandatory statement
                  description
                    "PE default VLAN.";
                }
                leaf vid {
                  // NCS drop when statement
                  type string;
                  // NCS drop mandatory statement
                  description
                    "Outer VLAN tag.";
                }
                leaf ce-default {
                  // NCS drop when statement
                  type empty;
                  // NCS drop mandatory statement
                  description
                    "CE default VLAN.";
                }
                leaf ce-vid {
                  // NCS drop when statement
                  type string;
                  // NCS drop mandatory statement
                  description
                    "Inner VLAN tag.";
                }
              }
              case tunnel {
                description
                  "Tunnel type.";
                leaf source-ip {
                  type string;
                  // NCS drop mandatory statement
                  description
                    "Source IP address.";
                }
                leaf peer-ip {
                  type string;
                  // NCS drop mandatory statement
                  description
                    "Peer IP address.";
                }
                leaf vni {
                  type string;
                  // NCS drop mandatory statement
                  description
                    "VXLAN network identifier.";
                }
              }
            }
          }
        }
      }
    }
    container mac-limit {
      presence "BD MAC address limit.";
      description
        "Configure BD MAC address limit.";
      leaf maximum {
        type string;
        // NCS drop must statement
        // NCS drop mandatory statement
        description
          "Maximum number of MAC addresses that can be learned. The value 0 means unlimited.";
      }
      leaf rate {
        type string;
        units "ms";
        // NCS drop must statement
        // NCS drop default statement
        description
          "Interval at which MAC addresses are learned. The value 0 indicates that no rate limit is set.";
      }
      leaf action {
        type ncs_template_mac-limit-forward;
        // NCS drop default statement
        description
          "Discard or forward after the number of learned MAC addresses reaches the maximum number.";
      }
      leaf up-threshold {
        // NCS drop when statement
        type string;
        // NCS drop must statement
        description
          "Upper limit for the number of MAC addresses.";
      }
      leaf down-threshold {
        // NCS drop when statement
        type string;
        // NCS drop must statement
        description
          "Lower limit for the number of MAC addresses.";
      }
    }
  }
  augment "/ncs:devices/ncs:device/ncs:live-status/bd:bd/bd:instances/bd:instance" {
    description
      "MAC attribute of a BD.";
    container mac-addresss {
      tailf:ncs-device-type "netconf";
      tailf:display-when "not(../../../../../ncs:module) or ../../../../../ncs:module[ncs:name='huawei-mac'] or (../../../../../ncs:live-status-protocol[not(ncs:capability)]) or (../../../../../ncs:live-status-protocol/ncs:capability/ncs:module[.='huawei-mac'])";
      description
        "List of BD forwarding entries.";
      list mac-address {
        key "address";
        description
          "Configure BD forwarding entry.";
        leaf address {
          type pub-type:live_ncs_mac-address;
          description
            "MAC address. Only support unicast MAC address.";
        }
        choice mac-type {
          // NCS drop mandatory statement
          description
            "MAC type, black hole or static.";
          case black-hole {
            description
              "Blackhole type.";
            leaf black-hole {
              type empty;
              // NCS drop mandatory statement
              description
                "Blackhole type.";
            }
          }
          case static {
            description
              "Static type.";
            choice out-interface-type {
              // NCS drop mandatory statement
              description
                "Outbound type.";
              case ac {
                description
                  "AC type.";
                leaf out-interface-name {
                  type leafref {
                    path "/ncs:devices/ncs:device/ncs:live-status/bd:bd/bd:instances/bd:instance/bd:service-points/bd:service-point/bd:interface-name" {
                      tailf:xpath-root 3;
                    }
                  }
                  // NCS drop must statement
                  // NCS drop mandatory statement
                  description
                    "Outbound interface name.";
                }
                leaf untag {
                  // NCS drop when statement
                  type empty;
                  // NCS drop mandatory statement
                  description
                    "Packets without VLAN tag.";
                }
                leaf pe-default {
                  // NCS drop when statement
                  type empty;
                  // NCS drop mandatory statement
                  description
                    "PE default VLAN.";
                }
                leaf vid {
                  // NCS drop when statement
                  type uint16 {
                    range "1..4094";
                  }
                  // NCS drop mandatory statement
                  description
                    "Outer VLAN tag.";
                }
                leaf ce-default {
                  // NCS drop when statement
                  type empty;
                  // NCS drop mandatory statement
                  description
                    "CE default VLAN.";
                }
                leaf ce-vid {
                  // NCS drop when statement
                  type uint16 {
                    range "1..4094";
                  }
                  // NCS drop mandatory statement
                  description
                    "Inner VLAN tag.";
                }
              }
              case tunnel {
                description
                  "Tunnel type.";
                leaf source-ip {
                  type inet:ipv4-address-no-zone;
                  // NCS drop mandatory statement
                  description
                    "Source IP address.";
                }
                leaf peer-ip {
                  type inet:ipv4-address-no-zone;
                  // NCS drop mandatory statement
                  description
                    "Peer IP address.";
                }
                leaf vni {
                  type uint32 {
                    range "1..16777215";
                  }
                  // NCS drop mandatory statement
                  description
                    "VXLAN network identifier.";
                }
              }
            }
          }
        }
      }
    }
    container mac-limit {
      tailf:ncs-device-type "netconf";
      tailf:display-when "not(../../../../../ncs:module) or ../../../../../ncs:module[ncs:name='huawei-mac'] or (../../../../../ncs:live-status-protocol[not(ncs:capability)]) or (../../../../../ncs:live-status-protocol/ncs:capability/ncs:module[.='huawei-mac'])";
      presence "BD MAC address limit.";
      description
        "Configure BD MAC address limit.";
      leaf maximum {
        type uint32 {
          range "0..2048000";
        }
        // NCS drop must statement
        // NCS drop mandatory statement
        description
          "Maximum number of MAC addresses that can be learned. The value 0 means unlimited.";
      }
      leaf rate {
        type uint16 {
          range "0..1000";
        }
        units "ms";
        // NCS drop must statement
        // NCS drop default statement
        description
          "Interval at which MAC addresses are learned. The value 0 indicates that no rate limit is set.";
      }
      leaf action {
        type live_ncs_mac-limit-forward;
        // NCS drop default statement
        description
          "Discard or forward after the number of learned MAC addresses reaches the maximum number.";
      }
      leaf up-threshold {
        // NCS drop when statement
        type uint8 {
          range "1..100";
        }
        // NCS drop must statement
        description
          "Upper limit for the number of MAC addresses.";
      }
      leaf down-threshold {
        // NCS drop when statement
        type uint8 {
          range "1..100";
        }
        // NCS drop must statement
        description
          "Lower limit for the number of MAC addresses.";
      }
    }
  }
  augment "/ncs:devices/ncs:device/ncs:config/bd:bd/bd:instances/bd:instance" {
    description
      "MAC attribute of a BD.";
    container mac-addresss {
      tailf:ncs-device-type "netconf";
      tailf:display-when "not(../../../../../ncs:module) or ../../../../../ncs:module[ncs:name='huawei-mac']";
      description
        "List of BD forwarding entries.";
      list mac-address {
        key "address";
        description
          "Configure BD forwarding entry.";
        leaf address {
          type pub-type:mac-address {
            pattern '[0-9a-f][0|2|4|6|8|a|c|e][0-9a-f]{2}(-[0-9a-f]{4}){2}';
          }
          description
            "MAC address. Only support unicast MAC address.";
        }
        choice mac-type {
          mandatory true;
          description
            "MAC type, black hole or static.";
          case black-hole {
            description
              "Blackhole type.";
            leaf black-hole {
              type empty;
              mandatory true;
              description
                "Blackhole type.";
            }
          }
          case static {
            description
              "Static type.";
            choice out-interface-type {
              mandatory true;
              description
                "Outbound type.";
              case ac {
                description
                  "AC type.";
                leaf out-interface-name {
                  type leafref {
                    path "/ncs:devices/ncs:device/ncs:config/bd:bd/bd:instances/bd:instance/bd:service-points/bd:service-point/bd:interface-name" {
                      tailf:xpath-root 3;
                    }
                  }
                  must '/ifm:ifm/ifm:interfaces/ifm:interface[ifm:name=current()]/ethernet:ethernet/ethernet:l2-sub-interface/ethernet:untag or /ifm:ifm/ifm:interfaces/ifm:interface[ifm:name=current()]/ethernet:ethernet/ethernet:l2-sub-interface/ethernet:default or /ifm:ifm/ifm:interfaces/ifm:interface[ifm:name=current()]/ethernet:ethernet/ethernet:l2-sub-interface/ethernet:dot1q/ethernet:vlans/ethernet:vlan-list or /ifm:ifm/ifm:interfaces/ifm:interface[ifm:name=current()]/ethernet:ethernet/ethernet:l2-sub-interface/ethernet:dot1q/ethernet:policy-vlans/ethernet:policy-vlan or /ifm:ifm/ifm:interfaces/ifm:interface[ifm:name=current()]/ethernet:ethernet/ethernet:l2-sub-interface/ethernet:qinqs/ethernet:qinq-vids/ethernet:qinq-vid or /ifm:ifm/ifm:interfaces/ifm:interface[ifm:name=current()]/ethernet:ethernet/ethernet:l2-sub-interface/ethernet:qinqs/ethernet:qinq-vid-ce-default/ethernet:pe-vlan-list' {
                    tailf:xpath-root 3;
                  }
                  mandatory true;
                  description
                    "Outbound interface name.";
                }
                leaf untag {
                  when '/ifm:ifm/ifm:interfaces/ifm:interface[ifm:name=current()/../out-interface-name]/ethernet:ethernet/ethernet:l2-sub-interface/ethernet:untag' {
                    tailf:xpath-root 3;
                  }
                  type empty;
                  mandatory true;
                  description
                    "Packets without VLAN tag.";
                }
                leaf pe-default {
                  when '/ifm:ifm/ifm:interfaces/ifm:interface[ifm:name=current()/../out-interface-name]/ethernet:ethernet/ethernet:l2-sub-interface/ethernet:default' {
                    tailf:xpath-root 3;
                  }
                  type empty;
                  mandatory true;
                  description
                    "PE default VLAN.";
                }
                leaf vid {
                  when '(/ifm:ifm/ifm:interfaces/ifm:interface[ifm:name=current()/../out-interface-name]/ethernet:ethernet/ethernet:l2-sub-interface/ethernet:dot1q or /ifm:ifm/ifm:interfaces/ifm:interface[ifm:name=current()/../out-interface-name]/ethernet:ethernet/ethernet:l2-sub-interface/ethernet:qinqs)' {
                    tailf:xpath-root 3;
                  }
                  type uint16 {
                    range "1..4094";
                  }
                  mandatory true;
                  description
                    "Outer VLAN tag.";
                }
                leaf ce-default {
                  when '/ifm:ifm/ifm:interfaces/ifm:interface[ifm:name=current()/../out-interface-name]/ethernet:ethernet/ethernet:l2-sub-interface/ethernet:qinqs/ethernet:qinq-vid-ce-default/ethernet:pe-vlan-list' {
                    tailf:xpath-root 3;
                  }
                  type empty;
                  mandatory true;
                  description
                    "CE default VLAN.";
                }
                leaf ce-vid {
                  when '/ifm:ifm/ifm:interfaces/ifm:interface[ifm:name=current()/../out-interface-name]/ethernet:ethernet/ethernet:l2-sub-interface/ethernet:qinqs/ethernet:qinq-vids/ethernet:qinq-vid[ethernet:pe-vlan-id=current()/../vid]/ethernet:ce-vlan-list' {
                    tailf:xpath-root 3;
                  }
                  type uint16 {
                    range "1..4094";
                  }
                  mandatory true;
                  description
                    "Inner VLAN tag.";
                }
              }
              case tunnel {
                description
                  "Tunnel type.";
                leaf source-ip {
                  type inet:ipv4-address-no-zone;
                  mandatory true;
                  description
                    "Source IP address.";
                }
                leaf peer-ip {
                  type inet:ipv4-address-no-zone;
                  mandatory true;
                  description
                    "Peer IP address.";
                }
                leaf vni {
                  type uint32 {
                    range "1..16777215";
                  }
                  mandatory true;
                  description
                    "VXLAN network identifier.";
                }
              }
            }
          }
        }
      }
    }
    container mac-limit {
      tailf:ncs-device-type "netconf";
      tailf:display-when "not(../../../../../ncs:module) or ../../../../../ncs:module[ncs:name='huawei-mac']";
      presence "BD MAC address limit.";
      description
        "Configure BD MAC address limit.";
      leaf maximum {
        type uint32 {
          range "0..2048000";
        }
        must 'not(../rate=0) or (../maximum>0)' {
          tailf:xpath-root 3;
        }
        mandatory true;
        description
          "Maximum number of MAC addresses that can be learned. The value 0 means unlimited.";
      }
      leaf rate {
        type uint16 {
          range "0..1000";
        }
        units "ms";
        must 'not(../maximum=0) or (../rate>0)' {
          tailf:xpath-root 3;
        }
        default "0";
        description
          "Interval at which MAC addresses are learned. The value 0 indicates that no rate limit is set.";
      }
      leaf action {
        type mac-limit-forward;
        default "discard";
        description
          "Discard or forward after the number of learned MAC addresses reaches the maximum number.";
      }
      leaf up-threshold {
        when '../maximum>0' {
          tailf:xpath-root 3;
        }
        type uint8 {
          range "1..100";
        }
        must '(not(../up-threshold) and not(../down-threshold)) or ((../up-threshold and ../down-threshold) and (../up-threshold>=../down-threshold))' {
          tailf:xpath-root 3;
        }
        description
          "Upper limit for the number of MAC addresses.";
      }
      leaf down-threshold {
        when '../maximum>0' {
          tailf:xpath-root 3;
        }
        type uint8 {
          range "1..100";
        }
        must '(not(../up-threshold) and not(../down-threshold)) or ((../up-threshold and ../down-threshold) and (../up-threshold>=../down-threshold))' {
          tailf:xpath-root 3;
        }
        description
          "Lower limit for the number of MAC addresses.";
      }
    }
  }
  augment "/ncs:devices/ncs:template/ncs:ned-id/ncs:config/l2vpn:l2vpn/l2vpn:instances/l2vpn:instance/l2vpn:vpls" {
    description
      "MAC attribute on VSI.";
    container mac {
      description
        "Configure MAC parameters on VSI.";
      container mac-addresss {
        description
          "Configure VSI MAC address table.";
        container qualifys {
          description
            "List of qualify MAC address table.";
          list qualify {
            // NCS patched for predictable order
            ordered-by user;
            // NCS drop must statement
            key "vlan-id address";
            description
              "Configure qualify MAC address entry.";
            leaf vlan-id {
              type string;
              description
                "VLAN ID.";
            }
            leaf address {
              type pub-type:ncs_template_mac-address;
              description
                "MAC address.";
            }
            choice mac-type {
              // NCS drop mandatory statement
              description
                "MAC type.";
              case black-hole {
                description
                  "Blackhole type.";
                leaf black-hole {
                  type empty;
                  // NCS drop mandatory statement
                  description
                    "Blackhole type.";
                }
              }
              case static {
                description
                  "Static type.";
                choice out-bound-type {
                  // NCS drop mandatory statement
                  description
                    "Outbound type.";
                  case ac {
                    description
                      "AC type.";
                    leaf out-if-name {
                      type string;
                      // NCS drop must statement
                      // NCS drop mandatory statement
                      description
                        "Outbound interface name.";
                    }
                  }
                  case pw {
                    description
                      "PW type.";
                    leaf pw-id {
                      type string;
                      // NCS drop mandatory statement
                      description
                        "PW ID.";
                    }
                    leaf peer-ip {
                      type string;
                      // NCS drop mandatory statement
                      description
                        "Peer IP address.";
                    }
                  }
                }
              }
            }
          }
        }
        container unqualifys {
          description
            "List of unqualify MAC address table.";
          list unqualify {
            // NCS patched for predictable order
            ordered-by user;
            // NCS drop must statement
            key "address";
            description
              "Configure unqualify MAC address entry.";
            leaf address {
              type pub-type:ncs_template_mac-address;
              description
                "MAC address.";
            }
            choice mac-type {
              // NCS drop mandatory statement
              description
                "MAC type.";
              case black-hole {
                description
                  "Blackhole type.";
                leaf black-hole {
                  type empty;
                  // NCS drop mandatory statement
                  description
                    "Blackhole type.";
                }
              }
              case static {
                description
                  "Static.";
                choice out-bound-type {
                  // NCS drop mandatory statement
                  description
                    "Outbound type.";
                  case ac {
                    description
                      "AC type.";
                    leaf out-if-name {
                      type string;
                      // NCS drop must statement
                      // NCS drop mandatory statement
                      description
                        "Outbound interface name.";
                    }
                    leaf pe-vid {
                      type string;
                      // NCS drop must statement
                      description
                        "Outer VLAN tag.";
                    }
                    leaf ce-vid {
                      type string;
                      // NCS drop must statement
                      description
                        "Inner VLAN tag. If ce-vid exists in qinq-vid, ce-vid is mandatory.";
                    }
                    leaf ce-any {
                      type empty;
                      description
                        "Any Inner VLAN ID. If pe-vid exists in pe-VLAN-list, ce-any is mandatory.";
                    }
                    leaf vlanif-name {
                      type string;
                      // NCS drop must statement
                      description
                        "VLANIF interface. The VLANIF ID must exist in pvid or trunk-VLANs.";
                    }
                  }
                  case pw {
                    description
                      "PW type.";
                    leaf pw-id {
                      type string;
                      // NCS drop mandatory statement
                      description
                        "PW ID.";
                    }
                    leaf peer-ip {
                      type string;
                      // NCS drop mandatory statement
                      description
                        "Peer IP address.";
                    }
                  }
                }
              }
            }
          }
        }
      }
      container suppression {
        description
          "Configure VSI traffic suppression list.";
        leaf inbound {
          type empty;
          // NCS drop must statement
          description
            "Inbound suppression.";
        }
        leaf outbound {
          type empty;
          // NCS drop must statement
          description
            "Outbound suppression.";
        }
      }
      container uni-suppressions {
        description
          "List of VSI traffic suppression.";
        list uni-suppression {
          // NCS patched for predictable order
          ordered-by user;
          // NCS drop must statement
          key "type direction";
          description
            "Configure VSI traffic suppression.";
          leaf type {
            type ncs_template_suppress-type;
            description
              "Traffic suppression type.";
          }
          leaf direction {
            type ncs_template_vsi-direction-type;
            description
              "Suppression direction.";
          }
          leaf cir {
            type string;
            units "kbit/s";
            // NCS drop mandatory statement
            description
              "CIR value.";
          }
          leaf cbs {
            type string;
            units "Byte";
            ext:dynamic-default {
              ext:default-value "../cir*(1500/8)" {
                // NCS drop when statement
                description
                  "When cir less than 100000kbit/s,the default value is cir * (1500/8)Byte.";
              }
              ext:default-value "18750000" {
                // NCS drop when statement
                description
                  "When cir more than 100000kbit/s,the default value is 100000 * (1500/8)Byte.";
              }
            }
            description
              "CBS value. If user does not specify this value, the system will calc a value by CIR value.";
          }
        }
      }
      container mac-limit {
        // NCS drop must statement
        presence "VSI MAC address limit.";
        description
          "Enable/disable to limit VSI MAC address.";
        leaf maximum {
          type string;
          // NCS drop must statement
          // NCS drop mandatory statement
          description
            "Maximum number of MAC addresses that can be learned in a VSI. The value 0 means unlimited.";
        }
        leaf rate {
          type string;
          units "ms";
          // NCS drop must statement
          // NCS drop default statement
          description
            "Interval at which MAC addresses are learned in a VSI. The value 0 indicates that no rate limit is set.";
        }
        leaf action {
          type ncs_template_mac-limit-forward;
          // NCS drop default statement
          description
            "Discard or forward after the number of learned MAC addresses reaches the maximum number in a VSI.";
        }
        leaf alarm {
          type ncs_template_mac-enable-status;
          // NCS drop default statement
          description
            "Whether an alarm is generated after the number of learned MAC addresses reaches the maximum number in a VSI.";
        }
        leaf up-threshold {
          // NCS drop when statement
          type string;
          // NCS drop must statement
          description
            "Upper limit for the number of MAC addresses.";
        }
        leaf down-threshold {
          // NCS drop when statement
          type string;
          // NCS drop must statement
          description
            "Lower limit for the number of MAC addresses.";
        }
      }
    }
  }
  augment "/ncs:devices/ncs:device/ncs:live-status/l2vpn:l2vpn/l2vpn:instances/l2vpn:instance/l2vpn:vpls" {
    description
      "MAC attribute on VSI.";
    container mac {
      tailf:ncs-device-type "netconf";
      tailf:display-when "not(../../../../../../ncs:module) or ../../../../../../ncs:module[ncs:name='huawei-mac'] or (../../../../../../ncs:live-status-protocol[not(ncs:capability)]) or (../../../../../../ncs:live-status-protocol/ncs:capability/ncs:module[.='huawei-mac'])";
      description
        "Configure MAC parameters on VSI.";
      container mac-addresss {
        description
          "Configure VSI MAC address table.";
        container qualifys {
          description
            "List of qualify MAC address table.";
          list qualify {
            // NCS drop must statement
            key "vlan-id address";
            description
              "Configure qualify MAC address entry.";
            leaf vlan-id {
              type uint16 {
                range "1..4094";
              }
              description
                "VLAN ID.";
            }
            leaf address {
              type pub-type:live_ncs_mac-address;
              description
                "MAC address.";
            }
            choice mac-type {
              // NCS drop mandatory statement
              description
                "MAC type.";
              case black-hole {
                description
                  "Blackhole type.";
                leaf black-hole {
                  type empty;
                  // NCS drop mandatory statement
                  description
                    "Blackhole type.";
                }
              }
              case static {
                description
                  "Static type.";
                choice out-bound-type {
                  // NCS drop mandatory statement
                  description
                    "Outbound type.";
                  case ac {
                    description
                      "AC type.";
                    leaf out-if-name {
                      type leafref {
                        path "/ncs:devices/ncs:device/ncs:live-status/l2vpn:l2vpn/l2vpn:instances/l2vpn:instance/l2vpn:vpls/l2vpn:acs/l2vpn:ac/l2vpn:interface-name" {
                          tailf:xpath-root 3;
                        }
                      }
                      // NCS drop must statement
                      // NCS drop mandatory statement
                      description
                        "Outbound interface name.";
                    }
                  }
                  case pw {
                    description
                      "PW type.";
                    leaf pw-id {
                      type leafref {
                        path "../../../../../l2vpn:ldp-signaling/l2vpn:pws/l2vpn:pw/l2vpn:negotiation-vc-id";
                      }
                      // NCS drop mandatory statement
                      description
                        "PW ID.";
                    }
                    leaf peer-ip {
                      type leafref {
                        path "../../../../../l2vpn:ldp-signaling/l2vpn:pws/l2vpn:pw/l2vpn:peer-ip";
                      }
                      // NCS drop mandatory statement
                      description
                        "Peer IP address.";
                    }
                  }
                }
              }
            }
          }
        }
        container unqualifys {
          description
            "List of unqualify MAC address table.";
          list unqualify {
            // NCS drop must statement
            key "address";
            description
              "Configure unqualify MAC address entry.";
            leaf address {
              type pub-type:live_ncs_mac-address;
              description
                "MAC address.";
            }
            choice mac-type {
              // NCS drop mandatory statement
              description
                "MAC type.";
              case black-hole {
                description
                  "Blackhole type.";
                leaf black-hole {
                  type empty;
                  // NCS drop mandatory statement
                  description
                    "Blackhole type.";
                }
              }
              case static {
                description
                  "Static.";
                choice out-bound-type {
                  // NCS drop mandatory statement
                  description
                    "Outbound type.";
                  case ac {
                    description
                      "AC type.";
                    leaf out-if-name {
                      type leafref {
                        path "/ncs:devices/ncs:device/ncs:live-status/ifm:ifm/ifm:interfaces/ifm:interface/ifm:name" {
                          tailf:xpath-root 3;
                        }
                      }
                      // NCS drop must statement
                      // NCS drop mandatory statement
                      description
                        "Outbound interface name.";
                    }
                    leaf pe-vid {
                      type uint16 {
                        range "0..4094";
                      }
                      // NCS drop must statement
                      description
                        "Outer VLAN tag.";
                    }
                    leaf ce-vid {
                      type uint16 {
                        range "0..4094";
                      }
                      // NCS drop must statement
                      description
                        "Inner VLAN tag. If ce-vid exists in qinq-vid, ce-vid is mandatory.";
                    }
                    leaf ce-any {
                      type empty;
                      description
                        "Any Inner VLAN ID. If pe-vid exists in pe-VLAN-list, ce-any is mandatory.";
                    }
                    leaf vlanif-name {
                      type leafref {
                        path "../../../../../l2vpn:acs/l2vpn:ac/l2vpn:interface-name";
                      }
                      // NCS drop must statement
                      description
                        "VLANIF interface. The VLANIF ID must exist in pvid or trunk-VLANs.";
                    }
                  }
                  case pw {
                    description
                      "PW type.";
                    leaf pw-id {
                      type leafref {
                        path "../../../../../l2vpn:ldp-signaling/l2vpn:pws/l2vpn:pw/l2vpn:negotiation-vc-id";
                      }
                      // NCS drop mandatory statement
                      description
                        "PW ID.";
                    }
                    leaf peer-ip {
                      type leafref {
                        path "../../../../../l2vpn:ldp-signaling/l2vpn:pws/l2vpn:pw/l2vpn:peer-ip";
                      }
                      // NCS drop mandatory statement
                      description
                        "Peer IP address.";
                    }
                  }
                }
              }
            }
          }
        }
      }
      container suppression {
        description
          "Configure VSI traffic suppression list.";
        leaf inbound {
          type empty;
          // NCS drop must statement
          description
            "Inbound suppression.";
        }
        leaf outbound {
          type empty;
          // NCS drop must statement
          description
            "Outbound suppression.";
        }
      }
      container uni-suppressions {
        description
          "List of VSI traffic suppression.";
        list uni-suppression {
          // NCS drop must statement
          key "type direction";
          description
            "Configure VSI traffic suppression.";
          leaf type {
            type live_ncs_suppress-type;
            description
              "Traffic suppression type.";
          }
          leaf direction {
            type live_ncs_vsi-direction-type;
            description
              "Suppression direction.";
          }
          leaf cir {
            type uint64 {
              range "0..4294967295";
            }
            units "kbit/s";
            // NCS drop mandatory statement
            description
              "CIR value.";
          }
          leaf cbs {
            type uint64 {
              range "0..4294967295";
            }
            units "Byte";
            ext:dynamic-default {
              ext:default-value "../cir*(1500/8)" {
                // NCS drop when statement
                description
                  "When cir less than 100000kbit/s,the default value is cir * (1500/8)Byte.";
              }
              ext:default-value "18750000" {
                // NCS drop when statement
                description
                  "When cir more than 100000kbit/s,the default value is 100000 * (1500/8)Byte.";
              }
            }
            description
              "CBS value. If user does not specify this value, the system will calc a value by CIR value.";
          }
        }
      }
      container mac-limit {
        // NCS drop must statement
        presence "VSI MAC address limit.";
        description
          "Enable/disable to limit VSI MAC address.";
        leaf maximum {
          type uint32 {
            range "0..2048000";
          }
          // NCS drop must statement
          // NCS drop mandatory statement
          description
            "Maximum number of MAC addresses that can be learned in a VSI. The value 0 means unlimited.";
        }
        leaf rate {
          type uint16 {
            range "0..1000";
          }
          units "ms";
          // NCS drop must statement
          // NCS drop default statement
          description
            "Interval at which MAC addresses are learned in a VSI. The value 0 indicates that no rate limit is set.";
        }
        leaf action {
          type live_ncs_mac-limit-forward;
          // NCS drop default statement
          description
            "Discard or forward after the number of learned MAC addresses reaches the maximum number in a VSI.";
        }
        leaf alarm {
          type live_ncs_mac-enable-status;
          // NCS drop default statement
          description
            "Whether an alarm is generated after the number of learned MAC addresses reaches the maximum number in a VSI.";
        }
        leaf up-threshold {
          // NCS drop when statement
          type uint8 {
            range "1..100";
          }
          // NCS drop must statement
          description
            "Upper limit for the number of MAC addresses.";
        }
        leaf down-threshold {
          // NCS drop when statement
          type uint8 {
            range "1..100";
          }
          // NCS drop must statement
          description
            "Lower limit for the number of MAC addresses.";
        }
      }
    }
  }
  augment "/ncs:devices/ncs:device/ncs:config/l2vpn:l2vpn/l2vpn:instances/l2vpn:instance/l2vpn:vpls" {
    description
      "MAC attribute on VSI.";
    container mac {
      tailf:ncs-device-type "netconf";
      tailf:display-when "not(../../../../../../ncs:module) or ../../../../../../ncs:module[ncs:name='huawei-mac']";
      description
        "Configure MAC parameters on VSI.";
      container mac-addresss {
        description
          "Configure VSI MAC address table.";
        container qualifys {
          description
            "List of qualify MAC address table.";
          list qualify {
            must "../../../../l2vpn:mac-learn-style='qualify'" {
              tailf:xpath-root 3;
            }
            key "vlan-id address";
            description
              "Configure qualify MAC address entry.";
            leaf vlan-id {
              type uint16 {
                range "1..4094";
              }
              description
                "VLAN ID.";
            }
            leaf address {
              type pub-type:mac-address {
                pattern '[0-9a-f][0|2|4|6|8|a|c|e][0-9a-f]{2}(-[0-9a-f]{4}){2}';
              }
              description
                "MAC address.";
            }
            choice mac-type {
              mandatory true;
              description
                "MAC type.";
              case black-hole {
                description
                  "Blackhole type.";
                leaf black-hole {
                  type empty;
                  mandatory true;
                  description
                    "Blackhole type.";
                }
              }
              case static {
                description
                  "Static type.";
                choice out-bound-type {
                  mandatory true;
                  description
                    "Outbound type.";
                  case ac {
                    description
                      "AC type.";
                    leaf out-if-name {
                      type leafref {
                        path "/ncs:devices/ncs:device/ncs:config/l2vpn:l2vpn/l2vpn:instances/l2vpn:instance/l2vpn:vpls/l2vpn:acs/l2vpn:ac/l2vpn:interface-name" {
                          tailf:xpath-root 3;
                        }
                      }
                      must '/ifm:ifm/ifm:interfaces/ifm:interface[ifm:name=current()]/ethernet:ethernet/ethernet:l3-sub-interface/ethernet:qinq-stacking' {
                        tailf:xpath-root 3;
                      }
                      mandatory true;
                      description
                        "Outbound interface name.";
                    }
                  }
                  case pw {
                    description
                      "PW type.";
                    leaf pw-id {
                      type leafref {
                        path "../../../../../l2vpn:ldp-signaling/l2vpn:pws/l2vpn:pw/l2vpn:negotiation-vc-id";
                      }
                      mandatory true;
                      description
                        "PW ID.";
                    }
                    leaf peer-ip {
                      type leafref {
                        path "../../../../../l2vpn:ldp-signaling/l2vpn:pws/l2vpn:pw/l2vpn:peer-ip";
                      }
                      mandatory true;
                      description
                        "Peer IP address.";
                    }
                  }
                }
              }
            }
          }
        }
        container unqualifys {
          description
            "List of unqualify MAC address table.";
          list unqualify {
            must "../../../../l2vpn:mac-learn-style='unqualify'" {
              tailf:xpath-root 3;
            }
            key "address";
            description
              "Configure unqualify MAC address entry.";
            leaf address {
              type pub-type:mac-address;
              description
                "MAC address.";
            }
            choice mac-type {
              mandatory true;
              description
                "MAC type.";
              case black-hole {
                description
                  "Blackhole type.";
                leaf black-hole {
                  type empty;
                  mandatory true;
                  description
                    "Blackhole type.";
                }
              }
              case static {
                description
                  "Static.";
                choice out-bound-type {
                  mandatory true;
                  description
                    "Outbound type.";
                  case ac {
                    description
                      "AC type.";
                    leaf out-if-name {
                      type leafref {
                        path "/ncs:devices/ncs:device/ncs:config/ifm:ifm/ifm:interfaces/ifm:interface/ifm:name" {
                          tailf:xpath-root 3;
                        }
                      }
                      must '((../vlanif-name and /ifm:ifm/ifm:interfaces/ifm:interface[ifm:name=current()]/ethernet:ethernet/ethernet:main-interface/ethernet:l2-attribute) or (../../../../../l2vpn:acs/l2vpn:ac[l2vpn:interface-name=current()]))' {
                        tailf:xpath-root 3;
                      }
                      mandatory true;
                      description
                        "Outbound interface name.";
                    }
                    leaf pe-vid {
                      type uint16 {
                        range "0..4094";
                      }
                      must '/ifm:ifm/ifm:interfaces/ifm:interface[ifm:name=current()/../out-if-name]/ethernet:ethernet/ethernet:l3-sub-interface/ethernet:qinq-termination/ethernet:qinq-vids/ethernet:qinq-vid or /ifm:ifm/ifm:interfaces/ifm:interface[ifm:name=current()/../out-if-name]/ethernet:ethernet/ethernet:l3-sub-interface/ethernet:dot1q-termination/ethernet:dot1q-vlans/ethernet:dot1q-vlans/ethernet:vlan-list or /ifm:ifm/ifm:interfaces/ifm:interface[ifm:name=current()/../out-if-name]/ethernet:ethernet/ethernet:l3-sub-interface/ethernet:dot1q-termination/ethernet:dot1q-vlans-policy/ethernet:policy-vlans/ethernet:policy-vlan or /ifm:ifm/ifm:interfaces/ifm:interface[ifm:name=current()/../out-if-name]/ethernet:ethernet/ethernet:l3-sub-interface/ethernet:qinq-stacking/ethernet:stacking-vid' {
                        tailf:xpath-root 3;
                      }
                      description
                        "Outer VLAN tag.";
                    }
                    leaf ce-vid {
                      type uint16 {
                        range "0..4094";
                      }
                      must '/ifm:ifm/ifm:interfaces/ifm:interface[ifm:name=current()/../out-if-name]/ethernet:ethernet/ethernet:l3-sub-interface/ethernet:qinq-termination/ethernet:qinq-vids/ethernet:qinq-vid' {
                        tailf:xpath-root 3;
                      }
                      description
                        "Inner VLAN tag. If ce-vid exists in qinq-vid, ce-vid is mandatory.";
                    }
                    leaf ce-any {
                      type empty;
                      description
                        "Any Inner VLAN ID. If pe-vid exists in pe-VLAN-list, ce-any is mandatory.";
                    }
                    leaf vlanif-name {
                      type leafref {
                        path "../../../../../l2vpn:acs/l2vpn:ac/l2vpn:interface-name";
                      }
                      must "/ifm:ifm/ifm:interfaces/ifm:interface[ifm:name=current()]/ifm:type='Vlanif' and (/ifm:ifm/ifm:interfaces/ifm:interface[ifm:name=current()/../out-if-name]/ethernet:ethernet/ethernet:main-interface/ethernet:l2-attribute/ethernet:pvid or /ifm:ifm/ifm:interfaces/ifm:interface[ifm:name=current()/../out-if-name]/ethernet:ethernet/ethernet:main-interface/ethernet:l2-attribute/ethernet:trunk-vlans)" {
                        tailf:xpath-root 3;
                      }
                      description
                        "VLANIF interface. The VLANIF ID must exist in pvid or trunk-VLANs.";
                    }
                  }
                  case pw {
                    description
                      "PW type.";
                    leaf pw-id {
                      type leafref {
                        path "../../../../../l2vpn:ldp-signaling/l2vpn:pws/l2vpn:pw/l2vpn:negotiation-vc-id";
                      }
                      mandatory true;
                      description
                        "PW ID.";
                    }
                    leaf peer-ip {
                      type leafref {
                        path "../../../../../l2vpn:ldp-signaling/l2vpn:pws/l2vpn:pw/l2vpn:peer-ip";
                      }
                      mandatory true;
                      description
                        "Peer IP address.";
                    }
                  }
                }
              }
            }
          }
        }
      }
      container suppression {
        description
          "Configure VSI traffic suppression list.";
        leaf inbound {
          type empty;
          must "../../../l2vpn:work-mode='normal' or ../../../l2vpn:work-mode='i-vsi-b-evpn-interworking'" {
            tailf:xpath-root 3;
          }
          description
            "Inbound suppression.";
        }
        leaf outbound {
          type empty;
          must "../../../l2vpn:work-mode='normal' or ../../../l2vpn:work-mode='i-vsi-b-evpn-interworking'" {
            tailf:xpath-root 3;
          }
          description
            "Outbound suppression.";
        }
      }
      container uni-suppressions {
        description
          "List of VSI traffic suppression.";
        list uni-suppression {
          must "../../../l2vpn:work-mode='normal'" {
            tailf:xpath-root 3;
          }
          key "type direction";
          description
            "Configure VSI traffic suppression.";
          leaf type {
            type suppress-type;
            description
              "Traffic suppression type.";
          }
          leaf direction {
            type vsi-direction-type;
            description
              "Suppression direction.";
          }
          leaf cir {
            type uint64 {
              range "0..4294967295";
            }
            units "kbit/s";
            mandatory true;
            description
              "CIR value.";
          }
          leaf cbs {
            type uint64 {
              range "0..4294967295";
            }
            units "Byte";
            ext:dynamic-default {
              ext:default-value "../cir*(1500/8)" {
                when '../cir < 100000' {
                  tailf:xpath-root 3;
                }
                description
                  "When cir less than 100000kbit/s,the default value is cir * (1500/8)Byte.";
              }
              ext:default-value "18750000" {
                when '../cir >= 100000' {
                  tailf:xpath-root 3;
                }
                description
                  "When cir more than 100000kbit/s,the default value is 100000 * (1500/8)Byte.";
              }
            }
            description
              "CBS value. If user does not specify this value, the system will calc a value by CIR value.";
          }
        }
      }
      container mac-limit {
        must "../../l2vpn:work-mode='normal' or ../../l2vpn:work-mode='i-vsi-b-evpn-interworking'" {
          tailf:xpath-root 3;
        }
        presence "VSI MAC address limit.";
        description
          "Enable/disable to limit VSI MAC address.";
        leaf maximum {
          type uint32 {
            range "0..2048000";
          }
          must 'not(../rate=0) or (../maximum>0)' {
            tailf:xpath-root 3;
          }
          mandatory true;
          description
            "Maximum number of MAC addresses that can be learned in a VSI. The value 0 means unlimited.";
        }
        leaf rate {
          type uint16 {
            range "0..1000";
          }
          units "ms";
          must 'not(../maximum=0) or (../rate>0)' {
            tailf:xpath-root 3;
          }
          default "0";
          description
            "Interval at which MAC addresses are learned in a VSI. The value 0 indicates that no rate limit is set.";
        }
        leaf action {
          type mac-limit-forward;
          default "discard";
          description
            "Discard or forward after the number of learned MAC addresses reaches the maximum number in a VSI.";
        }
        leaf alarm {
          type mac-enable-status;
          default "disable";
          description
            "Whether an alarm is generated after the number of learned MAC addresses reaches the maximum number in a VSI.";
        }
        leaf up-threshold {
          when '../maximum>0' {
            tailf:xpath-root 3;
          }
          type uint8 {
            range "1..100";
          }
          must '(not(../up-threshold) and not(../down-threshold)) or ((../up-threshold and ../down-threshold) and (../up-threshold>=../down-threshold))' {
            tailf:xpath-root 3;
          }
          description
            "Upper limit for the number of MAC addresses.";
        }
        leaf down-threshold {
          when '../maximum>0' {
            tailf:xpath-root 3;
          }
          type uint8 {
            range "1..100";
          }
          must '(not(../up-threshold) and not(../down-threshold)) or ((../up-threshold and ../down-threshold) and (../up-threshold>=../down-threshold))' {
            tailf:xpath-root 3;
          }
          description
            "Lower limit for the number of MAC addresses.";
        }
      }
    }
  }
  augment "/ncs:devices/ncs:template/ncs:ned-id/ncs:config/ifm:ifm/ifm:interfaces/ifm:interface/ethernet:ethernet" {
    description
      "MAC attribute of interface.";
    container mac {
      description
        "Configure MAC attribute of interface.";
      container sub-interface-mac-limit {
        // NCS drop must statement
        presence "Sub-interface MAC address limit.";
        description
          "Configure sub-interface MAC address limit.";
        choice limit-type {
          // NCS drop mandatory statement
          description
            "Sub-interface MAC limit type.";
          case limit-rule-ref {
            description
              "Reference global MAC limit rule.";
            leaf rule-name {
              type string;
              description
                "Rule name.";
            }
          }
          case limit-parameters {
            description
              "Specify MAC limit parameters.";
            leaf maximum {
              type string;
              // NCS drop must statement
              // NCS drop mandatory statement
              description
                "Maximum number of MAC addresses that can be learned on a sub-interface. The value 0 means unlimited.";
            }
            leaf rate {
              type string;
              units "ms";
              // NCS drop must statement
              // NCS drop default statement
              description
                "Interval at which MAC addresses are learned on a sub-interface. The value 0 indicates that no rate limit is set.";
            }
            leaf action {
              type ncs_template_mac-limit-forward;
              // NCS drop default statement
              description
                "Discard or forward after the number of learned MAC addresses reaches the maximum number on a sub-interface.";
            }
            leaf alarm {
              type ncs_template_mac-enable-status;
              // NCS drop default statement
              description
                "Whether an alarm is generated after the number of learned MAC addresses reaches the maximum number on a sub-interface.";
            }
          }
        }
      }
      container sub-interface-suppressions {
        description
          "List of sub-interface traffic suppression.";
        list sub-interface-suppression {
          // NCS patched for predictable order
          ordered-by user;
          // NCS drop must statement
          key "type direction";
          description
            "Configure sub-Interface traffic suppression.";
          leaf type {
            type ncs_template_suppress-type;
            description
              "Suppression type.";
          }
          leaf direction {
            type ncs_template_direction-type;
            description
              "Suppression direction.";
          }
          leaf cir {
            type string;
            units "kbit/s";
            // NCS drop mandatory statement
            description
              "CIR value.";
          }
          leaf cbs {
            type string;
            units "Byte";
            ext:dynamic-default {
              ext:default-value "../cir*(1500/8)" {
                // NCS drop when statement
                description
                  "When cir less than 100000kbit/s,the default value is cir * (1500/8)Byte.";
              }
              ext:default-value "18750000" {
                // NCS drop when statement
                description
                  "When cir more than 100000kbit/s,the default value is 100000 * (1500/8)Byte.";
              }
            }
            description
              "CBS value. If user does not specify this value, the system will calc a value by CIR value.";
          }
        }
      }
      container discards {
        description
          "List of interface packet discarding.";
        list discard {
          // NCS patched for predictable order
          ordered-by user;
          key "type";
          description
            "Configure an interface to discard broadcast packets.";
          leaf type {
            type ncs_template_discard-type;
            description
              "Discarding type.";
          }
        }
      }
    }
  }
  augment "/ncs:devices/ncs:device/ncs:live-status/ifm:ifm/ifm:interfaces/ifm:interface/ethernet:ethernet" {
    description
      "MAC attribute of interface.";
    container mac {
      tailf:ncs-device-type "netconf";
      tailf:display-when "not(../../../../../../ncs:module) or ../../../../../../ncs:module[ncs:name='huawei-mac'] or (../../../../../../ncs:live-status-protocol[not(ncs:capability)]) or (../../../../../../ncs:live-status-protocol/ncs:capability/ncs:module[.='huawei-mac'])";
      description
        "Configure MAC attribute of interface.";
      container sub-interface-mac-limit {
        // NCS drop must statement
        presence "Sub-interface MAC address limit.";
        description
          "Configure sub-interface MAC address limit.";
        choice limit-type {
          // NCS drop mandatory statement
          description
            "Sub-interface MAC limit type.";
          case limit-rule-ref {
            description
              "Reference global MAC limit rule.";
            leaf rule-name {
              type leafref {
                path "/ncs:devices/ncs:device/ncs:live-status/mac:mac/mac:mac-limit-rules/mac:mac-limit-rule/mac:name" {
                  tailf:xpath-root 3;
                }
              }
              description
                "Rule name.";
            }
          }
          case limit-parameters {
            description
              "Specify MAC limit parameters.";
            leaf maximum {
              type uint32 {
                range "0..131072";
              }
              // NCS drop must statement
              // NCS drop mandatory statement
              description
                "Maximum number of MAC addresses that can be learned on a sub-interface. The value 0 means unlimited.";
            }
            leaf rate {
              type uint16 {
                range "0..1000";
              }
              units "ms";
              // NCS drop must statement
              // NCS drop default statement
              description
                "Interval at which MAC addresses are learned on a sub-interface. The value 0 indicates that no rate limit is set.";
            }
            leaf action {
              type live_ncs_mac-limit-forward;
              // NCS drop default statement
              description
                "Discard or forward after the number of learned MAC addresses reaches the maximum number on a sub-interface.";
            }
            leaf alarm {
              type live_ncs_mac-enable-status;
              // NCS drop default statement
              description
                "Whether an alarm is generated after the number of learned MAC addresses reaches the maximum number on a sub-interface.";
            }
          }
        }
      }
      container sub-interface-suppressions {
        description
          "List of sub-interface traffic suppression.";
        list sub-interface-suppression {
          // NCS drop must statement
          key "type direction";
          description
            "Configure sub-Interface traffic suppression.";
          leaf type {
            type live_ncs_suppress-type;
            description
              "Suppression type.";
          }
          leaf direction {
            type live_ncs_direction-type;
            description
              "Suppression direction.";
          }
          leaf cir {
            type uint64 {
              range "0..4294967295";
            }
            units "kbit/s";
            // NCS drop mandatory statement
            description
              "CIR value.";
          }
          leaf cbs {
            type uint64 {
              range "0..4294967295";
            }
            units "Byte";
            ext:dynamic-default {
              ext:default-value "../cir*(1500/8)" {
                // NCS drop when statement
                description
                  "When cir less than 100000kbit/s,the default value is cir * (1500/8)Byte.";
              }
              ext:default-value "18750000" {
                // NCS drop when statement
                description
                  "When cir more than 100000kbit/s,the default value is 100000 * (1500/8)Byte.";
              }
            }
            description
              "CBS value. If user does not specify this value, the system will calc a value by CIR value.";
          }
        }
      }
      container discards {
        description
          "List of interface packet discarding.";
        list discard {
          key "type";
          description
            "Configure an interface to discard broadcast packets.";
          leaf type {
            type live_ncs_discard-type;
            description
              "Discarding type.";
          }
        }
      }
    }
  }
  augment "/ncs:devices/ncs:device/ncs:config/ifm:ifm/ifm:interfaces/ifm:interface/ethernet:ethernet" {
    description
      "MAC attribute of interface.";
    container mac {
      tailf:ncs-device-type "netconf";
      tailf:display-when "not(../../../../../../ncs:module) or ../../../../../../ncs:module[ncs:name='huawei-mac']";
      description
        "Configure MAC attribute of interface.";
      container sub-interface-mac-limit {
        must "(/l2vpn:l2vpn/l2vpn:instances/l2vpn:instance/l2vpn:vpls/l2vpn:acs/l2vpn:ac[l2vpn:interface-name=current()/../../../ifm:name]) or (../../../ifm:l2-mode-enable='true')" {
          tailf:xpath-root 3;
        }
        presence "Sub-interface MAC address limit.";
        description
          "Configure sub-interface MAC address limit.";
        choice limit-type {
          mandatory true;
          description
            "Sub-interface MAC limit type.";
          case limit-rule-ref {
            description
              "Reference global MAC limit rule.";
            leaf rule-name {
              type leafref {
                path "/ncs:devices/ncs:device/ncs:config/mac:mac/mac:mac-limit-rules/mac:mac-limit-rule/mac:name" {
                  tailf:xpath-root 3;
                }
              }
              description
                "Rule name.";
            }
          }
          case limit-parameters {
            description
              "Specify MAC limit parameters.";
            leaf maximum {
              type uint32 {
                range "0..131072";
              }
              must 'not(../rate=0) or (../maximum>0)' {
                tailf:xpath-root 3;
              }
              mandatory true;
              description
                "Maximum number of MAC addresses that can be learned on a sub-interface. The value 0 means unlimited.";
            }
            leaf rate {
              type uint16 {
                range "0..1000";
              }
              units "ms";
              must 'not(../maximum=0) or (../rate>0)' {
                tailf:xpath-root 3;
              }
              default "0";
              description
                "Interval at which MAC addresses are learned on a sub-interface. The value 0 indicates that no rate limit is set.";
            }
            leaf action {
              type mac-limit-forward;
              default "discard";
              description
                "Discard or forward after the number of learned MAC addresses reaches the maximum number on a sub-interface.";
            }
            leaf alarm {
              type mac-enable-status;
              default "enable";
              description
                "Whether an alarm is generated after the number of learned MAC addresses reaches the maximum number on a sub-interface.";
            }
          }
        }
      }
      container sub-interface-suppressions {
        description
          "List of sub-interface traffic suppression.";
        list sub-interface-suppression {
          must '(/l2vpn:l2vpn/l2vpn:instances/l2vpn:instance/l2vpn:vpls/l2vpn:acs/l2vpn:ac[l2vpn:interface-name=current()/../../../../ifm:name]) or /bd:bd/bd:instances/bd:instance/bd:service-points/bd:service-point[bd:interface-name=current()/../../../../ifm:name]' {
            tailf:xpath-root 3;
          }
          key "type direction";
          description
            "Configure sub-Interface traffic suppression.";
          leaf type {
            type suppress-type;
            description
              "Suppression type.";
          }
          leaf direction {
            type direction-type;
            description
              "Suppression direction.";
          }
          leaf cir {
            type uint64 {
              range "0..4294967295";
            }
            units "kbit/s";
            mandatory true;
            description
              "CIR value.";
          }
          leaf cbs {
            type uint64 {
              range "0..4294967295";
            }
            units "Byte";
            ext:dynamic-default {
              ext:default-value "../cir*(1500/8)" {
                when '../cir < 100000' {
                  tailf:xpath-root 3;
                }
                description
                  "When cir less than 100000kbit/s,the default value is cir * (1500/8)Byte.";
              }
              ext:default-value "18750000" {
                when '../cir >= 100000' {
                  tailf:xpath-root 3;
                }
                description
                  "When cir more than 100000kbit/s,the default value is 100000 * (1500/8)Byte.";
              }
            }
            description
              "CBS value. If user does not specify this value, the system will calc a value by CIR value.";
          }
        }
      }
      container discards {
        description
          "List of interface packet discarding.";
        list discard {
          key "type";
          description
            "Configure an interface to discard broadcast packets.";
          leaf type {
            type discard-type;
            description
              "Discarding type.";
          }
        }
      }
    }
  }
  augment "/ncs:devices/ncs:template/ncs:ned-id/ncs:config/l2vpn:l2vpn/l2vpn:instances/l2vpn:instance/l2vpn:vpls/l2vpn:ldp-signaling/l2vpn:pws/l2vpn:pw" {
    description
      "MAC attribute on PW.";
    container mac {
      // NCS drop when statement
      description
        "Configure MAC attribute on PW.";
      container mac-limit {
        presence "MAC address limit.";
        description
          "Configure MAC address limit.";
        leaf maximum {
          type string;
          // NCS drop must statement
          // NCS drop mandatory statement
          description
            "Maximum number of MAC addresses that can be learned. The value 0 means unlimited.";
        }
        leaf rate {
          type string;
          units "ms";
          // NCS drop must statement
          // NCS drop default statement
          description
            "Interval at which MAC addresses are learned. The value 0 indicates that no rate limit is set.";
        }
        leaf action {
          type ncs_template_mac-limit-forward;
          // NCS drop default statement
          description
            "Discard or forward after the number of learned MAC addresses reaches the maximum number.";
        }
        leaf alarm {
          type ncs_template_mac-enable-status;
          // NCS drop default statement
          description
            "Whether an alarm is generated after the number of learned MAC addresses reaches the maximum number.";
        }
      }
      container suppressions {
        description
          "Configure PW traffic suppress list.";
        uses ncs_template_pw-mac-suppression;
      }
    }
  }
  augment "/ncs:devices/ncs:device/ncs:live-status/l2vpn:l2vpn/l2vpn:instances/l2vpn:instance/l2vpn:vpls/l2vpn:ldp-signaling/l2vpn:pws/l2vpn:pw" {
    description
      "MAC attribute on PW.";
    container mac {
      tailf:ncs-device-type "netconf";
      tailf:display-when "not(../../../../../../../../../ncs:module) or ../../../../../../../../../ncs:module[ncs:name='huawei-mac'] or (../../../../../../../../../ncs:live-status-protocol[not(ncs:capability)]) or (../../../../../../../../../ncs:live-status-protocol/ncs:capability/ncs:module[.='huawei-mac'])";
      // NCS drop when statement
      description
        "Configure MAC attribute on PW.";
      container mac-limit {
        presence "MAC address limit.";
        description
          "Configure MAC address limit.";
        leaf maximum {
          type uint32 {
            range "0..130048";
          }
          // NCS drop must statement
          // NCS drop mandatory statement
          description
            "Maximum number of MAC addresses that can be learned. The value 0 means unlimited.";
        }
        leaf rate {
          type uint16 {
            range "0..1000";
          }
          units "ms";
          // NCS drop must statement
          // NCS drop default statement
          description
            "Interval at which MAC addresses are learned. The value 0 indicates that no rate limit is set.";
        }
        leaf action {
          type live_ncs_mac-limit-forward;
          // NCS drop default statement
          description
            "Discard or forward after the number of learned MAC addresses reaches the maximum number.";
        }
        leaf alarm {
          type live_ncs_mac-enable-status;
          // NCS drop default statement
          description
            "Whether an alarm is generated after the number of learned MAC addresses reaches the maximum number.";
        }
      }
      container suppressions {
        description
          "Configure PW traffic suppress list.";
        uses live_ncs_pw-mac-suppression;
      }
    }
  }
  augment "/ncs:devices/ncs:device/ncs:config/l2vpn:l2vpn/l2vpn:instances/l2vpn:instance/l2vpn:vpls/l2vpn:ldp-signaling/l2vpn:pws/l2vpn:pw" {
    description
      "MAC attribute on PW.";
    container mac {
      tailf:ncs-device-type "netconf";
      tailf:display-when "not(../../../../../../../../../ncs:module) or ../../../../../../../../../ncs:module[ncs:name='huawei-mac']";
      when '../l2vpn:name' {
        tailf:xpath-root 3;
      }
      description
        "Configure MAC attribute on PW.";
      container mac-limit {
        presence "MAC address limit.";
        description
          "Configure MAC address limit.";
        leaf maximum {
          type uint32 {
            range "0..130048";
          }
          must 'not(../rate=0) or (../rate=0 and ../maximum>0)' {
            tailf:xpath-root 3;
          }
          mandatory true;
          description
            "Maximum number of MAC addresses that can be learned. The value 0 means unlimited.";
        }
        leaf rate {
          type uint16 {
            range "0..1000";
          }
          units "ms";
          must 'not(../maximum=0) or (../maximum=0 and ../rate>0)' {
            tailf:xpath-root 3;
          }
          default "0";
          description
            "Interval at which MAC addresses are learned. The value 0 indicates that no rate limit is set.";
        }
        leaf action {
          type mac-limit-forward;
          default "discard";
          description
            "Discard or forward after the number of learned MAC addresses reaches the maximum number.";
        }
        leaf alarm {
          type mac-enable-status;
          default "enable";
          description
            "Whether an alarm is generated after the number of learned MAC addresses reaches the maximum number.";
        }
      }
      container suppressions {
        description
          "Configure PW traffic suppress list.";
        uses pw-mac-suppression;
      }
    }
  }
  augment "/ncs:devices/ncs:template/ncs:ned-id/ncs:config/l2vpn:l2vpn/l2vpn:instances/l2vpn:instance/l2vpn:vpls/l2vpn:bgp-multi-homing-signaling/l2vpn:pws/l2vpn:pw" {
    description
      "MAC attribute on PW.";
    container mac {
      // NCS drop when statement
      description
        "Configure MAC attribute on PW.";
      container suppressions {
        description
          "Configure PW traffic suppress list.";
        uses ncs_template_pw-mac-suppression;
      }
    }
  }
  augment "/ncs:devices/ncs:device/ncs:live-status/l2vpn:l2vpn/l2vpn:instances/l2vpn:instance/l2vpn:vpls/l2vpn:bgp-multi-homing-signaling/l2vpn:pws/l2vpn:pw" {
    description
      "MAC attribute on PW.";
    container mac {
      tailf:ncs-device-type "netconf";
      tailf:display-when "not(../../../../../../../../../ncs:module) or ../../../../../../../../../ncs:module[ncs:name='huawei-mac'] or (../../../../../../../../../ncs:live-status-protocol[not(ncs:capability)]) or (../../../../../../../../../ncs:live-status-protocol/ncs:capability/ncs:module[.='huawei-mac'])";
      // NCS drop when statement
      description
        "Configure MAC attribute on PW.";
      container suppressions {
        description
          "Configure PW traffic suppress list.";
        uses live_ncs_pw-mac-suppression;
      }
    }
  }
  augment "/ncs:devices/ncs:device/ncs:config/l2vpn:l2vpn/l2vpn:instances/l2vpn:instance/l2vpn:vpls/l2vpn:bgp-multi-homing-signaling/l2vpn:pws/l2vpn:pw" {
    description
      "MAC attribute on PW.";
    container mac {
      tailf:ncs-device-type "netconf";
      tailf:display-when "not(../../../../../../../../../ncs:module) or ../../../../../../../../../ncs:module[ncs:name='huawei-mac']";
      when '../l2vpn:name' {
        tailf:xpath-root 3;
      }
      description
        "Configure MAC attribute on PW.";
      container suppressions {
        description
          "Configure PW traffic suppress list.";
        uses pw-mac-suppression;
      }
    }
  }
  augment "/ncs:devices/ncs:template/ncs:ned-id/ncs:config/l2vpn:l2vpn/l2vpn:instances/l2vpn:instance/l2vpn:vpls/l2vpn:bgp-signaling/l2vpn:pws/l2vpn:pw" {
    description
      "MAC attribute on PW.";
    container mac {
      // NCS drop when statement
      description
        "Configure MAC attribute on PW.";
      container suppressions {
        description
          "Configure PW traffic suppress list.";
        uses ncs_template_pw-mac-suppression;
      }
    }
  }
  augment "/ncs:devices/ncs:device/ncs:live-status/l2vpn:l2vpn/l2vpn:instances/l2vpn:instance/l2vpn:vpls/l2vpn:bgp-signaling/l2vpn:pws/l2vpn:pw" {
    description
      "MAC attribute on PW.";
    container mac {
      tailf:ncs-device-type "netconf";
      tailf:display-when "not(../../../../../../../../../ncs:module) or ../../../../../../../../../ncs:module[ncs:name='huawei-mac'] or (../../../../../../../../../ncs:live-status-protocol[not(ncs:capability)]) or (../../../../../../../../../ncs:live-status-protocol/ncs:capability/ncs:module[.='huawei-mac'])";
      // NCS drop when statement
      description
        "Configure MAC attribute on PW.";
      container suppressions {
        description
          "Configure PW traffic suppress list.";
        uses live_ncs_pw-mac-suppression;
      }
    }
  }
  augment "/ncs:devices/ncs:device/ncs:config/l2vpn:l2vpn/l2vpn:instances/l2vpn:instance/l2vpn:vpls/l2vpn:bgp-signaling/l2vpn:pws/l2vpn:pw" {
    description
      "MAC attribute on PW.";
    container mac {
      tailf:ncs-device-type "netconf";
      tailf:display-when "not(../../../../../../../../../ncs:module) or ../../../../../../../../../ncs:module[ncs:name='huawei-mac']";
      when '../l2vpn:name' {
        tailf:xpath-root 3;
      }
      description
        "Configure MAC attribute on PW.";
      container suppressions {
        description
          "Configure PW traffic suppress list.";
        uses pw-mac-suppression;
      }
    }
  }
  augment "/ncs:devices/ncs:template/ncs:ned-id/ncs:config/l2vpn:l2vpn/l2vpn:instances/l2vpn:instance/l2vpn:vpls/l2vpn:bgpad-signaling/l2vpn:pws/l2vpn:pw" {
    description
      "MAC attribute on PW.";
    container mac {
      // NCS drop when statement
      description
        "Configure MAC attribute on PW.";
      container suppressions {
        description
          "Configure PW traffic suppress list.";
        uses ncs_template_pw-mac-suppression;
      }
    }
  }
  augment "/ncs:devices/ncs:device/ncs:live-status/l2vpn:l2vpn/l2vpn:instances/l2vpn:instance/l2vpn:vpls/l2vpn:bgpad-signaling/l2vpn:pws/l2vpn:pw" {
    description
      "MAC attribute on PW.";
    container mac {
      tailf:ncs-device-type "netconf";
      tailf:display-when "not(../../../../../../../../../ncs:module) or ../../../../../../../../../ncs:module[ncs:name='huawei-mac'] or (../../../../../../../../../ncs:live-status-protocol[not(ncs:capability)]) or (../../../../../../../../../ncs:live-status-protocol/ncs:capability/ncs:module[.='huawei-mac'])";
      // NCS drop when statement
      description
        "Configure MAC attribute on PW.";
      container suppressions {
        description
          "Configure PW traffic suppress list.";
        uses live_ncs_pw-mac-suppression;
      }
    }
  }
  augment "/ncs:devices/ncs:device/ncs:config/l2vpn:l2vpn/l2vpn:instances/l2vpn:instance/l2vpn:vpls/l2vpn:bgpad-signaling/l2vpn:pws/l2vpn:pw" {
    description
      "MAC attribute on PW.";
    container mac {
      tailf:ncs-device-type "netconf";
      tailf:display-when "not(../../../../../../../../../ncs:module) or ../../../../../../../../../ncs:module[ncs:name='huawei-mac']";
      when '../l2vpn:name' {
        tailf:xpath-root 3;
      }
      description
        "Configure MAC attribute on PW.";
      container suppressions {
        description
          "Configure PW traffic suppress list.";
        uses pw-mac-suppression;
      }
    }
  }
  augment "/ncs:devices/ncs:template/ncs:ned-id/ncs:config/ifm:ifm/ifm:interfaces/ifm:interface/ethernet:ethernet/ethernet:main-interface" {
    description
      "MAC attribute of main interface.";
    container mac-limit {
      presence "Main interface MAC address limit.";
      description
        "Configure main interface MAC address limit.";
      choice limit-type {
        // NCS drop mandatory statement
        description
          "MAC limit type.";
        case limit-rule-ref {
          description
            "Reference global MAC limit rule.";
          leaf rule-name {
            type string;
            // NCS drop mandatory statement
            description
              "Rule name.";
          }
        }
        case limit-parameter {
          description
            "Specify MAC limit parameters.";
          leaf maximum {
            type string;
            // NCS drop must statement
            // NCS drop mandatory statement
            description
              "Maximum number of MAC addresses that can be learned. The value 0 means unlimited.";
          }
          leaf rate {
            type string;
            units "ms";
            // NCS drop must statement
            // NCS drop default statement
            description
              "Interval at which MAC addresses are learned. The value 0 indicates that no rate limit is set.";
          }
          leaf action {
            type ncs_template_mac-limit-forward;
            // NCS drop default statement
            description
              "Discard or forward after the number of learned MAC addresses reaches the maximum number.";
          }
          leaf alarm {
            type ncs_template_mac-enable-status;
            // NCS drop default statement
            description
              "Whether an alarm is generated after the number of learned MAC addresses reaches the maximum number.";
          }
        }
      }
    }
  }
  augment "/ncs:devices/ncs:device/ncs:live-status/ifm:ifm/ifm:interfaces/ifm:interface/ethernet:ethernet/ethernet:main-interface" {
    description
      "MAC attribute of main interface.";
    container mac-limit {
      tailf:ncs-device-type "netconf";
      tailf:display-when "not(../../../../../../../ncs:module) or ../../../../../../../ncs:module[ncs:name='huawei-mac'] or (../../../../../../../ncs:live-status-protocol[not(ncs:capability)]) or (../../../../../../../ncs:live-status-protocol/ncs:capability/ncs:module[.='huawei-mac'])";
      presence "Main interface MAC address limit.";
      description
        "Configure main interface MAC address limit.";
      choice limit-type {
        // NCS drop mandatory statement
        description
          "MAC limit type.";
        case limit-rule-ref {
          description
            "Reference global MAC limit rule.";
          leaf rule-name {
            type leafref {
              path "/ncs:devices/ncs:device/ncs:live-status/mac:mac/mac:mac-limit-rules/mac:mac-limit-rule/mac:name" {
                tailf:xpath-root 3;
              }
            }
            // NCS drop mandatory statement
            description
              "Rule name.";
          }
        }
        case limit-parameter {
          description
            "Specify MAC limit parameters.";
          leaf maximum {
            type uint32 {
              range "0..131072";
            }
            // NCS drop must statement
            // NCS drop mandatory statement
            description
              "Maximum number of MAC addresses that can be learned. The value 0 means unlimited.";
          }
          leaf rate {
            type uint16 {
              range "0..1000";
            }
            units "ms";
            // NCS drop must statement
            // NCS drop default statement
            description
              "Interval at which MAC addresses are learned. The value 0 indicates that no rate limit is set.";
          }
          leaf action {
            type live_ncs_mac-limit-forward;
            // NCS drop default statement
            description
              "Discard or forward after the number of learned MAC addresses reaches the maximum number.";
          }
          leaf alarm {
            type live_ncs_mac-enable-status;
            // NCS drop default statement
            description
              "Whether an alarm is generated after the number of learned MAC addresses reaches the maximum number.";
          }
        }
      }
    }
  }
  augment "/ncs:devices/ncs:device/ncs:config/ifm:ifm/ifm:interfaces/ifm:interface/ethernet:ethernet/ethernet:main-interface" {
    description
      "MAC attribute of main interface.";
    container mac-limit {
      tailf:ncs-device-type "netconf";
      tailf:display-when "not(../../../../../../../ncs:module) or ../../../../../../../ncs:module[ncs:name='huawei-mac']";
      presence "Main interface MAC address limit.";
      description
        "Configure main interface MAC address limit.";
      choice limit-type {
        mandatory true;
        description
          "MAC limit type.";
        case limit-rule-ref {
          description
            "Reference global MAC limit rule.";
          leaf rule-name {
            type leafref {
              path "/ncs:devices/ncs:device/ncs:config/mac:mac/mac:mac-limit-rules/mac:mac-limit-rule/mac:name" {
                tailf:xpath-root 3;
              }
            }
            mandatory true;
            description
              "Rule name.";
          }
        }
        case limit-parameter {
          description
            "Specify MAC limit parameters.";
          leaf maximum {
            type uint32 {
              range "0..131072";
            }
            must 'not(../rate=0) or (../rate=0 and ../maximum>0)' {
              tailf:xpath-root 3;
            }
            mandatory true;
            description
              "Maximum number of MAC addresses that can be learned. The value 0 means unlimited.";
          }
          leaf rate {
            type uint16 {
              range "0..1000";
            }
            units "ms";
            must 'not(../maximum=0) or (../maximum=0 and ../rate>0)' {
              tailf:xpath-root 3;
            }
            default "0";
            description
              "Interval at which MAC addresses are learned. The value 0 indicates that no rate limit is set.";
          }
          leaf action {
            type mac-limit-forward;
            default "discard";
            description
              "Discard or forward after the number of learned MAC addresses reaches the maximum number.";
          }
          leaf alarm {
            type mac-enable-status;
            default "enable";
            description
              "Whether an alarm is generated after the number of learned MAC addresses reaches the maximum number.";
          }
        }
      }
    }
  }
}
