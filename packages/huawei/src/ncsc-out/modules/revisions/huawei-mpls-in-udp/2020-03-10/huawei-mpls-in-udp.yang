module huawei-mpls-in-udp {
  // Generated by yanger -t ncs
  tailf:mount-id "huawei-nc-1.0:huawei-nc-1.0";
  tailf:ncs-device-type "netconf";

  namespace "urn:huawei:yang:huawei-mpls-in-udp";
  prefix mpls-in-udp;

  import ietf-inet-types {
    prefix inet;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Specifies the traffic engineering configuration.";

  revision 2020-03-10 {
    description
      "Fixed some nodes description.";
    reference "Huawei private.";
  }
  revision 2019-10-28 {
    description
      "Init revision.";
    reference "Huawei private.";
  }
  ext:task-name "mplsinudp";

  augment "/ncs:devices/ncs:device/ncs:config" {
    container mpls-in-udp {
      tailf:ncs-device-type "netconf";
      tailf:display-when "not(../../ncs:module) or ../../ncs:module[ncs:name='huawei-mpls-in-udp']";
      presence "Enter mpls-in-udp view.";
      description
        "MPLS in UDP Configuration.";
      container validate-lists {
        description
          "List of source IP address validate.";
        list validate-list {
          key "destination-ip";
          max-elements 2000;
          description
            "Configure source IP address validate.";
          leaf destination-ip {
            type inet:ipv4-address-no-zone;
            description
              "Destination IP address.";
          }
          leaf enable {
            type boolean;
            default "false";
            description
              "Enable/disable validate.";
          }
          container source-ips {
            description
              "List of source IP.";
            list source-ip {
              must '../../destination-ip !=source-ip-address' {
                tailf:xpath-root 3;
              }
              key "source-ip-address";
              max-elements 2000;
              description
                "Configure source IP address.";
              leaf source-ip-address {
                type inet:ipv4-address-no-zone;
                description
                  "Source IP address.";
              }
            }
          }
        }
      }
    }
  }
  augment "/ncs:devices/ncs:device/ncs:live-status" {
    container mpls-in-udp {
      tailf:ncs-device-type "netconf";
      tailf:display-when "not(../../ncs:module) or ../../ncs:module[ncs:name='huawei-mpls-in-udp'] or (../../ncs:live-status-protocol[not(ncs:capability)]) or (../../ncs:live-status-protocol/ncs:capability/ncs:module[.='huawei-mpls-in-udp'])";
      presence "Enter mpls-in-udp view.";
      description
        "MPLS in UDP Configuration.";
      container validate-lists {
        description
          "List of source IP address validate.";
        list validate-list {
          key "destination-ip";
          // NCS drop max-elements statement
          description
            "Configure source IP address validate.";
          leaf destination-ip {
            type inet:ipv4-address-no-zone;
            description
              "Destination IP address.";
          }
          leaf enable {
            type boolean;
            // NCS drop default statement
            description
              "Enable/disable validate.";
          }
          container source-ips {
            description
              "List of source IP.";
            list source-ip {
              // NCS drop must statement
              key "source-ip-address";
              // NCS drop max-elements statement
              description
                "Configure source IP address.";
              leaf source-ip-address {
                type inet:ipv4-address-no-zone;
                description
                  "Source IP address.";
              }
            }
          }
        }
      }
    }
  }
  augment "/ncs:devices/ncs:template/ncs:ned-id/ncs:config" {
    container mpls-in-udp {
      presence "Enter mpls-in-udp view.";
      description
        "MPLS in UDP Configuration.";
      container validate-lists {
        description
          "List of source IP address validate.";
        list validate-list {
          // NCS patched for predictable order
          ordered-by user;
          key "destination-ip";
          // NCS drop max-elements statement
          description
            "Configure source IP address validate.";
          leaf destination-ip {
            type string;
            description
              "Destination IP address.";
          }
          leaf enable {
            type string;
            // NCS drop default statement
            description
              "Enable/disable validate.";
          }
          container source-ips {
            description
              "List of source IP.";
            list source-ip {
              // NCS patched for predictable order
              ordered-by user;
              // NCS drop must statement
              key "source-ip-address";
              // NCS drop max-elements statement
              description
                "Configure source IP address.";
              leaf source-ip-address {
                type string;
                description
                  "Source IP address.";
              }
            }
          }
        }
      }
    }
  }
}
