module huawei-ecc {
  // Generated by yanger -t ncs
  tailf:mount-id "huawei-nc-1.0:huawei-nc-1.0";
  tailf:ncs-device-type "netconf";

  namespace "urn:huawei:yang:huawei-ecc";
  prefix ecc;

  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "ECC.";

  revision 2019-05-02 {
    description
      "Initial revision.";
    reference "Huawei private.";
  }
  ext:task-name "ssh-server";

  typedef ncs_template_ecc-key-type {
    type string;
    description
      "ECC key length.";
  }

  typedef ncs_template_ecc-encode-type {
    type string;
    description
      "ECC encodein type list.";
  }

  typedef ncs_rpc_notif_ecc-key-type {
    type enumeration {
      enum "256" {
        value 256;
        description
          "Modulus 256.";
      }
      enum "384" {
        value 384;
        description
          "Modulus 384.";
      }
      enum "521" {
        value 521;
        description
          "Modulus 521.";
      }
    }
    description
      "ECC key length.";
  }

  typedef ncs_rpc_notif_ecc-encode-type {
    type enumeration {
      enum "der" {
        value 0;
        description
          "Der.";
      }
      enum "pem" {
        value 1;
        description
          "Pem.";
      }
      enum "openssh" {
        value 2;
        description
          "Openssh.";
      }
    }
    description
      "ECC encodein type list.";
  }

  typedef live_ncs_ecc-key-type {
    type enumeration {
      enum "256" {
        value 256;
        description
          "Modulus 256.";
      }
      enum "384" {
        value 384;
        description
          "Modulus 384.";
      }
      enum "521" {
        value 521;
        description
          "Modulus 521.";
      }
    }
    description
      "ECC key length.";
  }

  typedef live_ncs_ecc-encode-type {
    type enumeration {
      enum "der" {
        value 0;
        description
          "Der.";
      }
      enum "pem" {
        value 1;
        description
          "Pem.";
      }
      enum "openssh" {
        value 2;
        description
          "Openssh.";
      }
    }
    description
      "ECC encodein type list.";
  }

  typedef ecc-key-type {
    type enumeration {
      enum "256" {
        value 256;
        description
          "Modulus 256.";
      }
      enum "384" {
        value 384;
        description
          "Modulus 384.";
      }
      enum "521" {
        value 521;
        description
          "Modulus 521.";
      }
    }
    description
      "ECC key length.";
  }

  typedef ecc-encode-type {
    type enumeration {
      enum "der" {
        value 0;
        description
          "Der.";
      }
      enum "pem" {
        value 1;
        description
          "Pem.";
      }
      enum "openssh" {
        value 2;
        description
          "Openssh.";
      }
    }
    description
      "ECC encodein type list.";
  }

  augment "/ncs:devices/ncs:device/ncs:config" {
    container ecc {
      tailf:ncs-device-type "netconf";
      tailf:display-when "not(../../ncs:module) or ../../ncs:module[ncs:name='huawei-ecc']";
      description
        "ECC.";
      container local-keys {
        description
          "Configure local key table.";
        container local-key {
          presence "create eccLocalKey.";
          description
            "Enable/disable local key code.";
          leaf key-size {
            type ecc-key-type;
            default "521";
            description
              "Key size(256/384/521).";
          }
          // NCS drop config false leaf 'host-key-name'
          // NCS drop config false leaf 'host-key-code'
          // NCS drop config false leaf 'host-key-pem'
        }
      }
      container peer-keys {
        description
          "List of peer key table.";
        list peer-key {
          key "key-name";
          max-elements 20;
          description
            "Configure peer key code. If the key code is bound, it cannot be deleted, you need to unbind and then delete.";
          leaf key-name {
            type string {
              length "1..40";
            }
            description
              "Key name.";
          }
          leaf key-code {
            type string {
              length "1..4096";
            }
            mandatory true;
            ext:support-filter "true";
            description
              "Key code conforming to PEM, OpenSSH or DER format.";
          }
          leaf encoding-type {
            type ecc-encode-type;
            default "der";
            ext:support-filter "true";
            description
              "Encode type.";
          }
        }
      }
      container key-pairs {
        description
          "List of ECC keypair labels.";
        list key-pair {
          key "key-pair-label";
          max-elements 20;
          description
            "Configure ECC keypair label.";
          leaf key-pair-label {
            type string {
              length "1..35";
              pattern '[a-z0-9_]*';
            }
            description
              "Keypair Label Name : It only contains underscores (_), lowercase letters and digits.";
          }
          leaf key-size {
            type ecc-key-type;
            default "521";
            ext:support-filter "true";
            description
              "Size of Keypair.";
          }
          // NCS drop config false leaf 'host-key-code'
        }
      }
      container ecc-global {
        description
          "Configure global Configuration.";
        leaf max-key-pair {
          type int32 {
            range "1..20";
          }
          default "20";
          description
            "Maximum keypair value.";
        }
      }
    }
  }
  augment "/ncs:devices/ncs:device/ncs:live-status" {
    container ecc {
      tailf:ncs-device-type "netconf";
      tailf:display-when "not(../../ncs:module) or ../../ncs:module[ncs:name='huawei-ecc'] or (../../ncs:live-status-protocol[not(ncs:capability)]) or (../../ncs:live-status-protocol/ncs:capability/ncs:module[.='huawei-ecc'])";
      description
        "ECC.";
      container local-keys {
        description
          "Configure local key table.";
        container local-key {
          presence "create eccLocalKey.";
          description
            "Enable/disable local key code.";
          leaf key-size {
            type live_ncs_ecc-key-type;
            // NCS drop default statement
            description
              "Key size(256/384/521).";
          }
          leaf host-key-name {
            type string {
              length "0..264";
            }
            description
              "Hostkey name.";
          }
          leaf host-key-code {
            type string {
              length "0..1024";
            }
            description
              "Hostkey code.";
          }
          leaf host-key-pem {
            type string {
              length "0..1024";
            }
            description
              "Hostkey code in PEM format.";
          }
        }
      }
      container peer-keys {
        description
          "List of peer key table.";
        list peer-key {
          key "key-name";
          // NCS drop max-elements statement
          description
            "Configure peer key code. If the key code is bound, it cannot be deleted, you need to unbind and then delete.";
          leaf key-name {
            type string {
              length "1..40";
            }
            description
              "Key name.";
          }
          leaf key-code {
            type string {
              length "1..4096";
            }
            // NCS drop mandatory statement
            ext:support-filter "true";
            description
              "Key code conforming to PEM, OpenSSH or DER format.";
          }
          leaf encoding-type {
            type live_ncs_ecc-encode-type;
            // NCS drop default statement
            ext:support-filter "true";
            description
              "Encode type.";
          }
        }
      }
      container key-pairs {
        description
          "List of ECC keypair labels.";
        list key-pair {
          key "key-pair-label";
          // NCS drop max-elements statement
          description
            "Configure ECC keypair label.";
          leaf key-pair-label {
            type string {
              length "1..35";
              pattern '[a-z0-9_]*';
            }
            description
              "Keypair Label Name : It only contains underscores (_), lowercase letters and digits.";
          }
          leaf key-size {
            type live_ncs_ecc-key-type;
            // NCS drop default statement
            ext:support-filter "true";
            description
              "Size of Keypair.";
          }
          leaf host-key-code {
            type string {
              length "0..2048";
            }
            ext:support-filter "true";
            description
              "ECC hostkey code.";
          }
        }
      }
      container ecc-global {
        description
          "Configure global Configuration.";
        leaf max-key-pair {
          type int32 {
            range "1..20";
          }
          // NCS drop default statement
          description
            "Maximum keypair value.";
        }
      }
    }
  }
  augment "/ncs:devices/ncs:template/ncs:ned-id/ncs:config" {
    container ecc {
      description
        "ECC.";
      container local-keys {
        description
          "Configure local key table.";
        container local-key {
          presence "create eccLocalKey.";
          description
            "Enable/disable local key code.";
          leaf key-size {
            type ncs_template_ecc-key-type;
            // NCS drop default statement
            description
              "Key size(256/384/521).";
          }
          // NCS drop config false leaf 'host-key-name'
          // NCS drop config false leaf 'host-key-code'
          // NCS drop config false leaf 'host-key-pem'
        }
      }
      container peer-keys {
        description
          "List of peer key table.";
        list peer-key {
          // NCS patched for predictable order
          ordered-by user;
          key "key-name";
          // NCS drop max-elements statement
          description
            "Configure peer key code. If the key code is bound, it cannot be deleted, you need to unbind and then delete.";
          leaf key-name {
            type string;
            description
              "Key name.";
          }
          leaf key-code {
            type string;
            // NCS drop mandatory statement
            ext:support-filter "true";
            description
              "Key code conforming to PEM, OpenSSH or DER format.";
          }
          leaf encoding-type {
            type ncs_template_ecc-encode-type;
            // NCS drop default statement
            ext:support-filter "true";
            description
              "Encode type.";
          }
        }
      }
      container key-pairs {
        description
          "List of ECC keypair labels.";
        list key-pair {
          // NCS patched for predictable order
          ordered-by user;
          key "key-pair-label";
          // NCS drop max-elements statement
          description
            "Configure ECC keypair label.";
          leaf key-pair-label {
            type string;
            description
              "Keypair Label Name : It only contains underscores (_), lowercase letters and digits.";
          }
          leaf key-size {
            type ncs_template_ecc-key-type;
            // NCS drop default statement
            ext:support-filter "true";
            description
              "Size of Keypair.";
          }
          // NCS drop config false leaf 'host-key-code'
        }
      }
      container ecc-global {
        description
          "Configure global Configuration.";
        leaf max-key-pair {
          type string;
          // NCS drop default statement
          description
            "Maximum keypair value.";
        }
      }
    }
  }
}
