module huawei-bras-cu-controller-deviations-NE8000 {
  // Generated by yanger -t ncs
  tailf:mount-id "huawei-nc-1.0:huawei-nc-1.0";
  tailf:ncs-device-type "netconf";

  namespace "urn:huawei:yang:huawei-bras-cu-controller-deviations-NE8000";
  prefix bras-cu-controller-devs-NE8000;

  import huawei-bras-cu-controller {
    prefix bras-cu-controller;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "This module defines deviation statements for huawei-bras-cu-controller module.";

  revision 2019-11-06 {
    description
      "Initial revision.";
    reference "Huawei private.";
  }

  deviation "/ncs:devices/ncs:template/ncs:ned-id/ncs:config/bras-cu-controller:bras-cu-controller" {
    deviate not-supported;
  }
  deviation "/ncs:devices/ncs:device/ncs:live-status/bras-cu-controller:bras-cu-controller" {
    deviate not-supported;
  }
  deviation "/ncs:devices/ncs:device/ncs:config/bras-cu-controller:bras-cu-controller" {
    deviate not-supported;
  }
  deviation "/ncs:devices/ncs:device/ncs:rpc/bras-cu-controller:rpc-reset-south-conflict-by-up/bras-cu-controller:reset-south-conflict-by-up" {
    deviate not-supported;
  }
  deviation "/ncs:devices/ncs:device/ncs:rpc/bras-cu-controller:rpc-reset-south-conflict-all-up/bras-cu-controller:reset-south-conflict-all-up" {
    deviate not-supported;
  }
}
