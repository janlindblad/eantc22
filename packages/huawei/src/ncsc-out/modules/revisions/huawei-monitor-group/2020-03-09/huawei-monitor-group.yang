module huawei-monitor-group {
  // Generated by yanger -t ncs
  tailf:mount-id "huawei-nc-1.0:huawei-nc-1.0";
  tailf:ncs-device-type "netconf";

  yang-version 1;
  namespace "urn:huawei:yang:huawei-monitor-group";
  prefix monitor-group;

  import huawei-ifm {
    prefix ifm;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Global monitor group configuration.";

  revision 2020-03-09 {
    description
      "Fix trigger-up-delay units.";
    reference "Huawei private.";
  }
  revision 2019-04-28 {
    description
      "Initial revision.";
    reference "Huawei private.";
  }
  ext:task-name "interface-mgr";

  typedef ncs_template_status-type {
    type string;
    description
      "Status type is like inactive/active.";
  }

  typedef ncs_rpc_notif_status-type {
    type enumeration {
      enum "inactive" {
        value 0;
        description
          "The status of monitor group is inactive.";
      }
      enum "active" {
        value 1;
        description
          "The status of monitor group is active.";
      }
    }
    description
      "Status type is like inactive/active.";
  }

  typedef live_ncs_status-type {
    type enumeration {
      enum "inactive" {
        value 0;
        description
          "The status of monitor group is inactive.";
      }
      enum "active" {
        value 1;
        description
          "The status of monitor group is active.";
      }
    }
    description
      "Status type is like inactive/active.";
  }

  typedef status-type {
    type enumeration {
      enum "inactive" {
        value 0;
        description
          "The status of monitor group is inactive.";
      }
      enum "active" {
        value 1;
        description
          "The status of monitor group is active.";
      }
    }
    description
      "Status type is like inactive/active.";
  }

  augment "/ncs:devices/ncs:device/ncs:config" {
    container monitor-group {
      tailf:ncs-device-type "netconf";
      tailf:display-when "not(../../ncs:module) or ../../ncs:module[ncs:name='huawei-monitor-group']";
      description
        "Global monitor group configuration.";
      container groups {
        description
          "List of monitor groups.";
        list group {
          key "name";
          description
            "Configure this table to operate monitor groups on devices.";
          leaf name {
            type string {
              length "1..31";
            }
            description
              "Specifies the name of an interface monitoring group.";
          }
          leaf trigger-up-delay {
            type uint32 {
              range "0..4294967295";
            }
            units "s";
            default "0";
            description
              "Delay for a track interface to go up.";
          }
          leaf enable-status {
            type status-type;
            default "inactive";
            description
              "Status of monitor group.";
          }
          container binding-ifs {
            description
              "List of monitor group binding interfaces.";
            list binding-if {
              key "if-name";
              max-elements 32;
              description
                "Configure monitor group binding interface.";
              leaf if-name {
                type leafref {
                  path "/ncs:devices/ncs:device/ncs:config/ifm:ifm/ifm:interfaces/ifm:interface/ifm:name" {
                    tailf:xpath-root 3;
                  }
                }
                description
                  "Name of monitor group binding interface.";
              }
              leaf down-weight {
                type uint32 {
                  range "1..1000";
                }
                default "10";
                description
                  "Down weight of monitor group binding interface.";
              }
            }
          }
        }
      }
    }
  }
  augment "/ncs:devices/ncs:device/ncs:live-status" {
    container monitor-group {
      tailf:ncs-device-type "netconf";
      tailf:display-when "not(../../ncs:module) or ../../ncs:module[ncs:name='huawei-monitor-group'] or (../../ncs:live-status-protocol[not(ncs:capability)]) or (../../ncs:live-status-protocol/ncs:capability/ncs:module[.='huawei-monitor-group'])";
      description
        "Global monitor group configuration.";
      container groups {
        description
          "List of monitor groups.";
        list group {
          key "name";
          description
            "Configure this table to operate monitor groups on devices.";
          leaf name {
            type string {
              length "1..31";
            }
            description
              "Specifies the name of an interface monitoring group.";
          }
          leaf trigger-up-delay {
            type uint32 {
              range "0..4294967295";
            }
            units "s";
            // NCS drop default statement
            description
              "Delay for a track interface to go up.";
          }
          leaf enable-status {
            type live_ncs_status-type;
            // NCS drop default statement
            description
              "Status of monitor group.";
          }
          container binding-ifs {
            description
              "List of monitor group binding interfaces.";
            list binding-if {
              key "if-name";
              // NCS drop max-elements statement
              description
                "Configure monitor group binding interface.";
              leaf if-name {
                type leafref {
                  path "/ncs:devices/ncs:device/ncs:live-status/ifm:ifm/ifm:interfaces/ifm:interface/ifm:name" {
                    tailf:xpath-root 3;
                  }
                }
                description
                  "Name of monitor group binding interface.";
              }
              leaf down-weight {
                type uint32 {
                  range "1..1000";
                }
                // NCS drop default statement
                description
                  "Down weight of monitor group binding interface.";
              }
            }
          }
        }
      }
    }
  }
  augment "/ncs:devices/ncs:template/ncs:ned-id/ncs:config" {
    container monitor-group {
      description
        "Global monitor group configuration.";
      container groups {
        description
          "List of monitor groups.";
        list group {
          // NCS patched for predictable order
          ordered-by user;
          key "name";
          description
            "Configure this table to operate monitor groups on devices.";
          leaf name {
            type string;
            description
              "Specifies the name of an interface monitoring group.";
          }
          leaf trigger-up-delay {
            type string;
            units "s";
            // NCS drop default statement
            description
              "Delay for a track interface to go up.";
          }
          leaf enable-status {
            type ncs_template_status-type;
            // NCS drop default statement
            description
              "Status of monitor group.";
          }
          container binding-ifs {
            description
              "List of monitor group binding interfaces.";
            list binding-if {
              // NCS patched for predictable order
              ordered-by user;
              key "if-name";
              // NCS drop max-elements statement
              description
                "Configure monitor group binding interface.";
              leaf if-name {
                type string;
                description
                  "Name of monitor group binding interface.";
              }
              leaf down-weight {
                type string;
                // NCS drop default statement
                description
                  "Down weight of monitor group binding interface.";
              }
            }
          }
        }
      }
    }
  }
  augment "/ncs:devices/ncs:template/ncs:ned-id/ncs:config/ifm:ifm/ifm:interfaces/ifm:interface" {
    description
      "A set of track interfaces.";
    container track-monitor-group {
      description
        "Configure a set of track interfaces.";
      leaf name {
        type string;
        description
          "The monitoring group was tracked under the interface.";
      }
      leaf down-weight {
        // NCS drop when statement
        type string;
        description
          "Trigger down weight of a track interface.";
      }
    }
  }
  augment "/ncs:devices/ncs:device/ncs:live-status/ifm:ifm/ifm:interfaces/ifm:interface" {
    description
      "A set of track interfaces.";
    container track-monitor-group {
      tailf:ncs-device-type "netconf";
      tailf:display-when "not(../../../../../ncs:module) or ../../../../../ncs:module[ncs:name='huawei-monitor-group'] or (../../../../../ncs:live-status-protocol[not(ncs:capability)]) or (../../../../../ncs:live-status-protocol/ncs:capability/ncs:module[.='huawei-monitor-group'])";
      description
        "Configure a set of track interfaces.";
      leaf name {
        type leafref {
          path "/ncs:devices/ncs:device/ncs:live-status/monitor-group:monitor-group/monitor-group:groups/monitor-group:group/monitor-group:name" {
            tailf:xpath-root 3;
          }
        }
        description
          "The monitoring group was tracked under the interface.";
      }
      leaf down-weight {
        // NCS drop when statement
        type uint32 {
          range "1..1000";
        }
        description
          "Trigger down weight of a track interface.";
      }
    }
  }
  augment "/ncs:devices/ncs:device/ncs:config/ifm:ifm/ifm:interfaces/ifm:interface" {
    description
      "A set of track interfaces.";
    container track-monitor-group {
      tailf:ncs-device-type "netconf";
      tailf:display-when "not(../../../../../ncs:module) or ../../../../../ncs:module[ncs:name='huawei-monitor-group']";
      description
        "Configure a set of track interfaces.";
      leaf name {
        type leafref {
          path "/ncs:devices/ncs:device/ncs:config/monitor-group:monitor-group/monitor-group:groups/monitor-group:group/monitor-group:name" {
            tailf:xpath-root 3;
          }
        }
        description
          "The monitoring group was tracked under the interface.";
      }
      leaf down-weight {
        when '../name' {
          tailf:xpath-root 3;
        }
        type uint32 {
          range "1..1000";
        }
        description
          "Trigger down weight of a track interface.";
      }
    }
  }
}
