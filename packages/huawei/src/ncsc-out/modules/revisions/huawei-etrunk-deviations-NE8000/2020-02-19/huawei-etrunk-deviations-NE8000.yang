module huawei-etrunk-deviations-NE8000 {
  // Generated by yanger -t ncs
  tailf:mount-id "huawei-nc-1.0:huawei-nc-1.0";
  tailf:ncs-device-type "netconf";

  yang-version 1;
  namespace "urn:huawei:yang:huawei-etrunk-deviations-NE8000";
  prefix etrunk-devs-NE8000;

  import huawei-etrunk {
    prefix etrunk;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Enhanced Trunk (E-Trunk) is a mechanism that controls and implements link aggregation among multiple devices. E-Trunk implements device-level not board-level link reliability.";

  revision 2020-02-19 {
    description
      "Init revision.";
    reference "Huawei private.";
  }

  deviation "/ncs:devices/ncs:template/ncs:ned-id/ncs:config/etrunk:etrunk/etrunk:instances/etrunk:instance/etrunk:security-key-type" {
    deviate delete {
      // NCS drop default statement
    }
  }
  deviation "/ncs:devices/ncs:device/ncs:live-status/etrunk:etrunk/etrunk:instances/etrunk:instance/etrunk:security-key-type" {
    deviate delete {
      // NCS drop default statement
    }
  }
  deviation "/ncs:devices/ncs:device/ncs:config/etrunk:etrunk/etrunk:instances/etrunk:instance/etrunk:security-key-type" {
    deviate delete {
      default "simple";
    }
  }
  deviation "/ncs:devices/ncs:template/ncs:ned-id/ncs:config/etrunk:etrunk/etrunk:instances/etrunk:instance/etrunk:security-key-type" {
    deviate add {
      // NCS drop must statement
    }
  }
  deviation "/ncs:devices/ncs:device/ncs:live-status/etrunk:etrunk/etrunk:instances/etrunk:instance/etrunk:security-key-type" {
    deviate add {
      // NCS drop must statement
    }
  }
  deviation "/ncs:devices/ncs:device/ncs:config/etrunk:etrunk/etrunk:instances/etrunk:instance/etrunk:security-key-type" {
    deviate add {
      must '../security-key and ../security-key-type' {
        tailf:xpath-root 3;
      }
    }
  }
  deviation "/ncs:devices/ncs:template/ncs:ned-id/ncs:config/etrunk:etrunk/etrunk:instances/etrunk:instance/etrunk:security-key" {
    deviate add {
      // NCS drop must statement
    }
  }
  deviation "/ncs:devices/ncs:device/ncs:live-status/etrunk:etrunk/etrunk:instances/etrunk:instance/etrunk:security-key" {
    deviate add {
      // NCS drop must statement
    }
  }
  deviation "/ncs:devices/ncs:device/ncs:config/etrunk:etrunk/etrunk:instances/etrunk:instance/etrunk:security-key" {
    deviate add {
      must '../security-key and ../security-key-type' {
        tailf:xpath-root 3;
      }
    }
  }
  deviation "/ncs:devices/ncs:template/ncs:ned-id/ncs:config/etrunk:etrunk/etrunk:instances/etrunk:instance/etrunk:id" {
    deviate replace {
      type string;
    }
  }
  deviation "/ncs:devices/ncs:device/ncs:live-status/etrunk:etrunk/etrunk:instances/etrunk:instance/etrunk:id" {
    deviate replace {
      type uint16 {
        range "1..512";
      }
    }
  }
  deviation "/ncs:devices/ncs:device/ncs:config/etrunk:etrunk/etrunk:instances/etrunk:instance/etrunk:id" {
    deviate replace {
      type uint16 {
        range "1..512";
      }
    }
  }
}
