module huawei-ifm-hdlc {
  // Generated by yanger -t ncs
  tailf:mount-id "huawei-nc-1.0:huawei-nc-1.0";
  tailf:ncs-device-type "netconf";

  yang-version 1;
  namespace "urn:huawei:yang:huawei-ifm-hdlc";
  prefix ifm-hdlc;

  import huawei-ifm {
    prefix ifm;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "High-level data link control protocol.";

  revision 2019-12-22 {
    description
      "Initial revision.";
    reference "Huawei private.";
  }
  ext:task-name "hdlc";

  typedef ncs_template_damp-level {
    type string;
    description
      "HDLC damp level.";
  }

  typedef ncs_rpc_notif_damp-level {
    type enumeration {
      enum "light" {
        value 0;
        description
          "Light weight.";
      }
      enum "middle" {
        value 1;
        description
          "Middle weight.";
      }
      enum "heavy" {
        value 2;
        description
          "Heavy weight.";
      }
      enum "manual" {
        value 3;
        description
          "Manually configure the parameters.";
      }
    }
    description
      "HDLC damp level.";
  }

  typedef live_ncs_damp-level {
    type enumeration {
      enum "light" {
        value 0;
        description
          "Light weight.";
      }
      enum "middle" {
        value 1;
        description
          "Middle weight.";
      }
      enum "heavy" {
        value 2;
        description
          "Heavy weight.";
      }
      enum "manual" {
        value 3;
        description
          "Manually configure the parameters.";
      }
    }
    description
      "HDLC damp level.";
  }

  typedef damp-level {
    type enumeration {
      enum "light" {
        value 0;
        description
          "Light weight.";
      }
      enum "middle" {
        value 1;
        description
          "Middle weight.";
      }
      enum "heavy" {
        value 2;
        description
          "Heavy weight.";
      }
      enum "manual" {
        value 3;
        description
          "Manually configure the parameters.";
      }
    }
    description
      "HDLC damp level.";
  }

  augment "/ncs:devices/ncs:template/ncs:ned-id/ncs:config/ifm:ifm" {
    description
      "Configure extend interface attributes.";
    container hdlc-damp {
      // NCS drop must statement
      description
        "Configure HDLC link status damping, the suppress value must be less than the value of reuse x (2 to the power of (max-suppress-time/half-lifeperiod)).";
      leaf enable {
        type string;
        // NCS drop default statement
        description
          "Enable/disable the HDLC link status damping.";
      }
      leaf damp-level {
        // NCS drop when statement
        type ncs_template_damp-level;
        // NCS drop default statement
        description
          "HDLC link status damping level.";
      }
      leaf suppress {
        // NCS drop when statement
        type string;
        units "s";
        // NCS drop must statement
        description
          "1000 times of suppress threshold.";
      }
      leaf reuse {
        // NCS drop when statement
        type string;
        units "s";
        // NCS drop must statement
        description
          "1000 times of reuse threshold.";
      }
      leaf max-suppress-time {
        // NCS drop when statement
        type string;
        units "s";
        description
          "Max suppress time.";
      }
      leaf half-lifeperiod {
        // NCS drop when statement
        type string;
        units "s";
        description
          "HDLC protocol status damping half life time.";
      }
    }
  }
  augment "/ncs:devices/ncs:device/ncs:live-status/ifm:ifm" {
    description
      "Configure extend interface attributes.";
    container hdlc-damp {
      tailf:ncs-device-type "netconf";
      tailf:display-when "not(../../../ncs:module) or ../../../ncs:module[ncs:name='huawei-ifm-hdlc'] or (../../../ncs:live-status-protocol[not(ncs:capability)]) or (../../../ncs:live-status-protocol/ncs:capability/ncs:module[.='huawei-ifm-hdlc'])";
      // NCS drop must statement
      description
        "Configure HDLC link status damping, the suppress value must be less than the value of reuse x (2 to the power of (max-suppress-time/half-lifeperiod)).";
      leaf enable {
        type boolean;
        // NCS drop default statement
        description
          "Enable/disable the HDLC link status damping.";
      }
      leaf damp-level {
        // NCS drop when statement
        type live_ncs_damp-level;
        // NCS drop default statement
        description
          "HDLC link status damping level.";
      }
      leaf suppress {
        // NCS drop when statement
        type uint32 {
          range "2..20000";
        }
        units "s";
        // NCS drop must statement
        description
          "1000 times of suppress threshold.";
      }
      leaf reuse {
        // NCS drop when statement
        type uint32 {
          range "1..19999";
        }
        units "s";
        // NCS drop must statement
        description
          "1000 times of reuse threshold.";
      }
      leaf max-suppress-time {
        // NCS drop when statement
        type uint16 {
          range "1..255";
        }
        units "s";
        description
          "Max suppress time.";
      }
      leaf half-lifeperiod {
        // NCS drop when statement
        type uint16 {
          range "1..60";
        }
        units "s";
        description
          "HDLC protocol status damping half life time.";
      }
    }
  }
  augment "/ncs:devices/ncs:device/ncs:config/ifm:ifm" {
    description
      "Configure extend interface attributes.";
    container hdlc-damp {
      tailf:ncs-device-type "netconf";
      tailf:display-when "not(../../../ncs:module) or ../../../ncs:module[ncs:name='huawei-ifm-hdlc']";
      must "(damp-level='manual' and suppress and reuse and max-suppress-time and half-lifeperiod) or (damp-level!='manual')" {
        tailf:xpath-root 3;
      }
      description
        "Configure HDLC link status damping, the suppress value must be less than the value of reuse x (2 to the power of (max-suppress-time/half-lifeperiod)).";
      leaf enable {
        type boolean;
        default "true";
        description
          "Enable/disable the HDLC link status damping.";
      }
      leaf damp-level {
        when "../enable='true'" {
          tailf:xpath-root 3;
        }
        type damp-level;
        default "light";
        description
          "HDLC link status damping level.";
      }
      leaf suppress {
        when "../enable='true' and ../damp-level='manual'" {
          tailf:xpath-root 3;
        }
        type uint32 {
          range "2..20000";
        }
        units "s";
        must '../suppress>../reuse' {
          tailf:xpath-root 3;
        }
        description
          "1000 times of suppress threshold.";
      }
      leaf reuse {
        when "../enable='true' and ../damp-level='manual'" {
          tailf:xpath-root 3;
        }
        type uint32 {
          range "1..19999";
        }
        units "s";
        must '../suppress>../reuse' {
          tailf:xpath-root 3;
        }
        description
          "1000 times of reuse threshold.";
      }
      leaf max-suppress-time {
        when "../enable='true' and ../damp-level='manual'" {
          tailf:xpath-root 3;
        }
        type uint16 {
          range "1..255";
        }
        units "s";
        description
          "Max suppress time.";
      }
      leaf half-lifeperiod {
        when "../enable='true' and ../damp-level='manual'" {
          tailf:xpath-root 3;
        }
        type uint16 {
          range "1..60";
        }
        units "s";
        description
          "HDLC protocol status damping half life time.";
      }
    }
  }
}
