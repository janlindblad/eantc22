module huawei-ssl {
  // Generated by yanger -t ncs
  tailf:mount-id "huawei-nc-1.0:huawei-nc-1.0";
  tailf:ncs-device-type "netconf";

  namespace "urn:huawei:yang:huawei-ssl";
  prefix ssl;

  import huawei-extension {
    prefix ext;
  }
  import huawei-pub-type {
    prefix pub-type;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Secure Socket Layer (SSL)";

  revision 2020-07-02 {
    description
      "Initial revision.";
    reference "Huawei private.";
  }
  ext:task-name "ssl";

  typedef ncs_template_ssl-password-type {
    type pub-type:ncs_template_password-extend;
    description
      "SSL password type.";
  }

  typedef ncs_template_ssl-cert-type {
    type string;
    description
      "SSL certification type list.";
  }

  typedef ncs_template_ssl-key-type {
    type string;
    description
      "SSL public key encryption type list.";
  }

  typedef ncs_template_ssl-crl-type {
    type string;
    description
      "Certification revocation type list.";
  }

  typedef ncs_template_ssl-ca-type {
    type string;
    description
      "Certificate authority type list.";
  }

  typedef ncs_template_ssl-version {
    type string;
    description
      "SSL version type list.";
  }

  typedef ncs_template_encrypted {
    type string;
    description
      "SSL encrypted flag list.";
  }

  typedef ncs_template_ssl-bool {
    type string;
    description
      "Certificate Verify bool switch.";
  }

  typedef ncs_template_ssl-cipher-type {
    type string;
    description
      "Enumeration of ssl cipher type.";
  }

  typedef ncs_rpc_notif_ssl-password-type {
    type pub-type:ncs_rpc_notif_password-extend;
    description
      "SSL password type.";
  }

  typedef ncs_rpc_notif_ssl-cert-type {
    type enumeration {
      enum "asn1-cert" {
        value 1;
        description
          "Certype_asn1.";
      }
      enum "pem-cert" {
        value 2;
        description
          "Certype_pem.";
      }
      enum "pfx-cert" {
        value 3;
        description
          "Certype_pfx.";
      }
      enum "pem-chain" {
        value 4;
        description
          "Certype_pem-chain.";
      }
    }
    description
      "SSL certification type list.";
  }

  typedef ncs_rpc_notif_ssl-key-type {
    type enumeration {
      enum "rsa" {
        value 1;
        description
          "Keytype_rsa.";
      }
      enum "dsa" {
        value 2;
        description
          "Keytype_dsa.";
      }
    }
    description
      "SSL public key encryption type list.";
  }

  typedef ncs_rpc_notif_ssl-crl-type {
    type enumeration {
      enum "asn1-crl" {
        value 1;
        description
          "Crltype_asn1.";
      }
      enum "pem-crl" {
        value 2;
        description
          "Crltype_pem.";
      }
    }
    description
      "Certification revocation type list.";
  }

  typedef ncs_rpc_notif_ssl-ca-type {
    type enumeration {
      enum "asn1-ca" {
        value 1;
        description
          "Catype_asn1-ca.";
      }
      enum "pem-ca" {
        value 2;
        description
          "Catype_pem-ca.";
      }
      enum "pfx-ca" {
        value 3;
        description
          "Catype_pfx-ca.";
      }
    }
    description
      "Certificate authority type list.";
  }

  typedef ncs_rpc_notif_ssl-version {
    type enumeration {
      enum "tls1.0" {
        value 2;
        status obsolete;
        description
          "SSL version tls1.0. This version is insecure and is not supported currently. It is used for query compatibility only.";
      }
      enum "tls1.1" {
        value 3;
        description
          "SSL version tls1.1.";
      }
      enum "tls1.2" {
        value 4;
        description
          "SSL version tls1.2.";
      }
      enum "tls1.3" {
        value 5;
        description
          "SSL version tls1.3.";
      }
    }
    description
      "SSL version type list.";
  }

  typedef ncs_rpc_notif_encrypted {
    type enumeration {
      enum "ISENCRYPTED" {
        value 0;
        description
          "IS ENCRYPTED.";
      }
      enum "NOTENCRYPTED" {
        value 1;
        description
          "NOT ENCRYPTED.";
      }
    }
    description
      "SSL encrypted flag list.";
  }

  typedef ncs_rpc_notif_ssl-bool {
    type enumeration {
      enum "enable" {
        value 1;
        description
          "Service Enable.";
      }
      enum "disable" {
        value 2;
        description
          "Service Disable.";
      }
    }
    description
      "Certificate Verify bool switch.";
  }

  typedef ncs_rpc_notif_ssl-cipher-type {
    type enumeration {
      enum "rsa-with-aes-256-sha" {
        value 1;
        description
          "RSA-WITH-AES-256-SHA cipher suite.";
      }
      enum "rsa-with-aes-128-sha" {
        value 2;
        description
          "RSA-WITH-AES-128-SHA cipher suite.";
      }
      enum "dhe-rsa-with-aes-256-sha" {
        value 3;
        description
          "DHE-RSA-WITH-AES-256-SHA cipher suite.";
      }
      enum "dhe-dss-with-aes-256-sha" {
        value 4;
        description
          "DHE-DSS-WITH-AES-256-SHA cipher suite.";
      }
      enum "dhe-rsa-with-aes-128-sha" {
        value 5;
        description
          "DHE-RSA-WITH-AES-128-SHA cipher suite.";
      }
      enum "dhe-dss-with-aes-128-sha" {
        value 6;
        description
          "DHE-DSS-WITH-AES-128-SHA cipher suite.";
      }
      enum "rsa-aes-128-cbc-sha" {
        value 7;
        description
          "RSA-AES-128-CBC-SHA cipher suite.";
      }
      enum "rsa-aes-256-cbc-sha" {
        value 8;
        description
          "RSA-AES-256-CBC-SHA cipher suite.";
      }
      enum "rsa-aes-128-cbc-sha256" {
        value 9;
        description
          "RSA-AES-128-CBC-SHA256 cipher suite.";
      }
      enum "rsa-aes-256-cbc-sha256" {
        value 10;
        description
          "RSA-AES-256-CBC-SHA256 cipher suite.";
      }
      enum "dhe-dss-aes-128-cbc-sha" {
        value 11;
        description
          "DHE-DSS-AES-128-CBC-SHA cipher suite.";
      }
      enum "dhe-rsa-aes-128-cbc-sha" {
        value 12;
        description
          "DHE-RSA-AES-128-CBC-SHA cipher suite.";
      }
      enum "dhe-dss-aes-256-cbc-sha" {
        value 13;
        description
          "DHE-DSS-AES-256-CBC-SHA cipher suite.";
      }
      enum "dhe-rsa-aes-256-cbc-sha" {
        value 14;
        description
          "DHE-RSA-AES-256-CBC-SHA cipher suite.";
      }
      enum "dhe-dss-aes-128-cbc-sha256" {
        value 15;
        description
          "DHE-DSS-AES-128-CBC-SHA256 cipher suite.";
      }
      enum "dhe-rsa-aes-128-cbc-sha256" {
        value 16;
        description
          "DHE-RSA-AES-128-CBC-SHA256 cipher suite.";
      }
      enum "dhe-dss-aes-256-cbc-sha256" {
        value 17;
        description
          "DHE-DSS-AES-256-CBC-SHA256 cipher suite.";
      }
      enum "dhe-rsa-aes-256-cbc-sha256" {
        value 18;
        description
          "DHE-RSA-AES-256-CBC-SHA256 cipher suite.";
      }
      enum "rsa-with-aes-128-gcm-sha256" {
        value 19;
        description
          "RSA-WITH-AES-128-GCM-SHA256 cipher suite.";
      }
      enum "rsa-with-aes-256-gcm-sha384" {
        value 20;
        description
          "RSA-WITH-AES-256-GCM-SHA384 cipher suite.";
      }
      enum "dhe-rsa-with-aes-128-gcm-sha256" {
        value 21;
        description
          "DHE-RSA-WITH-AES-128-GCM-SHA256 cipher suite.";
      }
      enum "dhe-rsa-with-aes-256-gcm-sha384" {
        value 22;
        description
          "DHE-RSA-WITH-AES-256-GCM-SHA384 cipher suite.";
      }
      enum "dhe-dss-with-aes-128-gcm-sha256" {
        value 23;
        description
          "DHE-DSS-WITH-AES-128-GCM-SHA256 cipher suite.";
      }
      enum "dhe-dss-with-aes-256-gcm-sha384" {
        value 24;
        description
          "DHE-DSS-WITH-AES-256-GCM-SHA384 cipher suite.";
      }
      enum "ecdhe-rsa-with-aes-128-gcm-sha256" {
        value 25;
        description
          "ECDHE-RSA-WITH-AES-128-GCM-SHA256 cipher suite.";
      }
      enum "ecdhe-rsa-with-aes-256-gcm-sha384" {
        value 26;
        description
          "ECDHE-RSA-WITH-AES-256-GCM-SHA384 cipher suite.";
      }
      enum "aes-128-gcm-sha256" {
        value 27;
        description
          "AES-128-GCM-SHA256 cipher suite.";
      }
      enum "aes-256-gcm-sha384" {
        value 28;
        description
          "AES_256_GCM_SHA384 cipher suite.";
      }
      enum "chacha20-poly1305-sha256" {
        value 29;
        description
          "CHACHA20_POLY1305_SHA256 cipher suite.";
      }
      enum "aes-128-ccm-sha256" {
        value 30;
        description
          "AES_128_CCM_SHA256 cipher suite.";
      }
    }
    description
      "Enumeration of ssl cipher type.";
  }

  typedef live_ncs_ssl-password-type {
    type pub-type:live_ncs_password-extend;
    description
      "SSL password type.";
  }

  typedef live_ncs_ssl-cert-type {
    type enumeration {
      enum "asn1-cert" {
        value 1;
        description
          "Certype_asn1.";
      }
      enum "pem-cert" {
        value 2;
        description
          "Certype_pem.";
      }
      enum "pfx-cert" {
        value 3;
        description
          "Certype_pfx.";
      }
      enum "pem-chain" {
        value 4;
        description
          "Certype_pem-chain.";
      }
    }
    description
      "SSL certification type list.";
  }

  typedef live_ncs_ssl-key-type {
    type enumeration {
      enum "rsa" {
        value 1;
        description
          "Keytype_rsa.";
      }
      enum "dsa" {
        value 2;
        description
          "Keytype_dsa.";
      }
    }
    description
      "SSL public key encryption type list.";
  }

  typedef live_ncs_ssl-crl-type {
    type enumeration {
      enum "asn1-crl" {
        value 1;
        description
          "Crltype_asn1.";
      }
      enum "pem-crl" {
        value 2;
        description
          "Crltype_pem.";
      }
    }
    description
      "Certification revocation type list.";
  }

  typedef live_ncs_ssl-ca-type {
    type enumeration {
      enum "asn1-ca" {
        value 1;
        description
          "Catype_asn1-ca.";
      }
      enum "pem-ca" {
        value 2;
        description
          "Catype_pem-ca.";
      }
      enum "pfx-ca" {
        value 3;
        description
          "Catype_pfx-ca.";
      }
    }
    description
      "Certificate authority type list.";
  }

  typedef live_ncs_ssl-version {
    type enumeration {
      enum "tls1.0" {
        value 2;
        status obsolete;
        description
          "SSL version tls1.0. This version is insecure and is not supported currently. It is used for query compatibility only.";
      }
      enum "tls1.1" {
        value 3;
        description
          "SSL version tls1.1.";
      }
      enum "tls1.2" {
        value 4;
        description
          "SSL version tls1.2.";
      }
      enum "tls1.3" {
        value 5;
        description
          "SSL version tls1.3.";
      }
    }
    description
      "SSL version type list.";
  }

  typedef live_ncs_encrypted {
    type enumeration {
      enum "ISENCRYPTED" {
        value 0;
        description
          "IS ENCRYPTED.";
      }
      enum "NOTENCRYPTED" {
        value 1;
        description
          "NOT ENCRYPTED.";
      }
    }
    description
      "SSL encrypted flag list.";
  }

  typedef live_ncs_ssl-bool {
    type enumeration {
      enum "enable" {
        value 1;
        description
          "Service Enable.";
      }
      enum "disable" {
        value 2;
        description
          "Service Disable.";
      }
    }
    description
      "Certificate Verify bool switch.";
  }

  typedef live_ncs_ssl-cipher-type {
    type enumeration {
      enum "rsa-with-aes-256-sha" {
        value 1;
        description
          "RSA-WITH-AES-256-SHA cipher suite.";
      }
      enum "rsa-with-aes-128-sha" {
        value 2;
        description
          "RSA-WITH-AES-128-SHA cipher suite.";
      }
      enum "dhe-rsa-with-aes-256-sha" {
        value 3;
        description
          "DHE-RSA-WITH-AES-256-SHA cipher suite.";
      }
      enum "dhe-dss-with-aes-256-sha" {
        value 4;
        description
          "DHE-DSS-WITH-AES-256-SHA cipher suite.";
      }
      enum "dhe-rsa-with-aes-128-sha" {
        value 5;
        description
          "DHE-RSA-WITH-AES-128-SHA cipher suite.";
      }
      enum "dhe-dss-with-aes-128-sha" {
        value 6;
        description
          "DHE-DSS-WITH-AES-128-SHA cipher suite.";
      }
      enum "rsa-aes-128-cbc-sha" {
        value 7;
        description
          "RSA-AES-128-CBC-SHA cipher suite.";
      }
      enum "rsa-aes-256-cbc-sha" {
        value 8;
        description
          "RSA-AES-256-CBC-SHA cipher suite.";
      }
      enum "rsa-aes-128-cbc-sha256" {
        value 9;
        description
          "RSA-AES-128-CBC-SHA256 cipher suite.";
      }
      enum "rsa-aes-256-cbc-sha256" {
        value 10;
        description
          "RSA-AES-256-CBC-SHA256 cipher suite.";
      }
      enum "dhe-dss-aes-128-cbc-sha" {
        value 11;
        description
          "DHE-DSS-AES-128-CBC-SHA cipher suite.";
      }
      enum "dhe-rsa-aes-128-cbc-sha" {
        value 12;
        description
          "DHE-RSA-AES-128-CBC-SHA cipher suite.";
      }
      enum "dhe-dss-aes-256-cbc-sha" {
        value 13;
        description
          "DHE-DSS-AES-256-CBC-SHA cipher suite.";
      }
      enum "dhe-rsa-aes-256-cbc-sha" {
        value 14;
        description
          "DHE-RSA-AES-256-CBC-SHA cipher suite.";
      }
      enum "dhe-dss-aes-128-cbc-sha256" {
        value 15;
        description
          "DHE-DSS-AES-128-CBC-SHA256 cipher suite.";
      }
      enum "dhe-rsa-aes-128-cbc-sha256" {
        value 16;
        description
          "DHE-RSA-AES-128-CBC-SHA256 cipher suite.";
      }
      enum "dhe-dss-aes-256-cbc-sha256" {
        value 17;
        description
          "DHE-DSS-AES-256-CBC-SHA256 cipher suite.";
      }
      enum "dhe-rsa-aes-256-cbc-sha256" {
        value 18;
        description
          "DHE-RSA-AES-256-CBC-SHA256 cipher suite.";
      }
      enum "rsa-with-aes-128-gcm-sha256" {
        value 19;
        description
          "RSA-WITH-AES-128-GCM-SHA256 cipher suite.";
      }
      enum "rsa-with-aes-256-gcm-sha384" {
        value 20;
        description
          "RSA-WITH-AES-256-GCM-SHA384 cipher suite.";
      }
      enum "dhe-rsa-with-aes-128-gcm-sha256" {
        value 21;
        description
          "DHE-RSA-WITH-AES-128-GCM-SHA256 cipher suite.";
      }
      enum "dhe-rsa-with-aes-256-gcm-sha384" {
        value 22;
        description
          "DHE-RSA-WITH-AES-256-GCM-SHA384 cipher suite.";
      }
      enum "dhe-dss-with-aes-128-gcm-sha256" {
        value 23;
        description
          "DHE-DSS-WITH-AES-128-GCM-SHA256 cipher suite.";
      }
      enum "dhe-dss-with-aes-256-gcm-sha384" {
        value 24;
        description
          "DHE-DSS-WITH-AES-256-GCM-SHA384 cipher suite.";
      }
      enum "ecdhe-rsa-with-aes-128-gcm-sha256" {
        value 25;
        description
          "ECDHE-RSA-WITH-AES-128-GCM-SHA256 cipher suite.";
      }
      enum "ecdhe-rsa-with-aes-256-gcm-sha384" {
        value 26;
        description
          "ECDHE-RSA-WITH-AES-256-GCM-SHA384 cipher suite.";
      }
      enum "aes-128-gcm-sha256" {
        value 27;
        description
          "AES-128-GCM-SHA256 cipher suite.";
      }
      enum "aes-256-gcm-sha384" {
        value 28;
        description
          "AES_256_GCM_SHA384 cipher suite.";
      }
      enum "chacha20-poly1305-sha256" {
        value 29;
        description
          "CHACHA20_POLY1305_SHA256 cipher suite.";
      }
      enum "aes-128-ccm-sha256" {
        value 30;
        description
          "AES_128_CCM_SHA256 cipher suite.";
      }
    }
    description
      "Enumeration of ssl cipher type.";
  }

  typedef ssl-password-type {
    type pub-type:password-extend;
    description
      "SSL password type.";
  }

  typedef ssl-cert-type {
    type enumeration {
      enum "asn1-cert" {
        value 1;
        description
          "Certype_asn1.";
      }
      enum "pem-cert" {
        value 2;
        description
          "Certype_pem.";
      }
      enum "pfx-cert" {
        value 3;
        description
          "Certype_pfx.";
      }
      enum "pem-chain" {
        value 4;
        description
          "Certype_pem-chain.";
      }
    }
    description
      "SSL certification type list.";
  }

  typedef ssl-key-type {
    type enumeration {
      enum "rsa" {
        value 1;
        description
          "Keytype_rsa.";
      }
      enum "dsa" {
        value 2;
        description
          "Keytype_dsa.";
      }
    }
    description
      "SSL public key encryption type list.";
  }

  typedef ssl-crl-type {
    type enumeration {
      enum "asn1-crl" {
        value 1;
        description
          "Crltype_asn1.";
      }
      enum "pem-crl" {
        value 2;
        description
          "Crltype_pem.";
      }
    }
    description
      "Certification revocation type list.";
  }

  typedef ssl-ca-type {
    type enumeration {
      enum "asn1-ca" {
        value 1;
        description
          "Catype_asn1-ca.";
      }
      enum "pem-ca" {
        value 2;
        description
          "Catype_pem-ca.";
      }
      enum "pfx-ca" {
        value 3;
        description
          "Catype_pfx-ca.";
      }
    }
    description
      "Certificate authority type list.";
  }

  typedef ssl-version {
    type enumeration {
      enum "tls1.0" {
        value 2;
        status obsolete;
        description
          "SSL version tls1.0. This version is insecure and is not supported currently. It is used for query compatibility only.";
      }
      enum "tls1.1" {
        value 3;
        description
          "SSL version tls1.1.";
      }
      enum "tls1.2" {
        value 4;
        description
          "SSL version tls1.2.";
      }
      enum "tls1.3" {
        value 5;
        description
          "SSL version tls1.3.";
      }
    }
    description
      "SSL version type list.";
  }

  typedef encrypted {
    type enumeration {
      enum "ISENCRYPTED" {
        value 0;
        description
          "IS ENCRYPTED.";
      }
      enum "NOTENCRYPTED" {
        value 1;
        description
          "NOT ENCRYPTED.";
      }
    }
    description
      "SSL encrypted flag list.";
  }

  typedef ssl-bool {
    type enumeration {
      enum "enable" {
        value 1;
        description
          "Service Enable.";
      }
      enum "disable" {
        value 2;
        description
          "Service Disable.";
      }
    }
    description
      "Certificate Verify bool switch.";
  }

  typedef ssl-cipher-type {
    type enumeration {
      enum "rsa-with-aes-256-sha" {
        value 1;
        description
          "RSA-WITH-AES-256-SHA cipher suite.";
      }
      enum "rsa-with-aes-128-sha" {
        value 2;
        description
          "RSA-WITH-AES-128-SHA cipher suite.";
      }
      enum "dhe-rsa-with-aes-256-sha" {
        value 3;
        description
          "DHE-RSA-WITH-AES-256-SHA cipher suite.";
      }
      enum "dhe-dss-with-aes-256-sha" {
        value 4;
        description
          "DHE-DSS-WITH-AES-256-SHA cipher suite.";
      }
      enum "dhe-rsa-with-aes-128-sha" {
        value 5;
        description
          "DHE-RSA-WITH-AES-128-SHA cipher suite.";
      }
      enum "dhe-dss-with-aes-128-sha" {
        value 6;
        description
          "DHE-DSS-WITH-AES-128-SHA cipher suite.";
      }
      enum "rsa-aes-128-cbc-sha" {
        value 7;
        description
          "RSA-AES-128-CBC-SHA cipher suite.";
      }
      enum "rsa-aes-256-cbc-sha" {
        value 8;
        description
          "RSA-AES-256-CBC-SHA cipher suite.";
      }
      enum "rsa-aes-128-cbc-sha256" {
        value 9;
        description
          "RSA-AES-128-CBC-SHA256 cipher suite.";
      }
      enum "rsa-aes-256-cbc-sha256" {
        value 10;
        description
          "RSA-AES-256-CBC-SHA256 cipher suite.";
      }
      enum "dhe-dss-aes-128-cbc-sha" {
        value 11;
        description
          "DHE-DSS-AES-128-CBC-SHA cipher suite.";
      }
      enum "dhe-rsa-aes-128-cbc-sha" {
        value 12;
        description
          "DHE-RSA-AES-128-CBC-SHA cipher suite.";
      }
      enum "dhe-dss-aes-256-cbc-sha" {
        value 13;
        description
          "DHE-DSS-AES-256-CBC-SHA cipher suite.";
      }
      enum "dhe-rsa-aes-256-cbc-sha" {
        value 14;
        description
          "DHE-RSA-AES-256-CBC-SHA cipher suite.";
      }
      enum "dhe-dss-aes-128-cbc-sha256" {
        value 15;
        description
          "DHE-DSS-AES-128-CBC-SHA256 cipher suite.";
      }
      enum "dhe-rsa-aes-128-cbc-sha256" {
        value 16;
        description
          "DHE-RSA-AES-128-CBC-SHA256 cipher suite.";
      }
      enum "dhe-dss-aes-256-cbc-sha256" {
        value 17;
        description
          "DHE-DSS-AES-256-CBC-SHA256 cipher suite.";
      }
      enum "dhe-rsa-aes-256-cbc-sha256" {
        value 18;
        description
          "DHE-RSA-AES-256-CBC-SHA256 cipher suite.";
      }
      enum "rsa-with-aes-128-gcm-sha256" {
        value 19;
        description
          "RSA-WITH-AES-128-GCM-SHA256 cipher suite.";
      }
      enum "rsa-with-aes-256-gcm-sha384" {
        value 20;
        description
          "RSA-WITH-AES-256-GCM-SHA384 cipher suite.";
      }
      enum "dhe-rsa-with-aes-128-gcm-sha256" {
        value 21;
        description
          "DHE-RSA-WITH-AES-128-GCM-SHA256 cipher suite.";
      }
      enum "dhe-rsa-with-aes-256-gcm-sha384" {
        value 22;
        description
          "DHE-RSA-WITH-AES-256-GCM-SHA384 cipher suite.";
      }
      enum "dhe-dss-with-aes-128-gcm-sha256" {
        value 23;
        description
          "DHE-DSS-WITH-AES-128-GCM-SHA256 cipher suite.";
      }
      enum "dhe-dss-with-aes-256-gcm-sha384" {
        value 24;
        description
          "DHE-DSS-WITH-AES-256-GCM-SHA384 cipher suite.";
      }
      enum "ecdhe-rsa-with-aes-128-gcm-sha256" {
        value 25;
        description
          "ECDHE-RSA-WITH-AES-128-GCM-SHA256 cipher suite.";
      }
      enum "ecdhe-rsa-with-aes-256-gcm-sha384" {
        value 26;
        description
          "ECDHE-RSA-WITH-AES-256-GCM-SHA384 cipher suite.";
      }
      enum "aes-128-gcm-sha256" {
        value 27;
        description
          "AES-128-GCM-SHA256 cipher suite.";
      }
      enum "aes-256-gcm-sha384" {
        value 28;
        description
          "AES_256_GCM_SHA384 cipher suite.";
      }
      enum "chacha20-poly1305-sha256" {
        value 29;
        description
          "CHACHA20_POLY1305_SHA256 cipher suite.";
      }
      enum "aes-128-ccm-sha256" {
        value 30;
        description
          "AES_128_CCM_SHA256 cipher suite.";
      }
    }
    description
      "Enumeration of ssl cipher type.";
  }

  augment "/ncs:devices/ncs:device/ncs:config" {
    container ssl {
      tailf:ncs-device-type "netconf";
      tailf:display-when "not(../../ncs:module) or ../../ncs:module[ncs:name='huawei-ssl']";
      description
        "Secure Socket Layer (SSL)";
      container ssl-policys {
        description
          "List of all SSL policys.";
        list ssl-policy {
          key "policy-name";
          max-elements 4;
          description
            "Configure SSL policy, which is a collection of certificate and certification agency's. Other features can use the SSL policy by referring to the SSL policy name.";
          leaf policy-name {
            type string {
              length "1..23";
              pattern '[a-z0-9_]*';
            }
            description
              "Name for identifying an SSL policy, the ranging from 1 to 23. You can only use underline, letter and digit. The letter does not differentiate the capital, and will transforms to the small letter.";
          }
          leaf mini-version {
            type ssl-version;
            default "tls1.2";
            description
              "Set SSL version, surport tls1.1 and tls1.2, the defult value is tls1.2.";
          }
          leaf cert-ver3-enable {
            type ssl-bool;
            default "disable";
            description
              "Whether to enable X509v3 verification for certificates.";
          }
          leaf crl-ver2-enable {
            type ssl-bool;
            default "disable";
            description
              "Whether to enable X509v2 verification for CRLs.";
          }
          leaf basic-const-enable {
            type ssl-bool;
            default "disable";
            description
              "Whether to enable Basic Constraints Field verification for certificates.";
          }
          leaf mini-path-len {
            type uint32 {
              range "1..1024";
            }
            default "1";
            description
              "Whether to enable minimum path length verification for certificates.";
          }
          leaf key-usage-enable {
            type ssl-bool;
            default "disable";
            description
              "Whether to enable Key Usage Field verification for certificates.";
          }
          leaf diffie-hellman-modulus {
            type uint32 {
              range "2048 | 3072 | 4096";
            }
            default "3072";
            description
              "Set modulus for diffie-hellman key exchange algorithm.";
          }
          container ecdh-group {
            when '/ssl:ssl/ssl:ssl-policys/ssl:ssl-policy/ssl:policy-name' {
              tailf:xpath-root 3;
            }
            must "not (./nist='false' and ./curve='false' and ./brainpool='false')" {
              tailf:xpath-root 3;
            }
            description
              "Configure the ecdh groups for SSL policy.";
            leaf nist {
              type boolean;
              default "false";
              description
                "Enable/disable nist groups of ecdh.";
            }
            leaf curve {
              type boolean;
              default "true";
              description
                "Enable/disable curve groups of ecdh.";
            }
            leaf brainpool {
              type boolean;
              default "true";
              description
                "Enable/disable brainpool groups of ecdh.";
            }
          }
          container signature-alg {
            when '/ssl:ssl/ssl:ssl-policys/ssl:ssl-policy/ssl:policy-name' {
              tailf:xpath-root 3;
            }
            must "not (./ecdsa-secp256r1-sha256='false' and ./ecdsa-secp384r1-sha384='false' and ./ecdsa-secp521r1-sha512='false' and ./rsa-pss-pss-sha256='false' and ./rsa-pss-pss-sha384='false' and ./rsa-pss-pss-sha512='false' and ./rsa-pss-rsae-sha256='false' and ./rsa-pss-rsae-sha384='false' and ./rsa-pss-rsae-sha512='false' and ./rsa-pkcs1-sha256='false' and ./rsa-pkcs1-sha384='false' and ./rsa-pkcs1-sha512='false' and ./ecdsa-sha1='false' and ./ecdsa-sha224='false' and ./rsa-sha1='false' and ./rsa-sha224='false' and ./dsa-sha1='false' and ./dsa-sha224='false' and ./ed25519='false' and ./ed448='false' and ./dsa-sha256='false' and ./dsa-sha384='false' and ./dsa-sha512='false')" {
              tailf:xpath-root 3;
            }
            description
              "Configure signature algorithms for SSL policy.";
            leaf ecdsa-secp256r1-sha256 {
              type boolean;
              default "false";
              description
                "Enable/disable ecdsa-secp256r1-sha256 signature algorithm.";
            }
            leaf ecdsa-secp384r1-sha384 {
              type boolean;
              default "false";
              description
                "Enable/disable ecdsa-secp384r1-sha384 signature algorithm.";
            }
            leaf ecdsa-secp521r1-sha512 {
              type boolean;
              default "false";
              description
                "Enable/disable ecdsa-secp521r1-sha512 signature algorithm.";
            }
            leaf ed25519 {
              type boolean;
              default "true";
              description
                "Enable/disable ed25519 signature algorithm.";
            }
            leaf ed448 {
              type boolean;
              default "true";
              description
                "Enable/disable ed448 signature algorithm.";
            }
            leaf rsa-pss-pss-sha256 {
              type boolean;
              default "true";
              description
                "Enable/disable rsa-pss-pss-sha256 signature algorithm.";
            }
            leaf rsa-pss-pss-sha384 {
              type boolean;
              default "true";
              description
                "Enable/disable rsa-pss-pss-sha384 signature algorithm.";
            }
            leaf rsa-pss-pss-sha512 {
              type boolean;
              default "true";
              description
                "Enable/disable rsa-pss-pss-sha512 signature algorithm.";
            }
            leaf rsa-pss-rsae-sha256 {
              type boolean;
              default "true";
              description
                "Enable/disable rsa-pss-rsae-sha256 signature algorithm.";
            }
            leaf rsa-pss-rsae-sha384 {
              type boolean;
              default "true";
              description
                "Enable/disable rsa-pss-rsae-sha384 signature algorithm.";
            }
            leaf rsa-pss-rsae-sha512 {
              type boolean;
              default "true";
              description
                "Enable/disable rsa-pss-rsae-sha512 signature algorithm.";
            }
            leaf rsa-pkcs1-sha256 {
              type boolean;
              default "false";
              description
                "Enable/disable rsa-pkcs1-sha256 signature algorithm.";
            }
            leaf rsa-pkcs1-sha384 {
              type boolean;
              default "false";
              description
                "Enable/disable rsa-pkcs1-sha384 signature algorithm.";
            }
            leaf rsa-pkcs1-sha512 {
              type boolean;
              default "false";
              description
                "Enable/disable rsa-pkcs1-sha512 signature algorithm.";
            }
            leaf ecdsa-sha1 {
              type boolean;
              default "false";
              description
                "Enable/disable ecdsa-sha1 signature algorithm.";
            }
            leaf ecdsa-sha224 {
              type boolean;
              default "false";
              description
                "Enable/disable ecdsa-sha224 signature algorithm.";
            }
            leaf rsa-sha1 {
              type boolean;
              default "false";
              description
                "Enable/disable rsa-sha1 signature algorithm.";
            }
            leaf rsa-sha224 {
              type boolean;
              default "false";
              description
                "Enable/disable rsa-sha224 signature algorithm.";
            }
            leaf dsa-sha1 {
              type boolean;
              default "false";
              description
                "Enable/disable dsa-sha1 signature algorithm.";
            }
            leaf dsa-sha224 {
              type boolean;
              default "false";
              description
                "Enable/disable dsa-sha224 signature algorithm.";
            }
            leaf dsa-sha256 {
              type boolean;
              default "false";
              description
                "Enable/disable dsa-sha256 signature algorithm.";
            }
            leaf dsa-sha384 {
              type boolean;
              default "false";
              description
                "Enable/disable dsa-sha384 signature algorithm.";
            }
            leaf dsa-sha512 {
              type boolean;
              default "false";
              description
                "Enable/disable dsa-sha512 signature algorithm.";
            }
          }
          container cert-loads {
            when '/ssl:ssl/ssl:ssl-policys/ssl:ssl-policy/ssl:policy-name' {
              tailf:xpath-root 3;
            }
            description
              "List of all SSL certificate file loaded by SSL policy.";
            list cert-load {
              key "cert-file";
              description
                "Configure SSL certificate file loaded by SSL policy.";
              leaf cert-file {
                type string {
                  length "1..64";
                }
                description
                  "Cert file.";
              }
              leaf cert-type {
                type ssl-cert-type;
                must "(../cert-type='pfx-cert' and ((../is-mac and ../is-mac=1 and not (../key-file)) or (../key-file and not (../is-mac)))) or (../cert-type!='pfx-cert' and ../key-file and not (../is-mac))" {
                  tailf:xpath-root 3;
                }
                mandatory true;
                description
                  "CertType.";
              }
              leaf auth-code-crt {
                when "not(../cert-type='asn1-cert')" {
                  tailf:xpath-root 3;
                }
                type ssl-password-type {
                  length "1..168";
                }
                mandatory true;
                description
                  "AuthCode.";
              }
              leaf is-mac {
                when "(../cert-type='pfx-cert')" {
                  tailf:xpath-root 3;
                }
                type uint32 {
                  range "0..1";
                }
                description
                  "Mark for using MAC.";
              }
              leaf key-type {
                type ssl-key-type;
                mandatory true;
                description
                  "KeyType.";
              }
              leaf auth-code-mac {
                when "(../cert-type='pfx-cert' and ../is-mac=1)" {
                  tailf:xpath-root 3;
                }
                type ssl-password-type {
                  length "1..168";
                }
                mandatory true;
                description
                  "AuthCodeMac.";
              }
              leaf key-file {
                when 'not(../is-mac)' {
                  tailf:xpath-root 3;
                }
                type string {
                  length "1..64";
                }
                description
                  "KeyFile.";
              }
              // NCS drop config false leaf 'issuer-name'
              // NCS drop config false leaf 'valid-not-before'
              // NCS drop config false leaf 'valid-not-after'
              // NCS drop config false leaf 'is-cert-file-encrypted'
            }
          }
          container crl-loads {
            when '/ssl:ssl/ssl:ssl-policys/ssl:ssl-policy/ssl:policy-name' {
              tailf:xpath-root 3;
            }
            description
              "List of sslCrlLoad.";
            list crl-load {
              key "crl-file";
              max-elements 2;
              description
                "Configure sslCrlLoad policy.";
              leaf crl-file {
                type string {
                  length "1..64";
                }
                description
                  "CrlFile.";
              }
              leaf crl-type {
                type ssl-crl-type;
                mandatory true;
                description
                  "CrlType.";
              }
            }
          }
          container trust-ca-loads {
            when '/ssl:ssl/ssl:ssl-policys/ssl:ssl-policy/ssl:policy-name' {
              tailf:xpath-root 3;
            }
            description
              "List of sslTrustCALoads.";
            list trust-ca-load {
              key "ca-file";
              max-elements 4;
              description
                "Configure sslTrustCALoad policy.";
              leaf ca-file {
                type string {
                  length "1..64";
                }
                description
                  "CaFile.";
              }
              leaf ca-type {
                type ssl-ca-type;
                mandatory true;
                description
                  "CaType.";
              }
              leaf auth-code {
                when "not(../ca-type!='pfx-ca')" {
                  tailf:xpath-root 3;
                }
                type ssl-password-type {
                  length "1..168";
                }
                description
                  "AuthCode.";
              }
            }
          }
          leaf cipher-suite-name {
            type leafref {
              path "/ncs:devices/ncs:device/ncs:config/ssl:ssl/ssl:ssl-cipher-suites/ssl:ssl-cipher-suite/ssl:cipher-suite-name" {
                tailf:xpath-root 3;
              }
            }
            description
              "Name for identifying a cipher suite name.";
          }
          leaf exclude-rsa-kex {
            type ssl-bool;
            default "enable";
            description
              "Whether to exclude RSA key exchange algorithm.";
          }
          leaf exclude-hmac-sha1 {
            type ssl-bool;
            default "enable";
            description
              "Whether to exclude SHA-1 HMAC algorithm.";
          }
          leaf exclude-ciphermode-cbc {
            type ssl-bool;
            default "enable";
            description
              "Whether to exclude Cipher Block Chaining (CBC) mode algorithm.";
          }
        }
      }
      container ssl-cipher-suites {
        description
          "List of SSL cipher suites to configure.";
        list ssl-cipher-suite {
          key "cipher-suite-name";
          description
            "Configure SSL cipher suite.";
          leaf cipher-suite-name {
            type string {
              length "1..32";
              pattern '[a-z0-9_\*]*';
            }
            description
              "Configure name of cipher suite policy.";
          }
          leaf-list ssl-ciphers {
            type ssl-cipher-type;
            max-elements 4096;
            description
              "Configure list of SSL ciphers to configure policy.";
          }
        }
      }
    }
  }
  augment "/ncs:devices/ncs:device/ncs:live-status" {
    container ssl {
      tailf:ncs-device-type "netconf";
      tailf:display-when "not(../../ncs:module) or ../../ncs:module[ncs:name='huawei-ssl'] or (../../ncs:live-status-protocol[not(ncs:capability)]) or (../../ncs:live-status-protocol/ncs:capability/ncs:module[.='huawei-ssl'])";
      description
        "Secure Socket Layer (SSL)";
      container ssl-policys {
        description
          "List of all SSL policys.";
        list ssl-policy {
          key "policy-name";
          // NCS drop max-elements statement
          description
            "Configure SSL policy, which is a collection of certificate and certification agency's. Other features can use the SSL policy by referring to the SSL policy name.";
          leaf policy-name {
            type string {
              length "1..23";
              pattern '[a-z0-9_]*';
            }
            description
              "Name for identifying an SSL policy, the ranging from 1 to 23. You can only use underline, letter and digit. The letter does not differentiate the capital, and will transforms to the small letter.";
          }
          leaf mini-version {
            type live_ncs_ssl-version;
            // NCS drop default statement
            description
              "Set SSL version, surport tls1.1 and tls1.2, the defult value is tls1.2.";
          }
          leaf cert-ver3-enable {
            type live_ncs_ssl-bool;
            // NCS drop default statement
            description
              "Whether to enable X509v3 verification for certificates.";
          }
          leaf crl-ver2-enable {
            type live_ncs_ssl-bool;
            // NCS drop default statement
            description
              "Whether to enable X509v2 verification for CRLs.";
          }
          leaf basic-const-enable {
            type live_ncs_ssl-bool;
            // NCS drop default statement
            description
              "Whether to enable Basic Constraints Field verification for certificates.";
          }
          leaf mini-path-len {
            type uint32 {
              range "1..1024";
            }
            // NCS drop default statement
            description
              "Whether to enable minimum path length verification for certificates.";
          }
          leaf key-usage-enable {
            type live_ncs_ssl-bool;
            // NCS drop default statement
            description
              "Whether to enable Key Usage Field verification for certificates.";
          }
          leaf diffie-hellman-modulus {
            type uint32 {
              range "2048 | 3072 | 4096";
            }
            // NCS drop default statement
            description
              "Set modulus for diffie-hellman key exchange algorithm.";
          }
          container ecdh-group {
            // NCS drop when statement
            // NCS drop must statement
            description
              "Configure the ecdh groups for SSL policy.";
            leaf nist {
              type boolean;
              // NCS drop default statement
              description
                "Enable/disable nist groups of ecdh.";
            }
            leaf curve {
              type boolean;
              // NCS drop default statement
              description
                "Enable/disable curve groups of ecdh.";
            }
            leaf brainpool {
              type boolean;
              // NCS drop default statement
              description
                "Enable/disable brainpool groups of ecdh.";
            }
          }
          container signature-alg {
            // NCS drop when statement
            // NCS drop must statement
            description
              "Configure signature algorithms for SSL policy.";
            leaf ecdsa-secp256r1-sha256 {
              type boolean;
              // NCS drop default statement
              description
                "Enable/disable ecdsa-secp256r1-sha256 signature algorithm.";
            }
            leaf ecdsa-secp384r1-sha384 {
              type boolean;
              // NCS drop default statement
              description
                "Enable/disable ecdsa-secp384r1-sha384 signature algorithm.";
            }
            leaf ecdsa-secp521r1-sha512 {
              type boolean;
              // NCS drop default statement
              description
                "Enable/disable ecdsa-secp521r1-sha512 signature algorithm.";
            }
            leaf ed25519 {
              type boolean;
              // NCS drop default statement
              description
                "Enable/disable ed25519 signature algorithm.";
            }
            leaf ed448 {
              type boolean;
              // NCS drop default statement
              description
                "Enable/disable ed448 signature algorithm.";
            }
            leaf rsa-pss-pss-sha256 {
              type boolean;
              // NCS drop default statement
              description
                "Enable/disable rsa-pss-pss-sha256 signature algorithm.";
            }
            leaf rsa-pss-pss-sha384 {
              type boolean;
              // NCS drop default statement
              description
                "Enable/disable rsa-pss-pss-sha384 signature algorithm.";
            }
            leaf rsa-pss-pss-sha512 {
              type boolean;
              // NCS drop default statement
              description
                "Enable/disable rsa-pss-pss-sha512 signature algorithm.";
            }
            leaf rsa-pss-rsae-sha256 {
              type boolean;
              // NCS drop default statement
              description
                "Enable/disable rsa-pss-rsae-sha256 signature algorithm.";
            }
            leaf rsa-pss-rsae-sha384 {
              type boolean;
              // NCS drop default statement
              description
                "Enable/disable rsa-pss-rsae-sha384 signature algorithm.";
            }
            leaf rsa-pss-rsae-sha512 {
              type boolean;
              // NCS drop default statement
              description
                "Enable/disable rsa-pss-rsae-sha512 signature algorithm.";
            }
            leaf rsa-pkcs1-sha256 {
              type boolean;
              // NCS drop default statement
              description
                "Enable/disable rsa-pkcs1-sha256 signature algorithm.";
            }
            leaf rsa-pkcs1-sha384 {
              type boolean;
              // NCS drop default statement
              description
                "Enable/disable rsa-pkcs1-sha384 signature algorithm.";
            }
            leaf rsa-pkcs1-sha512 {
              type boolean;
              // NCS drop default statement
              description
                "Enable/disable rsa-pkcs1-sha512 signature algorithm.";
            }
            leaf ecdsa-sha1 {
              type boolean;
              // NCS drop default statement
              description
                "Enable/disable ecdsa-sha1 signature algorithm.";
            }
            leaf ecdsa-sha224 {
              type boolean;
              // NCS drop default statement
              description
                "Enable/disable ecdsa-sha224 signature algorithm.";
            }
            leaf rsa-sha1 {
              type boolean;
              // NCS drop default statement
              description
                "Enable/disable rsa-sha1 signature algorithm.";
            }
            leaf rsa-sha224 {
              type boolean;
              // NCS drop default statement
              description
                "Enable/disable rsa-sha224 signature algorithm.";
            }
            leaf dsa-sha1 {
              type boolean;
              // NCS drop default statement
              description
                "Enable/disable dsa-sha1 signature algorithm.";
            }
            leaf dsa-sha224 {
              type boolean;
              // NCS drop default statement
              description
                "Enable/disable dsa-sha224 signature algorithm.";
            }
            leaf dsa-sha256 {
              type boolean;
              // NCS drop default statement
              description
                "Enable/disable dsa-sha256 signature algorithm.";
            }
            leaf dsa-sha384 {
              type boolean;
              // NCS drop default statement
              description
                "Enable/disable dsa-sha384 signature algorithm.";
            }
            leaf dsa-sha512 {
              type boolean;
              // NCS drop default statement
              description
                "Enable/disable dsa-sha512 signature algorithm.";
            }
          }
          container cert-loads {
            // NCS drop when statement
            description
              "List of all SSL certificate file loaded by SSL policy.";
            list cert-load {
              key "cert-file";
              description
                "Configure SSL certificate file loaded by SSL policy.";
              leaf cert-file {
                type string {
                  length "1..64";
                }
                description
                  "Cert file.";
              }
              leaf cert-type {
                type live_ncs_ssl-cert-type;
                // NCS drop must statement
                // NCS drop mandatory statement
                description
                  "CertType.";
              }
              leaf auth-code-crt {
                // NCS drop when statement
                type live_ncs_ssl-password-type;
                // NCS drop mandatory statement
                description
                  "AuthCode.";
              }
              leaf is-mac {
                // NCS drop when statement
                type uint32 {
                  range "0..1";
                }
                description
                  "Mark for using MAC.";
              }
              leaf key-type {
                type live_ncs_ssl-key-type;
                // NCS drop mandatory statement
                description
                  "KeyType.";
              }
              leaf auth-code-mac {
                // NCS drop when statement
                type live_ncs_ssl-password-type;
                // NCS drop mandatory statement
                description
                  "AuthCodeMac.";
              }
              leaf key-file {
                // NCS drop when statement
                type string {
                  length "1..64";
                }
                description
                  "KeyFile.";
              }
              leaf issuer-name {
                // NCS drop when statement
                type string {
                  length "1..255";
                }
                description
                  "Issuer name.";
              }
              leaf valid-not-before {
                // NCS drop when statement
                type string {
                  length "1..255";
                }
                description
                  "Validity Not Before.";
              }
              leaf valid-not-after {
                // NCS drop when statement
                type string {
                  length "1..255";
                }
                description
                  "Validity Not After.";
              }
              leaf is-cert-file-encrypted {
                type live_ncs_encrypted;
                description
                  "Is cert-file Encrypted.";
              }
            }
          }
          container crl-loads {
            // NCS drop when statement
            description
              "List of sslCrlLoad.";
            list crl-load {
              key "crl-file";
              // NCS drop max-elements statement
              description
                "Configure sslCrlLoad policy.";
              leaf crl-file {
                type string {
                  length "1..64";
                }
                description
                  "CrlFile.";
              }
              leaf crl-type {
                type live_ncs_ssl-crl-type;
                // NCS drop mandatory statement
                description
                  "CrlType.";
              }
            }
          }
          container trust-ca-loads {
            // NCS drop when statement
            description
              "List of sslTrustCALoads.";
            list trust-ca-load {
              key "ca-file";
              // NCS drop max-elements statement
              description
                "Configure sslTrustCALoad policy.";
              leaf ca-file {
                type string {
                  length "1..64";
                }
                description
                  "CaFile.";
              }
              leaf ca-type {
                type live_ncs_ssl-ca-type;
                // NCS drop mandatory statement
                description
                  "CaType.";
              }
              leaf auth-code {
                // NCS drop when statement
                type live_ncs_ssl-password-type;
                description
                  "AuthCode.";
              }
            }
          }
          leaf cipher-suite-name {
            type leafref {
              path "/ncs:devices/ncs:device/ncs:live-status/ssl:ssl/ssl:ssl-cipher-suites/ssl:ssl-cipher-suite/ssl:cipher-suite-name" {
                tailf:xpath-root 3;
              }
            }
            description
              "Name for identifying a cipher suite name.";
          }
          leaf exclude-rsa-kex {
            type live_ncs_ssl-bool;
            // NCS drop default statement
            description
              "Whether to exclude RSA key exchange algorithm.";
          }
          leaf exclude-hmac-sha1 {
            type live_ncs_ssl-bool;
            // NCS drop default statement
            description
              "Whether to exclude SHA-1 HMAC algorithm.";
          }
          leaf exclude-ciphermode-cbc {
            type live_ncs_ssl-bool;
            // NCS drop default statement
            description
              "Whether to exclude Cipher Block Chaining (CBC) mode algorithm.";
          }
        }
      }
      container ssl-cipher-suites {
        description
          "List of SSL cipher suites to configure.";
        list ssl-cipher-suite {
          key "cipher-suite-name";
          description
            "Configure SSL cipher suite.";
          leaf cipher-suite-name {
            type string {
              length "1..32";
              pattern '[a-z0-9_\*]*';
            }
            description
              "Configure name of cipher suite policy.";
          }
          leaf-list ssl-ciphers {
            type live_ncs_ssl-cipher-type;
            // NCS drop max-elements statement
            description
              "Configure list of SSL ciphers to configure policy.";
          }
        }
      }
    }
  }
  augment "/ncs:devices/ncs:template/ncs:ned-id/ncs:config" {
    container ssl {
      description
        "Secure Socket Layer (SSL)";
      container ssl-policys {
        description
          "List of all SSL policys.";
        list ssl-policy {
          // NCS patched for predictable order
          ordered-by user;
          key "policy-name";
          // NCS drop max-elements statement
          description
            "Configure SSL policy, which is a collection of certificate and certification agency's. Other features can use the SSL policy by referring to the SSL policy name.";
          leaf policy-name {
            type string;
            description
              "Name for identifying an SSL policy, the ranging from 1 to 23. You can only use underline, letter and digit. The letter does not differentiate the capital, and will transforms to the small letter.";
          }
          leaf mini-version {
            type ncs_template_ssl-version;
            // NCS drop default statement
            description
              "Set SSL version, surport tls1.1 and tls1.2, the defult value is tls1.2.";
          }
          leaf cert-ver3-enable {
            type ncs_template_ssl-bool;
            // NCS drop default statement
            description
              "Whether to enable X509v3 verification for certificates.";
          }
          leaf crl-ver2-enable {
            type ncs_template_ssl-bool;
            // NCS drop default statement
            description
              "Whether to enable X509v2 verification for CRLs.";
          }
          leaf basic-const-enable {
            type ncs_template_ssl-bool;
            // NCS drop default statement
            description
              "Whether to enable Basic Constraints Field verification for certificates.";
          }
          leaf mini-path-len {
            type string;
            // NCS drop default statement
            description
              "Whether to enable minimum path length verification for certificates.";
          }
          leaf key-usage-enable {
            type ncs_template_ssl-bool;
            // NCS drop default statement
            description
              "Whether to enable Key Usage Field verification for certificates.";
          }
          leaf diffie-hellman-modulus {
            type string;
            // NCS drop default statement
            description
              "Set modulus for diffie-hellman key exchange algorithm.";
          }
          container ecdh-group {
            // NCS drop when statement
            // NCS drop must statement
            description
              "Configure the ecdh groups for SSL policy.";
            leaf nist {
              type string;
              // NCS drop default statement
              description
                "Enable/disable nist groups of ecdh.";
            }
            leaf curve {
              type string;
              // NCS drop default statement
              description
                "Enable/disable curve groups of ecdh.";
            }
            leaf brainpool {
              type string;
              // NCS drop default statement
              description
                "Enable/disable brainpool groups of ecdh.";
            }
          }
          container signature-alg {
            // NCS drop when statement
            // NCS drop must statement
            description
              "Configure signature algorithms for SSL policy.";
            leaf ecdsa-secp256r1-sha256 {
              type string;
              // NCS drop default statement
              description
                "Enable/disable ecdsa-secp256r1-sha256 signature algorithm.";
            }
            leaf ecdsa-secp384r1-sha384 {
              type string;
              // NCS drop default statement
              description
                "Enable/disable ecdsa-secp384r1-sha384 signature algorithm.";
            }
            leaf ecdsa-secp521r1-sha512 {
              type string;
              // NCS drop default statement
              description
                "Enable/disable ecdsa-secp521r1-sha512 signature algorithm.";
            }
            leaf ed25519 {
              type string;
              // NCS drop default statement
              description
                "Enable/disable ed25519 signature algorithm.";
            }
            leaf ed448 {
              type string;
              // NCS drop default statement
              description
                "Enable/disable ed448 signature algorithm.";
            }
            leaf rsa-pss-pss-sha256 {
              type string;
              // NCS drop default statement
              description
                "Enable/disable rsa-pss-pss-sha256 signature algorithm.";
            }
            leaf rsa-pss-pss-sha384 {
              type string;
              // NCS drop default statement
              description
                "Enable/disable rsa-pss-pss-sha384 signature algorithm.";
            }
            leaf rsa-pss-pss-sha512 {
              type string;
              // NCS drop default statement
              description
                "Enable/disable rsa-pss-pss-sha512 signature algorithm.";
            }
            leaf rsa-pss-rsae-sha256 {
              type string;
              // NCS drop default statement
              description
                "Enable/disable rsa-pss-rsae-sha256 signature algorithm.";
            }
            leaf rsa-pss-rsae-sha384 {
              type string;
              // NCS drop default statement
              description
                "Enable/disable rsa-pss-rsae-sha384 signature algorithm.";
            }
            leaf rsa-pss-rsae-sha512 {
              type string;
              // NCS drop default statement
              description
                "Enable/disable rsa-pss-rsae-sha512 signature algorithm.";
            }
            leaf rsa-pkcs1-sha256 {
              type string;
              // NCS drop default statement
              description
                "Enable/disable rsa-pkcs1-sha256 signature algorithm.";
            }
            leaf rsa-pkcs1-sha384 {
              type string;
              // NCS drop default statement
              description
                "Enable/disable rsa-pkcs1-sha384 signature algorithm.";
            }
            leaf rsa-pkcs1-sha512 {
              type string;
              // NCS drop default statement
              description
                "Enable/disable rsa-pkcs1-sha512 signature algorithm.";
            }
            leaf ecdsa-sha1 {
              type string;
              // NCS drop default statement
              description
                "Enable/disable ecdsa-sha1 signature algorithm.";
            }
            leaf ecdsa-sha224 {
              type string;
              // NCS drop default statement
              description
                "Enable/disable ecdsa-sha224 signature algorithm.";
            }
            leaf rsa-sha1 {
              type string;
              // NCS drop default statement
              description
                "Enable/disable rsa-sha1 signature algorithm.";
            }
            leaf rsa-sha224 {
              type string;
              // NCS drop default statement
              description
                "Enable/disable rsa-sha224 signature algorithm.";
            }
            leaf dsa-sha1 {
              type string;
              // NCS drop default statement
              description
                "Enable/disable dsa-sha1 signature algorithm.";
            }
            leaf dsa-sha224 {
              type string;
              // NCS drop default statement
              description
                "Enable/disable dsa-sha224 signature algorithm.";
            }
            leaf dsa-sha256 {
              type string;
              // NCS drop default statement
              description
                "Enable/disable dsa-sha256 signature algorithm.";
            }
            leaf dsa-sha384 {
              type string;
              // NCS drop default statement
              description
                "Enable/disable dsa-sha384 signature algorithm.";
            }
            leaf dsa-sha512 {
              type string;
              // NCS drop default statement
              description
                "Enable/disable dsa-sha512 signature algorithm.";
            }
          }
          container cert-loads {
            // NCS drop when statement
            description
              "List of all SSL certificate file loaded by SSL policy.";
            list cert-load {
              // NCS patched for predictable order
              ordered-by user;
              key "cert-file";
              description
                "Configure SSL certificate file loaded by SSL policy.";
              leaf cert-file {
                type string;
                description
                  "Cert file.";
              }
              leaf cert-type {
                type ncs_template_ssl-cert-type;
                // NCS drop must statement
                // NCS drop mandatory statement
                description
                  "CertType.";
              }
              leaf auth-code-crt {
                // NCS drop when statement
                type ncs_template_ssl-password-type;
                // NCS drop mandatory statement
                description
                  "AuthCode.";
              }
              leaf is-mac {
                // NCS drop when statement
                type string;
                description
                  "Mark for using MAC.";
              }
              leaf key-type {
                type ncs_template_ssl-key-type;
                // NCS drop mandatory statement
                description
                  "KeyType.";
              }
              leaf auth-code-mac {
                // NCS drop when statement
                type ncs_template_ssl-password-type;
                // NCS drop mandatory statement
                description
                  "AuthCodeMac.";
              }
              leaf key-file {
                // NCS drop when statement
                type string;
                description
                  "KeyFile.";
              }
              // NCS drop config false leaf 'issuer-name'
              // NCS drop config false leaf 'valid-not-before'
              // NCS drop config false leaf 'valid-not-after'
              // NCS drop config false leaf 'is-cert-file-encrypted'
            }
          }
          container crl-loads {
            // NCS drop when statement
            description
              "List of sslCrlLoad.";
            list crl-load {
              // NCS patched for predictable order
              ordered-by user;
              key "crl-file";
              // NCS drop max-elements statement
              description
                "Configure sslCrlLoad policy.";
              leaf crl-file {
                type string;
                description
                  "CrlFile.";
              }
              leaf crl-type {
                type ncs_template_ssl-crl-type;
                // NCS drop mandatory statement
                description
                  "CrlType.";
              }
            }
          }
          container trust-ca-loads {
            // NCS drop when statement
            description
              "List of sslTrustCALoads.";
            list trust-ca-load {
              // NCS patched for predictable order
              ordered-by user;
              key "ca-file";
              // NCS drop max-elements statement
              description
                "Configure sslTrustCALoad policy.";
              leaf ca-file {
                type string;
                description
                  "CaFile.";
              }
              leaf ca-type {
                type ncs_template_ssl-ca-type;
                // NCS drop mandatory statement
                description
                  "CaType.";
              }
              leaf auth-code {
                // NCS drop when statement
                type ncs_template_ssl-password-type;
                description
                  "AuthCode.";
              }
            }
          }
          leaf cipher-suite-name {
            type string;
            description
              "Name for identifying a cipher suite name.";
          }
          leaf exclude-rsa-kex {
            type ncs_template_ssl-bool;
            // NCS drop default statement
            description
              "Whether to exclude RSA key exchange algorithm.";
          }
          leaf exclude-hmac-sha1 {
            type ncs_template_ssl-bool;
            // NCS drop default statement
            description
              "Whether to exclude SHA-1 HMAC algorithm.";
          }
          leaf exclude-ciphermode-cbc {
            type ncs_template_ssl-bool;
            // NCS drop default statement
            description
              "Whether to exclude Cipher Block Chaining (CBC) mode algorithm.";
          }
        }
      }
      container ssl-cipher-suites {
        description
          "List of SSL cipher suites to configure.";
        list ssl-cipher-suite {
          // NCS patched for predictable order
          ordered-by user;
          key "cipher-suite-name";
          description
            "Configure SSL cipher suite.";
          leaf cipher-suite-name {
            type string;
            description
              "Configure name of cipher suite policy.";
          }
          leaf-list ssl-ciphers {
            // NCS patched for predictable order
            ordered-by user;
            type ncs_template_ssl-cipher-type;
            // NCS drop max-elements statement
            description
              "Configure list of SSL ciphers to configure policy.";
          }
        }
      }
    }
  }
}
