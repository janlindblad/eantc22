module huawei-bier {
  // Generated by yanger -t ncs
  tailf:mount-id "huawei-nc-1.0:huawei-nc-1.0";
  tailf:ncs-device-type "netconf";

  namespace "urn:huawei:yang:huawei-bier";
  prefix bier;

  import ietf-inet-types {
    prefix inet;
  }
  import huawei-extension {
    prefix ext;
  }
  import huawei-pub-type {
    prefix pub-type;
  }
  import huawei-ifm {
    prefix ifm;
  }
  import huawei-ip {
    prefix ip;
  }
  import huawei-srv6 {
    prefix srv6;
  }
  import huawei-network-instance {
    prefix ni;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Model for Bit Index Explicit Replication (BIER).";

  revision 2020-02-21 {
    description
      "Modify prefixs container to bier; Modify description.";
    reference "Huawei private.";
  }
  revision 2019-09-06 {
    description
      "Init revision.";
    reference "Huawei private.";
  }
  ext:task-name "bier";

  typedef ncs_template_underlay-protocol-type {
    type string;
    description
      "BIER underlay protocol type.";
  }

  typedef ncs_template_bit-string-length {
    type string;
    description
      "Enumerated values of the BitString length.";
  }

  typedef ncs_template_igp-algorithm-type {
    type string;
    description
      "IGP algorithm type.";
  }

  typedef ncs_template_bier-algorithm-type {
    type string;
    description
      "BIER algorithm type.";
  }

  typedef ncs_template_bier-encapsulation-type {
    type string;
    description
      "Encapsulation types for BIER.";
  }

  typedef ncs_template_address-family-type {
    type string;
    description
      "Address family.";
  }

  typedef ncs_template_birt-nexthop-invalid-type {
    type string;
    description
      "Reason for the invalid nexthop.";
  }

  typedef ncs_rpc_notif_underlay-protocol-type {
    type enumeration {
      enum "ospf" {
        value 1;
        description
          "OSPF.";
      }
      enum "isis" {
        value 2;
        description
          "IS-IS.";
      }
    }
    description
      "BIER underlay protocol type.";
  }

  typedef ncs_rpc_notif_bit-string-length {
    type enumeration {
      enum "64-bit" {
        value 1;
        description
          "64-bit BitString.";
      }
      enum "128-bit" {
        value 2;
        description
          "128-bit BitString.";
      }
      enum "256-bit" {
        value 3;
        description
          "256-bit BitString.";
      }
    }
    description
      "Enumerated values of the BitString length.";
  }

  typedef ncs_rpc_notif_igp-algorithm-type {
    type enumeration {
      enum "SPF" {
        value 0;
        description
          "Shortest Path First (SPF) algorithm based on link metric.";
      }
      enum "SSPF" {
        value 1;
        description
          "Strict Shortest Path First (SPF) algorithm based on link metric.";
      }
    }
    description
      "IGP algorithm type.";
  }

  typedef ncs_rpc_notif_bier-algorithm-type {
    type enumeration {
      enum "no-specific" {
        value 0;
        description
          "No BIER-specific algorithm is used.";
      }
    }
    description
      "BIER algorithm type.";
  }

  typedef ncs_rpc_notif_bier-encapsulation-type {
    type enumeration {
      enum "mpls" {
        value 1;
        description
          "MPLS encapsulation for BIER.";
      }
      enum "ipv6" {
        value 2;
        description
          "IPv6 encapsulation for BIER.";
      }
    }
    description
      "Encapsulation types for BIER.";
  }

  typedef ncs_rpc_notif_address-family-type {
    type enumeration {
      enum "ipv4-unicast" {
        value 1;
        description
          "IPv4 address family.";
      }
      enum "ipv6-unicast" {
        value 2;
        description
          "IPv6 address family.";
      }
    }
    description
      "Address family.";
  }

  typedef ncs_rpc_notif_birt-nexthop-invalid-type {
    type enumeration {
      enum "none" {
        value 0;
        description
          "Valid nexthop.";
      }
      enum "missing-neighbor" {
        value 1;
        description
          "Invalid sub-domain configuration.";
      }
      enum "lack-label" {
        value 2;
        description
          "The encapsulation cunfigured on nexthop does not support the destination BFR-ID.";
      }
      enum "exceed-load-balance-number" {
        value 3;
        description
          "The value is larger than the maximum number of load balancing paths.";
      }
      enum "miss-bsl" {
        value 6;
        description
          "The BSL is not configured for the next hop device.";
      }
    }
    description
      "Reason for the invalid nexthop.";
  }

  typedef live_ncs_underlay-protocol-type {
    type enumeration {
      enum "ospf" {
        value 1;
        description
          "OSPF.";
      }
      enum "isis" {
        value 2;
        description
          "IS-IS.";
      }
    }
    description
      "BIER underlay protocol type.";
  }

  typedef live_ncs_bit-string-length {
    type enumeration {
      enum "64-bit" {
        value 1;
        description
          "64-bit BitString.";
      }
      enum "128-bit" {
        value 2;
        description
          "128-bit BitString.";
      }
      enum "256-bit" {
        value 3;
        description
          "256-bit BitString.";
      }
    }
    description
      "Enumerated values of the BitString length.";
  }

  typedef live_ncs_igp-algorithm-type {
    type enumeration {
      enum "SPF" {
        value 0;
        description
          "Shortest Path First (SPF) algorithm based on link metric.";
      }
      enum "SSPF" {
        value 1;
        description
          "Strict Shortest Path First (SPF) algorithm based on link metric.";
      }
    }
    description
      "IGP algorithm type.";
  }

  typedef live_ncs_bier-algorithm-type {
    type enumeration {
      enum "no-specific" {
        value 0;
        description
          "No BIER-specific algorithm is used.";
      }
    }
    description
      "BIER algorithm type.";
  }

  typedef live_ncs_bier-encapsulation-type {
    type enumeration {
      enum "mpls" {
        value 1;
        description
          "MPLS encapsulation for BIER.";
      }
      enum "ipv6" {
        value 2;
        description
          "IPv6 encapsulation for BIER.";
      }
    }
    description
      "Encapsulation types for BIER.";
  }

  typedef live_ncs_address-family-type {
    type enumeration {
      enum "ipv4-unicast" {
        value 1;
        description
          "IPv4 address family.";
      }
      enum "ipv6-unicast" {
        value 2;
        description
          "IPv6 address family.";
      }
    }
    description
      "Address family.";
  }

  typedef live_ncs_birt-nexthop-invalid-type {
    type enumeration {
      enum "none" {
        value 0;
        description
          "Valid nexthop.";
      }
      enum "missing-neighbor" {
        value 1;
        description
          "Invalid sub-domain configuration.";
      }
      enum "lack-label" {
        value 2;
        description
          "The encapsulation cunfigured on nexthop does not support the destination BFR-ID.";
      }
      enum "exceed-load-balance-number" {
        value 3;
        description
          "The value is larger than the maximum number of load balancing paths.";
      }
      enum "miss-bsl" {
        value 6;
        description
          "The BSL is not configured for the next hop device.";
      }
    }
    description
      "Reason for the invalid nexthop.";
  }

  typedef underlay-protocol-type {
    type enumeration {
      enum "ospf" {
        value 1;
        description
          "OSPF.";
      }
      enum "isis" {
        value 2;
        description
          "IS-IS.";
      }
    }
    description
      "BIER underlay protocol type.";
  }

  typedef bit-string-length {
    type enumeration {
      enum "64-bit" {
        value 1;
        description
          "64-bit BitString.";
      }
      enum "128-bit" {
        value 2;
        description
          "128-bit BitString.";
      }
      enum "256-bit" {
        value 3;
        description
          "256-bit BitString.";
      }
    }
    description
      "Enumerated values of the BitString length.";
  }

  typedef igp-algorithm-type {
    type enumeration {
      enum "SPF" {
        value 0;
        description
          "Shortest Path First (SPF) algorithm based on link metric.";
      }
      enum "SSPF" {
        value 1;
        description
          "Strict Shortest Path First (SPF) algorithm based on link metric.";
      }
    }
    description
      "IGP algorithm type.";
  }

  typedef bier-algorithm-type {
    type enumeration {
      enum "no-specific" {
        value 0;
        description
          "No BIER-specific algorithm is used.";
      }
    }
    description
      "BIER algorithm type.";
  }

  typedef bier-encapsulation-type {
    type enumeration {
      enum "mpls" {
        value 1;
        description
          "MPLS encapsulation for BIER.";
      }
      enum "ipv6" {
        value 2;
        description
          "IPv6 encapsulation for BIER.";
      }
    }
    description
      "Encapsulation types for BIER.";
  }

  typedef address-family-type {
    type enumeration {
      enum "ipv4-unicast" {
        value 1;
        description
          "IPv4 address family.";
      }
      enum "ipv6-unicast" {
        value 2;
        description
          "IPv6 address family.";
      }
    }
    description
      "Address family.";
  }

  typedef birt-nexthop-invalid-type {
    type enumeration {
      enum "none" {
        value 0;
        description
          "Valid nexthop.";
      }
      enum "missing-neighbor" {
        value 1;
        description
          "Invalid sub-domain configuration.";
      }
      enum "lack-label" {
        value 2;
        description
          "The encapsulation cunfigured on nexthop does not support the destination BFR-ID.";
      }
      enum "exceed-load-balance-number" {
        value 3;
        description
          "The value is larger than the maximum number of load balancing paths.";
      }
      enum "miss-bsl" {
        value 6;
        description
          "The BSL is not configured for the next hop device.";
      }
    }
    description
      "Reason for the invalid nexthop.";
  }

  augment "/ncs:devices/ncs:device/ncs:config" {
    container bier {
      tailf:ncs-device-type "netconf";
      tailf:display-when "not(../../ncs:module) or ../../ncs:module[ncs:name='huawei-bier']";
      presence "BIER enable.";
      description
        "BIER configuration.";
      container sub-domains {
        description
          "List of BIER sub-domain.";
        list sub-domain {
          must "not(./bfr-id) or (not(./encapsulations/encapsulation[bsl='64-bit'][encapsulation-type='mpls']/max-si) or (./bfr-id <= (./encapsulations/encapsulation[bsl='64-bit'][encapsulation-type='mpls']/max-si + 1) * 64))" {
            tailf:xpath-root 3;
          }
          must "not(./bfr-id) or (not(./encapsulations/encapsulation[bsl='128-bit'][encapsulation-type='mpls']/max-si) or (./bfr-id <= (./encapsulations/encapsulation[bsl='128-bit'][encapsulation-type='mpls']/max-si + 1) * 128))" {
            tailf:xpath-root 3;
          }
          must "not(./bfr-id) or (not(./encapsulations/encapsulation[bsl='256-bit'][encapsulation-type='mpls']/max-si) or (./bfr-id <= (./encapsulations/encapsulation[bsl='256-bit'][encapsulation-type='mpls']/max-si + 1) * 256))" {
            tailf:xpath-root 3;
          }
          key "address-family sub-domain-id";
          description
            "Configure BIER sub-domain.";
          leaf address-family {
            type address-family-type;
            description
              "IPv4 or IPv6 address family.";
          }
          leaf sub-domain-id {
            type uint16 {
              range "0..255";
            }
            description
              "BIER sub-domain ID.";
          }
          leaf bfr-prefix-interface {
            type leafref {
              path "/ncs:devices/ncs:device/ncs:config/ifm:ifm/ifm:interfaces/ifm:interface/ifm:name" {
                tailf:xpath-root 3;
              }
            }
            must "/ifm:ifm/ifm:interfaces/ifm:interface[ifm:name=current()]/ifm:type='LoopBack' and /ifm:ifm/ifm:interfaces/ifm:interface[ifm:name=current()]/ifm:vrf-name='_public_'" {
              tailf:xpath-root 3;
            }
            description
              "BFR prefix interface.";
          }
          leaf ipv6-specified-address {
            when "../bfr-prefix-interface and ../address-family='ipv6-unicast'" {
              tailf:xpath-root 3;
            }
            type inet:ipv6-address-no-zone;
            must "/ifm:ifm/ifm:interfaces/ifm:interface[current()/../bfr-prefix-interface=ifm:name]/ip:ipv6/ip:addresses/ip:address[ip:ip=current()]/ip:type='global'" {
              tailf:xpath-root 3;
            }
            must '/ifm:ifm/ifm:interfaces/ifm:interface[current()/../bfr-prefix-interface=ifm:name]/ip:ipv6/ip:addresses/ip:address[ip:ip=current()]/ip:prefix-length=128' {
              tailf:xpath-root 3;
            }
            description
              "Specified IPv6 BFR prefix.";
          }
          choice end-bier-address {
            description
              "The end-bier address of BIER IPv6 for current SD.";
            case srv6-locator {
              description
                "Srv6 locator.";
              container srv6-locator {
                when "../address-family='ipv6-unicast'" {
                  tailf:xpath-root 3;
                }
                description
                  "Configure Srv6 locator.";
                leaf locator {
                  type leafref {
                    path "/ncs:devices/ncs:device/ncs:config/ni:network-instance/ni:instances/ni:instance/srv6:srv6/srv6:locators/srv6:locator/srv6:name" {
                      tailf:xpath-root 3;
                    }
                  }
                  mandatory true;
                  description
                    "SRv6 locator.";
                }
                leaf auto-sid {
                  type boolean;
                  must "../auto-sid='false'" {
                    tailf:xpath-root 3;
                  }
                  default "false";
                  description
                    "Enable/disable Auto sid.";
                }
                leaf sid {
                  type inet:ipv6-address-no-zone;
                  mandatory true;
                  description
                    "End-bier-sid for SD.";
                }
              }
            }
          }
          leaf underlay-protocol {
            type underlay-protocol-type;
            description
              "BIER underlay protocol.";
          }
          leaf bfr-id {
            type uint16 {
              range "1..65535";
            }
            description
              "BFR-ID.";
          }
          leaf load-balance-num {
            type uint8 {
              range "1..16";
            }
            default "1";
            description
              "Maximum number of paths for multicast load balancing.";
          }
          // NCS drop config false leaf 'mt-id'
          // NCS drop config false leaf 'igp-algorithm'
          // NCS drop config false leaf 'bier-algorithm'
          container encapsulations {
            description
              "List of BIER encapsulation.";
            list encapsulation {
              key "bsl encapsulation-type";
              description
                "Configure BIER encapsulation.";
              leaf bsl {
                type bit-string-length;
                description
                  "BIER BitString length, which is 64/128/256 bits. Multiple devices in a subdomain must have the same BSL.";
              }
              leaf encapsulation-type {
                type bier-encapsulation-type;
                must "(../../../address-family='ipv4-unicast' and ../encapsulation-type='mpls') or (../../../address-family='ipv6-unicast' and ../encapsulation-type='ipv6')" {
                  tailf:xpath-root 3;
                }
                description
                  "BIER encapsulation type configuration.";
              }
              leaf max-si {
                type uint16 {
                  range "0..255";
                }
                mandatory true;
                description
                  "Maximum set identifier.";
              }
              // NCS drop config false leaf 'bift-id'
            }
          }
          // NCS drop config false container 'local-infos'
          // NCS drop config false container routings
        }
      }
      // NCS drop config false container prefixs
    }
  }
  augment "/ncs:devices/ncs:device/ncs:live-status" {
    container bier {
      tailf:ncs-device-type "netconf";
      tailf:display-when "not(../../ncs:module) or ../../ncs:module[ncs:name='huawei-bier'] or (../../ncs:live-status-protocol[not(ncs:capability)]) or (../../ncs:live-status-protocol/ncs:capability/ncs:module[.='huawei-bier'])";
      presence "BIER enable.";
      description
        "BIER configuration.";
      container sub-domains {
        description
          "List of BIER sub-domain.";
        list sub-domain {
          // NCS drop must statement
          // NCS drop must statement
          // NCS drop must statement
          key "address-family sub-domain-id";
          description
            "Configure BIER sub-domain.";
          leaf address-family {
            type live_ncs_address-family-type;
            description
              "IPv4 or IPv6 address family.";
          }
          leaf sub-domain-id {
            type uint16 {
              range "0..255";
            }
            description
              "BIER sub-domain ID.";
          }
          leaf bfr-prefix-interface {
            type leafref {
              path "/ncs:devices/ncs:device/ncs:live-status/ifm:ifm/ifm:interfaces/ifm:interface/ifm:name" {
                tailf:xpath-root 3;
              }
            }
            // NCS drop must statement
            description
              "BFR prefix interface.";
          }
          leaf ipv6-specified-address {
            // NCS drop when statement
            type inet:ipv6-address-no-zone;
            // NCS drop must statement
            // NCS drop must statement
            description
              "Specified IPv6 BFR prefix.";
          }
          choice end-bier-address {
            description
              "The end-bier address of BIER IPv6 for current SD.";
            case srv6-locator {
              description
                "Srv6 locator.";
              container srv6-locator {
                // NCS drop when statement
                description
                  "Configure Srv6 locator.";
                leaf locator {
                  type leafref {
                    path "/ncs:devices/ncs:device/ncs:live-status/ni:network-instance/ni:instances/ni:instance/srv6:srv6/srv6:locators/srv6:locator/srv6:name" {
                      tailf:xpath-root 3;
                    }
                  }
                  // NCS drop mandatory statement
                  description
                    "SRv6 locator.";
                }
                leaf auto-sid {
                  type boolean;
                  // NCS drop must statement
                  // NCS drop default statement
                  description
                    "Enable/disable Auto sid.";
                }
                leaf sid {
                  type inet:ipv6-address-no-zone;
                  // NCS drop mandatory statement
                  description
                    "End-bier-sid for SD.";
                }
              }
            }
          }
          leaf underlay-protocol {
            type live_ncs_underlay-protocol-type;
            description
              "BIER underlay protocol.";
          }
          leaf bfr-id {
            type uint16 {
              range "1..65535";
            }
            description
              "BFR-ID.";
          }
          leaf load-balance-num {
            type uint8 {
              range "1..16";
            }
            // NCS drop default statement
            description
              "Maximum number of paths for multicast load balancing.";
          }
          leaf mt-id {
            type uint16;
            description
              "Multi-topology type identifier.";
          }
          leaf igp-algorithm {
            type live_ncs_igp-algorithm-type;
            description
              "IGP algorithm type.";
          }
          leaf bier-algorithm {
            type live_ncs_bier-algorithm-type;
            description
              "BIER algorithm type.";
          }
          container encapsulations {
            description
              "List of BIER encapsulation.";
            list encapsulation {
              key "bsl encapsulation-type";
              description
                "Configure BIER encapsulation.";
              leaf bsl {
                type live_ncs_bit-string-length;
                description
                  "BIER BitString length, which is 64/128/256 bits. Multiple devices in a subdomain must have the same BSL.";
              }
              leaf encapsulation-type {
                type live_ncs_bier-encapsulation-type;
                // NCS drop must statement
                description
                  "BIER encapsulation type configuration.";
              }
              leaf max-si {
                type uint16 {
                  range "0..255";
                }
                // NCS drop mandatory statement
                description
                  "Maximum set identifier.";
              }
              leaf bift-id {
                type uint32 {
                  range "0..4294967295";
                }
                description
                  "BIFT ID base.";
              }
            }
          }
          container local-infos {
            description
              "BIER sub-domain state.";
            leaf igp-process-id {
              type uint32;
              description
                "Process ID of the underlay routing protocol.";
            }
            leaf igp-sub-process-id {
              type uint32;
              description
                "Sub-process ID of the underlay routing protocol.";
            }
            leaf bfr-prefix {
              type inet:ip-address-no-zone;
              description
                "BFR prefix address.";
            }
            leaf bfr-prefix-mask-len {
              type uint8 {
                range "0..128";
              }
              description
                "BFR prefix address mask length.";
            }
            leaf end-bier-sid {
              type inet:ipv6-address-no-zone;
              description
                "End-bier-sid of the SD.";
            }
          }
          container routings {
            description
              "List of BIER routing state.";
            list routing {
              key "bsl destination-prefix";
              description
                "BIER routing state.";
              leaf bsl {
                type live_ncs_bit-string-length;
                description
                  "BIER BitString length, which is 64/128/256 bits.";
              }
              leaf destination-prefix {
                type inet:ip-address-no-zone;
                description
                  "Destination prefix.";
              }
              leaf underlay-protocol {
                type live_ncs_underlay-protocol-type;
                description
                  "Underlay IGP used by BIER.";
              }
              choice prefix-igp-attribute {
                description
                  "IGP attributes.";
                case ospf-protocol {
                  description
                    "OSPF.";
                  leaf router-id {
                    type inet:ip-address-no-zone;
                    description
                      "OSPF router ID.";
                  }
                }
                case isis-protocol {
                  description
                    "IS-IS.";
                  leaf system-id {
                    type string {
                      length "1..16";
                    }
                    description
                      "IS-IS system ID.";
                  }
                }
                case local-system {
                  description
                    "Local system.";
                  leaf is-local-system {
                    type boolean;
                    description
                      "Prefix is advertised by local system.";
                  }
                }
              }
              leaf bfr-id {
                type uint16 {
                  range "1..65535";
                }
                description
                  "BFR-ID.";
              }
              leaf up-time {
                type pub-type:live_ncs_time-tick;
                description
                  "Prefix survival time.";
              }
              container nexthops {
                description
                  "List of Next-hop state.";
                list nexthop {
                  key "next-hop-addr next-hop-outbound-if";
                  description
                    "Next-hop state.";
                  leaf next-hop-addr {
                    type inet:ip-address-no-zone;
                    description
                      "Next-hop prefix address.";
                  }
                  leaf next-hop-outbound-if {
                    type pub-type:live_ncs_if-name;
                    description
                      "Next-hop outbound interface.";
                  }
                  leaf bfr-neighbor {
                    type inet:ip-address-no-zone;
                    description
                      "BIER neighbor.";
                  }
                  leaf underlay-protocol {
                    type live_ncs_underlay-protocol-type;
                    description
                      "Underlay IGP used by BIER.";
                  }
                  choice igp-attribute {
                    description
                      "IGP attributes.";
                    case ospf-protocol {
                      description
                        "OSPF.";
                      leaf router-id {
                        type inet:ip-address-no-zone;
                        description
                          "OSPF router ID.";
                      }
                    }
                    case isis-protocol {
                      description
                        "IS-IS.";
                      leaf system-id {
                        type string {
                          length "1..16";
                        }
                        description
                          "IS-IS system ID.";
                      }
                    }
                    case local-system {
                      description
                        "Local system.";
                      leaf is-local-system {
                        type boolean;
                        description
                          "Prefix is advertised by local system.";
                      }
                    }
                  }
                  leaf up-time {
                    type pub-type:live_ncs_time-tick;
                    description
                      "Neighbor relationship establishment time.";
                  }
                  leaf bift-id {
                    type uint32 {
                      range "0..4294967295";
                    }
                    description
                      "The BIFT-ID assigned by this nexthop node.";
                  }
                  leaf direct-flag {
                    type boolean;
                    description
                      "The nexthop is directly conected.";
                  }
                }
              }
              container invalid-nexthops {
                description
                  "List of Next-hop state.";
                list invalid-nexthop {
                  key "next-hop-addr next-hop-outbound-if";
                  description
                    "Next-hop state.";
                  leaf next-hop-addr {
                    type inet:ip-address-no-zone;
                    description
                      "Next-hop prefix address.";
                  }
                  leaf next-hop-outbound-if {
                    type pub-type:live_ncs_if-name;
                    description
                      "Next-hop outbound interface.";
                  }
                  leaf bfr-neighbor {
                    type inet:ip-address-no-zone;
                    description
                      "BIER neighbor.";
                  }
                  leaf underlay-protocol {
                    type live_ncs_underlay-protocol-type;
                    description
                      "Underlay IGP used by BIER.";
                  }
                  choice igp-attribute {
                    description
                      "IGP attributes.";
                    case ospf-protocol {
                      description
                        "OSPF.";
                      leaf router-id {
                        type inet:ip-address-no-zone;
                        description
                          "OSPF router ID.";
                      }
                    }
                    case isis-protocol {
                      description
                        "IS-IS.";
                      leaf system-id {
                        type string {
                          length "1..16";
                        }
                        description
                          "IS-IS system ID.";
                      }
                    }
                    case local-system {
                      description
                        "Local system.";
                      leaf is-local-system {
                        type boolean;
                        description
                          "Prefix is advertised by local system.";
                      }
                    }
                  }
                  leaf up-time {
                    type pub-type:live_ncs_time-tick;
                    description
                      "Neighbor relationship establishment time.";
                  }
                  leaf bift-id {
                    type uint32 {
                      range "0..4294967295";
                    }
                    description
                      "The BIFT-ID assigned by this nexthop node.";
                  }
                  leaf invalid-reason {
                    type live_ncs_birt-nexthop-invalid-type;
                    description
                      "Invalid nexthop reason.";
                  }
                }
              }
            }
          }
        }
      }
      container prefixs {
        description
          "List of BIER prefix state.";
        list prefix {
          key "address-family sub-domain-id bfr-prefix bfr-prefix-mask-len underlay-protocol";
          description
            "BIER prefix state.";
          leaf address-family {
            type live_ncs_address-family-type;
            description
              "IPv4 or IPv6 address family.";
          }
          leaf sub-domain-id {
            type uint16 {
              range "0..255";
            }
            description
              "BIER sub-domain ID.";
          }
          leaf bfr-prefix {
            type inet:ip-address-no-zone;
            description
              "BFR prefix address.";
          }
          leaf bfr-prefix-mask-len {
            type uint8 {
              range "0..128";
            }
            description
              "BFR prefix address mask length.";
          }
          leaf underlay-protocol {
            type live_ncs_underlay-protocol-type;
            description
              "Underlay IGP used by BIER.";
          }
          leaf bfr-id {
            type uint16 {
              range "1..65535";
            }
            ext:support-filter "true";
            description
              "BFR-ID.";
          }
          leaf end-bier-sid {
            type inet:ipv6-address-no-zone;
            description
              "End-bier-sid of the SD.";
          }
          leaf igp-process-id {
            type uint32;
            description
              "Process ID of the underlay IGP.";
          }
          leaf mt-id {
            type uint32;
            description
              "Multi-topology ID of the underlay IGP.";
          }
          leaf igp-sub-process-id {
            type uint32;
            description
              "Sub-process ID of the underlay IGP.";
          }
          choice igp-attribute {
            description
              "IGP attributes.";
            case ospf-protocol {
              description
                "OSPF.";
              leaf router-id {
                type inet:ip-address-no-zone;
                ext:support-filter "true";
                description
                  "OSPF router ID.";
              }
            }
            case isis-protocol {
              description
                "IS-IS.";
              leaf system-id {
                type string {
                  length "1..16";
                }
                ext:support-filter "true";
                description
                  "IS-IS system ID.";
              }
            }
            case local-system {
              description
                "Local system.";
              leaf is-local-system {
                type boolean;
                description
                  "Prefix is advertised by local system.";
              }
            }
          }
          leaf prefix-igp-flags {
            type bits {
              bit local {
                description
                  "Local prefix.";
              }
              bit intra {
                description
                  "Intra-domain prefix.";
              }
              bit invalid {
                description
                  "Invalid prefix.";
              }
              bit duplicate {
                description
                  "Duplicate prefix.";
              }
              bit best {
                description
                  "Best prefix.";
              }
            }
            description
              "BIER prefix IGP state.";
          }
          leaf prefix-sd-flags {
            type bits {
              bit duplicate-sd {
                description
                  "Duplicate sub-domain ID.";
              }
              bit invalid-igp-cfg {
                description
                  "Invalid IGP configuration.";
              }
              bit invalid-bar {
                description
                  "Invalid BIER algorithm.";
              }
              bit invalid-ipa {
                description
                  "Invalid IGP algorithm.";
              }
              bit duplicate-bfr-id {
                description
                  "Duplicate BFR-ID.";
              }
              bit invalid-mt {
                description
                  "Invalid multi-topology.";
              }
              bit supress-bfr-id-adv {
                description
                  "BFR-ID advertisement suppression.";
              }
            }
            description
              "BIER prefix sub-domain state.";
          }
          leaf igp-algorithm {
            type live_ncs_igp-algorithm-type;
            description
              "IGP algorithm type.";
          }
          leaf bier-algorithm {
            type live_ncs_bier-algorithm-type;
            description
              "BIER algorithm type.";
          }
          container encapsulation-infos {
            description
              "BIER prefix encapsulation state.";
            container encapsulations {
              description
                "List of BIER prefix encapsulation state.";
              list encapsulation {
                key "bsl encapsulation-type";
                description
                  "BIER prefix encapsulation state.";
                leaf bsl {
                  type live_ncs_bit-string-length;
                  description
                    "BIER BitString length, which is 64/128/256 bits.";
                }
                leaf encapsulation-type {
                  type live_ncs_bier-encapsulation-type;
                  description
                    "BIER encapsulation type.";
                }
                leaf max-si {
                  type uint16 {
                    range "0..255";
                  }
                  description
                    "Maximum set identifier.";
                }
                leaf up-time {
                  type pub-type:live_ncs_time-tick;
                  description
                    "Prefix survival time.";
                }
                leaf bift-id-base {
                  type uint32 {
                    range "0..4294967295";
                  }
                  description
                    "Start BIFT-ID in the BIER encapsulation information.";
                }
              }
            }
            container invalid-encapsulations {
              description
                "List of BIER prefix encapsulation state.";
              list invalid-encapsulation {
                key "bsl encapsulation-type";
                description
                  "BIER prefix encapsulation state.";
                leaf bsl {
                  type live_ncs_bit-string-length;
                  description
                    "BIER BitString length, which is 64/128/256 bits.";
                }
                leaf encapsulation-type {
                  type live_ncs_bier-encapsulation-type;
                  description
                    "BIER encapsulation type.";
                }
                leaf max-si {
                  type uint16 {
                    range "0..255";
                  }
                  description
                    "Maximum set identifier.";
                }
                leaf up-time {
                  type pub-type:live_ncs_time-tick;
                  description
                    "Prefix survival time.";
                }
                leaf bift-id-base {
                  type uint32 {
                    range "0..4294967295";
                  }
                  description
                    "Start BIFT-ID in the BIER encapsulation information.";
                }
                leaf invalid-reason {
                  type bits {
                    bit unknown-sd {
                      position 0;
                      description
                        "Unknown sub-domain ID.";
                    }
                    bit invalid-igp-cfg {
                      position 1;
                      description
                        "The SD advertised by an IGP instance is the same as that advertised by another IGP instance.";
                    }
                    bit duplicate-bsl {
                      position 2;
                      description
                        "Duplicate BitString length.";
                    }
                    bit invalid-bsl {
                      position 3;
                      description
                        "Invalid BitString length.";
                    }
                    bit unsupport-bsl {
                      position 4;
                      description
                        "Unsupported BitString length.";
                    }
                    bit invalid-label {
                      position 5;
                      description
                        "Invalid MPLS label.";
                    }
                    bit invalid-label-range {
                      position 6;
                      description
                        "Invalid range of MPLS labels.";
                    }
                    bit overlap-label-range {
                      position 7;
                      description
                        "Overlap range of MPLS labels.";
                    }
                    bit sd-unsupport-bsl {
                      position 8;
                      description
                        "BitString length is not configured locally.";
                    }
                    bit invalid-bsl-bfrid-maxsi-asso {
                      position 9;
                      description
                        "The advertised BFR-ID exceeds the maximum value that can be expressed by the advertised BSL and Max-SI.";
                    }
                    bit invalid-prefix-mask {
                      position 10;
                      description
                        "Invalid prefix mask.";
                    }
                  }
                  description
                    "Invalid BSL reason.";
                }
              }
            }
          }
        }
      }
    }
  }
  augment "/ncs:devices/ncs:template/ncs:ned-id/ncs:config" {
    container bier {
      presence "BIER enable.";
      description
        "BIER configuration.";
      container sub-domains {
        description
          "List of BIER sub-domain.";
        list sub-domain {
          // NCS patched for predictable order
          ordered-by user;
          // NCS drop must statement
          // NCS drop must statement
          // NCS drop must statement
          key "address-family sub-domain-id";
          description
            "Configure BIER sub-domain.";
          leaf address-family {
            type ncs_template_address-family-type;
            description
              "IPv4 or IPv6 address family.";
          }
          leaf sub-domain-id {
            type string;
            description
              "BIER sub-domain ID.";
          }
          leaf bfr-prefix-interface {
            type string;
            // NCS drop must statement
            description
              "BFR prefix interface.";
          }
          leaf ipv6-specified-address {
            // NCS drop when statement
            type string;
            // NCS drop must statement
            // NCS drop must statement
            description
              "Specified IPv6 BFR prefix.";
          }
          choice end-bier-address {
            description
              "The end-bier address of BIER IPv6 for current SD.";
            case srv6-locator {
              description
                "Srv6 locator.";
              container srv6-locator {
                // NCS drop when statement
                description
                  "Configure Srv6 locator.";
                leaf locator {
                  type string;
                  // NCS drop mandatory statement
                  description
                    "SRv6 locator.";
                }
                leaf auto-sid {
                  type string;
                  // NCS drop must statement
                  // NCS drop default statement
                  description
                    "Enable/disable Auto sid.";
                }
                leaf sid {
                  type string;
                  // NCS drop mandatory statement
                  description
                    "End-bier-sid for SD.";
                }
              }
            }
          }
          leaf underlay-protocol {
            type ncs_template_underlay-protocol-type;
            description
              "BIER underlay protocol.";
          }
          leaf bfr-id {
            type string;
            description
              "BFR-ID.";
          }
          leaf load-balance-num {
            type string;
            // NCS drop default statement
            description
              "Maximum number of paths for multicast load balancing.";
          }
          // NCS drop config false leaf 'mt-id'
          // NCS drop config false leaf 'igp-algorithm'
          // NCS drop config false leaf 'bier-algorithm'
          container encapsulations {
            description
              "List of BIER encapsulation.";
            list encapsulation {
              // NCS patched for predictable order
              ordered-by user;
              key "bsl encapsulation-type";
              description
                "Configure BIER encapsulation.";
              leaf bsl {
                type ncs_template_bit-string-length;
                description
                  "BIER BitString length, which is 64/128/256 bits. Multiple devices in a subdomain must have the same BSL.";
              }
              leaf encapsulation-type {
                type ncs_template_bier-encapsulation-type;
                // NCS drop must statement
                description
                  "BIER encapsulation type configuration.";
              }
              leaf max-si {
                type string;
                // NCS drop mandatory statement
                description
                  "Maximum set identifier.";
              }
              // NCS drop config false leaf 'bift-id'
            }
          }
          // NCS drop config false container 'local-infos'
          // NCS drop config false container routings
        }
      }
      // NCS drop config false container prefixs
    }
  }
}
