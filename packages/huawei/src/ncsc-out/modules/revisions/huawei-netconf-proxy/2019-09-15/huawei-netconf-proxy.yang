module huawei-netconf-proxy {
  // Generated by yanger -t ncs
  tailf:mount-id "huawei-nc-1.0:huawei-nc-1.0";
  tailf:ncs-device-type "netconf";

  namespace "urn:huawei:yang:huawei-netconf-proxy";
  prefix ncp;

  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "NETCONF Proxy Protocol Data Types and Protocol Operations.
     This YANG module describe how to define a netconf proxy.";

  revision 2019-09-15 {
    description
      "Initial revision.";
    reference "Huawei private.";
  }
  ext:task-name "netconf";

  augment "/ncs:devices/ncs:device/ncs:config" {
    // NCS drop config false container proxy
  }
  augment "/ncs:devices/ncs:device/ncs:live-status" {
    container proxy {
      tailf:ncs-device-type "netconf";
      tailf:display-when "not(../../ncs:module) or ../../ncs:module[ncs:name='huawei-netconf-proxy'] or (../../ncs:live-status-protocol[not(ncs:capability)]) or (../../ncs:live-status-protocol/ncs:capability/ncs:module[.='huawei-netconf-proxy'])";
      description
        "Container for NETCONF Proxy.";
      list target-list {
        key "target";
        description
          "Statistics of target list information.";
        leaf target {
          type string {
            length "1..127";
          }
          description
            "Target name.";
        }
        leaf target-id {
          ext:support-filter "true";
          type string {
            length "1..127";
          }
          description
            "Target Identifier.";
        }
        leaf target-type {
          ext:support-filter "true";
          type string {
            length "1..127";
          }
          description
            "The type of the target.";
        }
      }
    }
  }
  augment "/ncs:devices/ncs:template/ncs:ned-id/ncs:config" {
    // NCS drop config false container proxy
  }
}
