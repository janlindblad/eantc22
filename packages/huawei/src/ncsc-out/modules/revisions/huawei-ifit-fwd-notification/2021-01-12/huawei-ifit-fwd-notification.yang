module huawei-ifit-fwd-notification {
  // Generated by yanger -t ncs
  tailf:mount-id "huawei-nc-1.0:huawei-nc-1.0";
  tailf:ncs-device-type "netconf";

  yang-version 1;
  namespace "urn:huawei:yang:huawei-ifit-fwd-notification";
  prefix ifit-fwd-notification;

  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Notification of ifit-fwd-notification.";

  revision 2021-01-12 {
    description
      "Modify description: add new notification of ifit instances spec exceed.";
    reference "Huawei private.";
  }
  revision 2019-07-08 {
    description
      "Initial revision.";
    reference "Huawei private.";
  }
  ext:task-name "ifit";

  augment "/ncs:devices/ncs:device/ncs:notifications/ncs:received-notifications/ncs:notification/ncs:data" {
    container ifit-instance-spec-exceed-resume {
      presence "";
      config false;
      description
        "The total number of iFIT instances on the interface board has been lower than the upper limit.";
      leaf type {
        type string {
          length "1..32";
        }
        description
          "The Instance Type.";
      }
      leaf slot-id {
        type string {
          length "1..32";
        }
        description
          "Slot ID of an interface board.";
      }
      leaf flow-limit-num {
        type uint32;
        description
          "Maximum number of iFIT Instances on the interface board.";
      }
    }
  }
  augment "/ncs:devices/ncs:device/ncs:notifications/ncs:received-notifications/ncs:notification/ncs:data" {
    container ifit-instance-spec-exceed {
      presence "";
      config false;
      description
        "The total number of iFIT instances on the interface board reaches the upper limit.";
      leaf type {
        type string {
          length "1..32";
        }
        description
          "The Instance Type.";
      }
      leaf slot-id {
        type string {
          length "1..32";
        }
        description
          "Slot ID of an interface board.";
      }
      leaf flow-limit-num {
        type uint32;
        description
          "Maximum number of iFIT Instances on the interface board.";
      }
    }
  }
  augment "/ncs:devices/ncs:device/ncs:notifications/ncs:received-notifications/ncs:notification/ncs:data" {
    container ifit-static-flow-exceed-resume {
      presence "";
      config false;
      description
        "The total number of iFIT static flows and reverse flows on the interface board fell below the upper limit.";
      leaf slot-id {
        type string {
          length "1..32";
        }
        description
          "Slot ID of an interface board.";
      }
      leaf flow-limit-num {
        type uint32;
        description
          "Maximum number of iFIT Instances on the interface board.";
      }
    }
  }
  augment "/ncs:devices/ncs:device/ncs:notifications/ncs:received-notifications/ncs:notification/ncs:data" {
    container ifit-static-flow-exceed {
      presence "";
      config false;
      description
        "The total number of iFIT static flows and reverse flows on the interface board reached the upper limit.";
      leaf slot-id {
        type string {
          length "1..32";
        }
        description
          "Slot ID of an interface board.";
      }
      leaf flow-limit-num {
        type uint32;
        description
          "Maximum number of iFIT Instances on the interface board.";
      }
    }
  }
  augment "/ncs:devices/ncs:device/ncs:notifications/ncs:received-notifications/ncs:notification/ncs:data" {
    container ifit-dynamic-flow-exceed-resume {
      presence "";
      config false;
      description
        "The total number of iFIT dynamic flows on the interface board fell below the upper limit.";
      leaf slot-id {
        type string {
          length "1..32";
        }
        description
          "Slot ID of an interface board.";
      }
      leaf flow-limit-num {
        type uint32;
        description
          "Maximum number of iFIT Instances on the interface board.";
      }
    }
  }
  augment "/ncs:devices/ncs:device/ncs:notifications/ncs:received-notifications/ncs:notification/ncs:data" {
    container ifit-dynamic-flow-exceed {
      presence "";
      config false;
      description
        "The total number of iFIT dynamic flows on the interface board reached the upper limit.";
      leaf slot-id {
        type string {
          length "1..32";
        }
        description
          "Slot ID of an interface board.";
      }
      leaf flow-limit-num {
        type uint32;
        description
          "Maximum number of iFIT Instances on the interface board.";
      }
    }
  }
  augment "/ncs:devices/ncs:device/ncs:netconf-notifications/ncs:received-notifications/ncs:notification/ncs:data" {
    container ifit-instance-spec-exceed-resume {
      presence "";
      config false;
      description
        "The total number of iFIT instances on the interface board has been lower than the upper limit.";
      leaf type {
        type string {
          length "1..32";
        }
        description
          "The Instance Type.";
      }
      leaf slot-id {
        type string {
          length "1..32";
        }
        description
          "Slot ID of an interface board.";
      }
      leaf flow-limit-num {
        type uint32;
        description
          "Maximum number of iFIT Instances on the interface board.";
      }
    }
  }
  augment "/ncs:devices/ncs:device/ncs:netconf-notifications/ncs:received-notifications/ncs:notification/ncs:data" {
    container ifit-instance-spec-exceed {
      presence "";
      config false;
      description
        "The total number of iFIT instances on the interface board reaches the upper limit.";
      leaf type {
        type string {
          length "1..32";
        }
        description
          "The Instance Type.";
      }
      leaf slot-id {
        type string {
          length "1..32";
        }
        description
          "Slot ID of an interface board.";
      }
      leaf flow-limit-num {
        type uint32;
        description
          "Maximum number of iFIT Instances on the interface board.";
      }
    }
  }
  augment "/ncs:devices/ncs:device/ncs:netconf-notifications/ncs:received-notifications/ncs:notification/ncs:data" {
    container ifit-static-flow-exceed-resume {
      presence "";
      config false;
      description
        "The total number of iFIT static flows and reverse flows on the interface board fell below the upper limit.";
      leaf slot-id {
        type string {
          length "1..32";
        }
        description
          "Slot ID of an interface board.";
      }
      leaf flow-limit-num {
        type uint32;
        description
          "Maximum number of iFIT Instances on the interface board.";
      }
    }
  }
  augment "/ncs:devices/ncs:device/ncs:netconf-notifications/ncs:received-notifications/ncs:notification/ncs:data" {
    container ifit-static-flow-exceed {
      presence "";
      config false;
      description
        "The total number of iFIT static flows and reverse flows on the interface board reached the upper limit.";
      leaf slot-id {
        type string {
          length "1..32";
        }
        description
          "Slot ID of an interface board.";
      }
      leaf flow-limit-num {
        type uint32;
        description
          "Maximum number of iFIT Instances on the interface board.";
      }
    }
  }
  augment "/ncs:devices/ncs:device/ncs:netconf-notifications/ncs:received-notifications/ncs:notification/ncs:data" {
    container ifit-dynamic-flow-exceed-resume {
      presence "";
      config false;
      description
        "The total number of iFIT dynamic flows on the interface board fell below the upper limit.";
      leaf slot-id {
        type string {
          length "1..32";
        }
        description
          "Slot ID of an interface board.";
      }
      leaf flow-limit-num {
        type uint32;
        description
          "Maximum number of iFIT Instances on the interface board.";
      }
    }
  }
  augment "/ncs:devices/ncs:device/ncs:netconf-notifications/ncs:received-notifications/ncs:notification/ncs:data" {
    container ifit-dynamic-flow-exceed {
      presence "";
      config false;
      description
        "The total number of iFIT dynamic flows on the interface board reached the upper limit.";
      leaf slot-id {
        type string {
          length "1..32";
        }
        description
          "Slot ID of an interface board.";
      }
      leaf flow-limit-num {
        type uint32;
        description
          "Maximum number of iFIT Instances on the interface board.";
      }
    }
  }
}
