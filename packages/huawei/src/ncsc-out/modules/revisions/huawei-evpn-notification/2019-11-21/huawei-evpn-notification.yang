module huawei-evpn-notification {
  // Generated by yanger -t ncs
  tailf:mount-id "huawei-nc-1.0:huawei-nc-1.0";
  tailf:ncs-device-type "netconf";

  yang-version 1;
  namespace "urn:huawei:yang:huawei-evpn-notification";
  prefix evpn-notification;

  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Notification of EVPN.";

  revision 2019-11-21 {
    description
      "Init revision.";
    reference "Huawei private.";
  }
  ext:task-name "evpnbgp";

  augment "/ncs:devices/ncs:device/ncs:notifications/ncs:received-notifications/ncs:notification/ncs:data" {
    container evpn-discard-route {
      presence "";
      config false;
      description
        "The EVPN instance discards the newly learned MAC and MAC/IP routes.";
      leaf route-type {
        type string {
          length "1..11";
        }
        description
          "The MAC or MAC/IP route type.";
      }
    }
  }
  augment "/ncs:devices/ncs:device/ncs:notifications/ncs:received-notifications/ncs:notification/ncs:data" {
    container evpn-srv6-modify-arg {
      presence "";
      config false;
      description
        "The minimum length of the ARG is changed, split horizon function may fail temporarily.";
      leaf last-arg-len {
        type uint32;
        description
          "Last ARG length.";
      }
      leaf current-arg-len {
        type uint32;
        description
          "Current ARG length.";
      }
    }
  }
  augment "/ncs:devices/ncs:device/ncs:notifications/ncs:received-notifications/ncs:notification/ncs:data" {
    container evpn-etree-mul-err {
      presence "";
      config false;
      description
        "In an EVPN E-Tree scenario where a CE is dual-homed to PEs, the leaf attributes of the PEs' AC interfaces bound to the EVPN instance were different, causing a traffic loop.";
      leaf evpn-instance-name {
        type string {
          length "1..31";
        }
        description
          "EVPN instance name.";
      }
      leaf interface-name {
        type string {
          length "1..63";
        }
        description
          "Interface name.";
      }
    }
  }
  augment "/ncs:devices/ncs:device/ncs:netconf-notifications/ncs:received-notifications/ncs:notification/ncs:data" {
    container evpn-discard-route {
      presence "";
      config false;
      description
        "The EVPN instance discards the newly learned MAC and MAC/IP routes.";
      leaf route-type {
        type string {
          length "1..11";
        }
        description
          "The MAC or MAC/IP route type.";
      }
    }
  }
  augment "/ncs:devices/ncs:device/ncs:netconf-notifications/ncs:received-notifications/ncs:notification/ncs:data" {
    container evpn-srv6-modify-arg {
      presence "";
      config false;
      description
        "The minimum length of the ARG is changed, split horizon function may fail temporarily.";
      leaf last-arg-len {
        type uint32;
        description
          "Last ARG length.";
      }
      leaf current-arg-len {
        type uint32;
        description
          "Current ARG length.";
      }
    }
  }
  augment "/ncs:devices/ncs:device/ncs:netconf-notifications/ncs:received-notifications/ncs:notification/ncs:data" {
    container evpn-etree-mul-err {
      presence "";
      config false;
      description
        "In an EVPN E-Tree scenario where a CE is dual-homed to PEs, the leaf attributes of the PEs' AC interfaces bound to the EVPN instance were different, causing a traffic loop.";
      leaf evpn-instance-name {
        type string {
          length "1..31";
        }
        description
          "EVPN instance name.";
      }
      leaf interface-name {
        type string {
          length "1..63";
        }
        description
          "Interface name.";
      }
    }
  }
}
