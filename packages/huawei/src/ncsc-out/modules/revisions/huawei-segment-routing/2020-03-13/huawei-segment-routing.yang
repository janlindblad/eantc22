module huawei-segment-routing {
  // Generated by yanger -t ncs
  tailf:mount-id "huawei-nc-1.0:huawei-nc-1.0";
  tailf:ncs-device-type "netconf";

  namespace "urn:huawei:yang:huawei-segment-routing";
  prefix sr;

  import huawei-routing-policy {
    prefix rtp;
  }
  import ietf-inet-types {
    prefix inet;
  }
  import huawei-extension {
    prefix ext;
  }
  import huawei-network-instance {
    prefix ni;
  }
  include huawei-segment-routing-type;
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Segment routing.";

  revision 2020-03-13 {
    description
      "Modify the format specification.";
    reference "Huawei private.";
  }
  revision 2020-03-09 {
    description
      "Modify the description.";
    reference "Huawei private.";
  }
  revision 2020-03-03 {
    description
      "Modify the description.";
    reference "Huawei private.";
  }
  revision 2020-02-04 {
    description
      "Modify the description.";
    reference "Huawei private.";
  }
  revision 2019-12-23 {
    description
      "Reconstructing Yang file by yin mechanism.";
    reference "Huawei private.";
  }
  revision 2019-11-15 {
    description
      "Reconstructing Yang file by yin mechanism.";
    reference "Huawei private.";
  }
  revision 2019-09-21 {
    description
      "Reconstructing Yang file by yin mechanism.";
    reference "Huawei private.";
  }
  revision 2019-04-04 {
    description
      "Initial revision.";
    reference "Huawei private.";
  }
  ext:task-name "segr";

  augment "/ncs:devices/ncs:template/ncs:ned-id/ncs:config/ni:network-instance/ni:instances/ni:instance" {
    description
      "Segment routing augment to L3VPN.";
    container segment-routing {
      // NCS drop when statement
      description
        "Configure segment routing.";
      leaf enable {
        type string;
        // NCS drop default statement
        description
          "Enable/disable segment routing.";
      }
      leaf tunnel-prefer {
        // NCS drop when statement
        type string;
        // NCS drop default statement
        description
          "Prefer segment routing tunnel.";
      }
      container srlbs {
        // NCS drop when statement
        description
          "List of segment routing local block.";
        list srlb {
          // NCS patched for predictable order
          ordered-by user;
          key "begin end";
          // NCS drop max-elements statement
          description
            "Configure segment routing local block. Currently only one configuration is supported.";
          leaf begin {
            type string;
            description
              "SRLB begin value. The value range is determined by the PAF file of the corresponding device.
               Special explanation:
               Range: The range comes from PAF.";
          }
          leaf end {
            type string;
            description
              "SRLB begin value. The value range is determined by the PAF file of the corresponding device.
               Special explanation:
               Range: The range comes from PAF.";
          }
        }
      }
      container bfds {
        // NCS drop when statement
        description
          "List of SRBFDS configuration.";
        list bfd {
          // NCS patched for predictable order
          ordered-by user;
          key "type mode-type";
          // NCS drop max-elements statement
          description
            "Configure SRBFDS configuration.";
          leaf type {
            type ncs_template_bfd-type;
            description
              "Sets a BFD type.";
          }
          leaf mode-type {
            type string;
            description
              "Sets a session mode.";
          }
          leaf ip-prefix {
            type string;
            description
              "Sets a policy name.";
          }
          leaf min-rx {
            type string;
            units "ms";
            // NCS drop default statement
            description
              "Sets a minimum receive interval. Different products have different value ranges.";
          }
          leaf min-tx {
            type string;
            units "ms";
            // NCS drop default statement
            description
              "Sets a minimum transmit interval. Different products have different value ranges.";
          }
          leaf detect-multiplier {
            type string;
            // NCS drop default statement
            description
              "Sets a detect multiplier.";
          }
          leaf effect-sr-lsp {
            type string;
            // NCS drop default statement
            description
              "Enable/disable effect SR BE tunnel.";
          }
          leaf nil-fec {
            // NCS drop when statement
            type string;
            // NCS drop default statement
            description
              "Enable/disable use nil FEC.";
          }
        }
      }
      container traffic-stats {
        // NCS drop when statement
        description
          "Configure the stats of SR traffic.";
        leaf mode {
          type string;
          // NCS drop must statement
          // NCS drop default statement
          description
            "The stats mode of SR traffic.";
        }
        leaf prefix-name {
          // NCS drop when statement
          type string;
          description
            "The name of prefix.";
        }
      }
      container adjacency-sid {
        // NCS drop when statement
        description
          "Configure Segment Routing IPv4 static adjacency label.";
        container globals {
          description
            "List of Segment Routing global linkage label.";
          list global {
            // NCS patched for predictable order
            ordered-by user;
            key "local-ip-address remote-ip-address absolute-sid";
            description
              "Configure Segment Routing global linkage label.";
            leaf local-ip-address {
              type string;
              description
                "Specifies the ip address of the local interface.";
            }
            leaf remote-ip-address {
              type string;
              // NCS drop must statement
              description
                "Remote ip address.";
            }
            leaf absolute-sid {
              type string;
              description
                "Segment ID. The value range is determined by the PAF. The yang node is static-label-blocks of huawei-segment-routing.";
            }
          }
        }
      }
      container bindings {
        // NCS drop when statement
        description
          "Configure bindings.";
        container prefix-sid-mappings {
          description
            "List of address prefix mapping SID information.";
          list prefix-sid-mapping {
            // NCS patched for predictable order
            ordered-by user;
            // NCS drop must statement
            key "ip-address mask-length algorithm";
            description
              "Configure address prefix mapping SID information.";
            leaf ip-address {
              type string;
              description
                "Address prefix.";
            }
            leaf mask-length {
              type string;
              description
                "Mask length of address, only the 32 bit mask length is supported currently.";
            }
            leaf algorithm {
              type string;
              description
                "Prefix SID algorithm.";
            }
            leaf start-sid {
              type string;
              // NCS drop mandatory statement
              description
                "Start of SID index range.";
            }
            leaf range {
              type string;
              // NCS drop default statement
              description
                "Number of allocated SIDs.";
            }
            leaf attach-flag {
              type string;
              // NCS drop default statement
              description
                "Enable/disable the attach flag.";
            }
          }
        }
      }
      // NCS drop config false container 'static-label-blocks'
      // NCS drop config false container 'ipv4-state'
    }
  }
  augment "/ncs:devices/ncs:device/ncs:live-status/ni:network-instance/ni:instances/ni:instance" {
    description
      "Segment routing augment to L3VPN.";
    container segment-routing {
      tailf:ncs-device-type "netconf";
      tailf:display-when "not(../../../../../ncs:module) or ../../../../../ncs:module[ncs:name='huawei-segment-routing'] or (../../../../../ncs:live-status-protocol[not(ncs:capability)]) or (../../../../../ncs:live-status-protocol/ncs:capability/ncs:module[.='huawei-segment-routing'])";
      // NCS drop when statement
      description
        "Configure segment routing.";
      leaf enable {
        type boolean;
        // NCS drop default statement
        description
          "Enable/disable segment routing.";
      }
      leaf tunnel-prefer {
        // NCS drop when statement
        type enumeration {
          enum "ldp" {
            value 1;
            description
              "LDP tunnel.";
          }
          enum "sr-be" {
            value 2;
            description
              "SR BE tunnel.";
          }
        }
        // NCS drop default statement
        description
          "Prefer segment routing tunnel.";
      }
      container srlbs {
        // NCS drop when statement
        description
          "List of segment routing local block.";
        list srlb {
          key "begin end";
          // NCS drop max-elements statement
          description
            "Configure segment routing local block. Currently only one configuration is supported.";
          leaf begin {
            type uint32 {
              range "16..1048575";
            }
            description
              "SRLB begin value. The value range is determined by the PAF file of the corresponding device.
               Special explanation:
               Range: The range comes from PAF.";
          }
          leaf end {
            type uint32 {
              range "16..1048575";
            }
            description
              "SRLB begin value. The value range is determined by the PAF file of the corresponding device.
               Special explanation:
               Range: The range comes from PAF.";
          }
        }
      }
      container bfds {
        // NCS drop when statement
        description
          "List of SRBFDS configuration.";
        list bfd {
          key "type mode-type";
          // NCS drop max-elements statement
          description
            "Configure SRBFDS configuration.";
          leaf type {
            type live_ncs_bfd-type;
            description
              "Sets a BFD type.";
          }
          leaf mode-type {
            type enumeration {
              enum "tunnel" {
                value 1;
                description
                  "The type of session mode is tunnel.";
              }
            }
            description
              "Sets a session mode.";
          }
          leaf ip-prefix {
            type leafref {
              path "/ncs:devices/ncs:device/ncs:live-status/rtp:routing-policy/rtp:ipv4-prefix-filters/rtp:ipv4-prefix-filter/rtp:name" {
                tailf:xpath-root 3;
              }
            }
            description
              "Sets a policy name.";
          }
          leaf min-rx {
            type uint32 {
              range "3..20000";
            }
            units "ms";
            // NCS drop default statement
            description
              "Sets a minimum receive interval. Different products have different value ranges.";
          }
          leaf min-tx {
            type uint32 {
              range "3..20000";
            }
            units "ms";
            // NCS drop default statement
            description
              "Sets a minimum transmit interval. Different products have different value ranges.";
          }
          leaf detect-multiplier {
            type uint32 {
              range "3..50";
            }
            // NCS drop default statement
            description
              "Sets a detect multiplier.";
          }
          leaf effect-sr-lsp {
            type boolean;
            // NCS drop default statement
            description
              "Enable/disable effect SR BE tunnel.";
          }
          leaf nil-fec {
            // NCS drop when statement
            type boolean;
            // NCS drop default statement
            description
              "Enable/disable use nil FEC.";
          }
        }
      }
      container traffic-stats {
        // NCS drop when statement
        description
          "Configure the stats of SR traffic.";
        leaf mode {
          type enumeration {
            enum "none" {
              value 0;
              description
                "SRBE traffic statistics are not enabled.";
            }
            enum "host" {
              value 1;
              description
                "SRBE traffic statistics host mode.";
            }
            enum "ip-prefix" {
              value 2;
              description
                "SRBE traffic statistics host IP prefix mode.";
            }
          }
          // NCS drop must statement
          // NCS drop default statement
          description
            "The stats mode of SR traffic.";
        }
        leaf prefix-name {
          // NCS drop when statement
          type leafref {
            path "/ncs:devices/ncs:device/ncs:live-status/rtp:routing-policy/rtp:ipv4-prefix-filters/rtp:ipv4-prefix-filter/rtp:name" {
              tailf:xpath-root 3;
            }
          }
          description
            "The name of prefix.";
        }
      }
      container adjacency-sid {
        // NCS drop when statement
        description
          "Configure Segment Routing IPv4 static adjacency label.";
        container globals {
          description
            "List of Segment Routing global linkage label.";
          list global {
            key "local-ip-address remote-ip-address absolute-sid";
            description
              "Configure Segment Routing global linkage label.";
            leaf local-ip-address {
              type inet:ipv4-address-no-zone;
              description
                "Specifies the ip address of the local interface.";
            }
            leaf remote-ip-address {
              type inet:ipv4-address-no-zone;
              // NCS drop must statement
              description
                "Remote ip address.";
            }
            leaf absolute-sid {
              type uint32 {
                range "1..4294967295";
              }
              description
                "Segment ID. The value range is determined by the PAF. The yang node is static-label-blocks of huawei-segment-routing.";
            }
          }
        }
      }
      container bindings {
        // NCS drop when statement
        description
          "Configure bindings.";
        container prefix-sid-mappings {
          description
            "List of address prefix mapping SID information.";
          list prefix-sid-mapping {
            // NCS drop must statement
            key "ip-address mask-length algorithm";
            description
              "Configure address prefix mapping SID information.";
            leaf ip-address {
              type inet:ipv4-address-no-zone;
              description
                "Address prefix.";
            }
            leaf mask-length {
              type uint8 {
                range "32";
              }
              description
                "Mask length of address, only the 32 bit mask length is supported currently.";
            }
            leaf algorithm {
              type uint32 {
                range "0";
              }
              description
                "Prefix SID algorithm.";
            }
            leaf start-sid {
              type uint32 {
                range "0..65534";
              }
              // NCS drop mandatory statement
              description
                "Start of SID index range.";
            }
            leaf range {
              type uint16 {
                range "1..65535";
              }
              // NCS drop default statement
              description
                "Number of allocated SIDs.";
            }
            leaf attach-flag {
              type boolean;
              // NCS drop default statement
              description
                "Enable/disable the attach flag.";
            }
          }
        }
      }
      container static-label-blocks {
        description
          "List of segment routing global block.";
        list static-label-block {
          key "lower-sid upper-sid";
          description
            "Statistics of segment routing global block. The range of global labels reserved by the local device for segment routing.";
          leaf lower-sid {
            type uint32 {
              range "1..4294967295";
            }
            description
              "Minimum SID available.";
          }
          leaf upper-sid {
            type uint32 {
              range "1..4294967295";
            }
            description
              "Maximum SID available.";
          }
          leaf range {
            type uint32 {
              range "1..4294967295";
            }
            description
              "Total number of SIDs available.";
          }
        }
      }
      container ipv4-state {
        description
          "Statistics of IPv4.";
        container prefix-mpls-forwardings {
          description
            "List of label for transmission.";
          list prefix-mpls-forwarding {
            key "ip-address mask-length";
            description
              "Statistics of label for transmission.";
            leaf ip-address {
              type inet:ipv4-address-no-zone;
              description
                "The prefix IP address.";
            }
            leaf mask-length {
              type uint8 {
                range "1..32";
              }
              description
                "The length of prefix mask.";
            }
            leaf in-label {
              type uint32 {
                range "1..4294967295";
              }
              description
                "In label.";
            }
            leaf out-label {
              type string {
                length "1..20";
              }
              description
                "Out label.";
            }
            leaf if-name {
              type string {
                length "1..64";
              }
              description
                "Local interface.";
            }
            leaf next-hop {
              type inet:ipv4-address-no-zone;
              description
                "IP address of next hop.";
            }
            leaf lsp-xc-role {
              type string {
                length "1..50";
              }
              description
                "Label type.";
            }
            leaf mpls-mtu {
              type string {
                length "1..50";
              }
              units "Byte";
              description
                "MPLS maximum transmission unit (MTU).";
            }
            leaf mtu {
              type uint32 {
                range "1..4294967295";
              }
              units "Byte";
              description
                "MTU.";
            }
            leaf state {
              type string {
                length "1..50";
              }
              description
                "Lable state.";
            }
          }
        }
        container bfd-states {
          description
            "List of queries BFD session.";
          list bfd-state {
            key "type mode-type ip-address mask-length";
            description
              "Statistics of queries BFD session.";
            leaf type {
              type live_ncs_bfd-type;
              description
                "BFD type.";
            }
            leaf mode-type {
              type enumeration {
                enum "tunnel" {
                  value 1;
                  description
                    "The type of session mode is tunnel.";
                }
              }
              description
                "Session mode.";
            }
            leaf ip-address {
              type inet:ipv4-address-no-zone;
              description
                "Destination IP address.";
            }
            leaf mask-length {
              type uint8 {
                range "1..32";
              }
              description
                "IP address mask length.";
            }
            leaf state {
              type string {
                length "1..64";
              }
              description
                "Session state.";
            }
            leaf discriminator {
              type uint32 {
                range "0..4294967295";
              }
              description
                "Local discriminator.";
            }
          }
        }
      }
    }
  }
  augment "/ncs:devices/ncs:device/ncs:config/ni:network-instance/ni:instances/ni:instance" {
    description
      "Segment routing augment to L3VPN.";
    container segment-routing {
      tailf:ncs-device-type "netconf";
      tailf:display-when "not(../../../../../ncs:module) or ../../../../../ncs:module[ncs:name='huawei-segment-routing']";
      when "../ni:name='_public_'" {
        tailf:xpath-root 3;
      }
      description
        "Configure segment routing.";
      leaf enable {
        type boolean;
        default "false";
        description
          "Enable/disable segment routing.";
      }
      leaf tunnel-prefer {
        when "../enable='true'" {
          tailf:xpath-root 3;
        }
        type enumeration {
          enum "ldp" {
            value 1;
            description
              "LDP tunnel.";
          }
          enum "sr-be" {
            value 2;
            description
              "SR BE tunnel.";
          }
        }
        default "ldp";
        description
          "Prefer segment routing tunnel.";
      }
      container srlbs {
        when "../enable='true'" {
          tailf:xpath-root 3;
        }
        description
          "List of segment routing local block.";
        list srlb {
          key "begin end";
          max-elements 1;
          description
            "Configure segment routing local block. Currently only one configuration is supported.";
          leaf begin {
            type uint32 {
              range "16..1048575";
            }
            description
              "SRLB begin value. The value range is determined by the PAF file of the corresponding device.
               Special explanation:
               Range: The range comes from PAF.";
          }
          leaf end {
            type uint32 {
              range "16..1048575";
            }
            description
              "SRLB begin value. The value range is determined by the PAF file of the corresponding device.
               Special explanation:
               Range: The range comes from PAF.";
          }
        }
      }
      container bfds {
        when "../enable='true'" {
          tailf:xpath-root 3;
        }
        description
          "List of SRBFDS configuration.";
        list bfd {
          key "type mode-type";
          max-elements 1;
          description
            "Configure SRBFDS configuration.";
          leaf type {
            type bfd-type;
            description
              "Sets a BFD type.";
          }
          leaf mode-type {
            type enumeration {
              enum "tunnel" {
                value 1;
                description
                  "The type of session mode is tunnel.";
              }
            }
            description
              "Sets a session mode.";
          }
          leaf ip-prefix {
            type leafref {
              path "/ncs:devices/ncs:device/ncs:config/rtp:routing-policy/rtp:ipv4-prefix-filters/rtp:ipv4-prefix-filter/rtp:name" {
                tailf:xpath-root 3;
              }
            }
            description
              "Sets a policy name.";
          }
          leaf min-rx {
            type uint32 {
              range "3..20000";
            }
            units "ms";
            default "10";
            description
              "Sets a minimum receive interval. Different products have different value ranges.";
          }
          leaf min-tx {
            type uint32 {
              range "3..20000";
            }
            units "ms";
            default "10";
            description
              "Sets a minimum transmit interval. Different products have different value ranges.";
          }
          leaf detect-multiplier {
            type uint32 {
              range "3..50";
            }
            default "3";
            description
              "Sets a detect multiplier.";
          }
          leaf effect-sr-lsp {
            type boolean;
            default "false";
            description
              "Enable/disable effect SR BE tunnel.";
          }
          leaf nil-fec {
            when "../type='bfd'" {
              tailf:xpath-root 3;
            }
            type boolean;
            default "false";
            description
              "Enable/disable use nil FEC.";
          }
        }
      }
      container traffic-stats {
        when "../enable='true'" {
          tailf:xpath-root 3;
        }
        description
          "Configure the stats of SR traffic.";
        leaf mode {
          type enumeration {
            enum "none" {
              value 0;
              description
                "SRBE traffic statistics are not enabled.";
            }
            enum "host" {
              value 1;
              description
                "SRBE traffic statistics host mode.";
            }
            enum "ip-prefix" {
              value 2;
              description
                "SRBE traffic statistics host IP prefix mode.";
            }
          }
          must "../mode!='ip-prefix' or ../prefix-name" {
            tailf:xpath-root 3;
          }
          default "none";
          description
            "The stats mode of SR traffic.";
        }
        leaf prefix-name {
          when "../mode='ip-prefix'" {
            tailf:xpath-root 3;
          }
          type leafref {
            path "/ncs:devices/ncs:device/ncs:config/rtp:routing-policy/rtp:ipv4-prefix-filters/rtp:ipv4-prefix-filter/rtp:name" {
              tailf:xpath-root 3;
            }
          }
          description
            "The name of prefix.";
        }
      }
      container adjacency-sid {
        when "../enable='true'" {
          tailf:xpath-root 3;
        }
        description
          "Configure Segment Routing IPv4 static adjacency label.";
        container globals {
          description
            "List of Segment Routing global linkage label.";
          list global {
            key "local-ip-address remote-ip-address absolute-sid";
            description
              "Configure Segment Routing global linkage label.";
            leaf local-ip-address {
              type inet:ipv4-address-no-zone;
              description
                "Specifies the ip address of the local interface.";
            }
            leaf remote-ip-address {
              type inet:ipv4-address-no-zone;
              must '../local-ip-address!=../remote-ip-address' {
                tailf:xpath-root 3;
              }
              description
                "Remote ip address.";
            }
            leaf absolute-sid {
              type uint32 {
                range "1..4294967295";
              }
              description
                "Segment ID. The value range is determined by the PAF. The yang node is static-label-blocks of huawei-segment-routing.";
            }
          }
        }
      }
      container bindings {
        when "../enable='true'" {
          tailf:xpath-root 3;
        }
        description
          "Configure bindings.";
        container prefix-sid-mappings {
          description
            "List of address prefix mapping SID information.";
          list prefix-sid-mapping {
            must 'start-sid + range <= 65535' {
              tailf:xpath-root 3;
            }
            key "ip-address mask-length algorithm";
            description
              "Configure address prefix mapping SID information.";
            leaf ip-address {
              type inet:ipv4-address-no-zone;
              description
                "Address prefix.";
            }
            leaf mask-length {
              type uint8 {
                range "32";
              }
              description
                "Mask length of address, only the 32 bit mask length is supported currently.";
            }
            leaf algorithm {
              type uint32 {
                range "0";
              }
              description
                "Prefix SID algorithm.";
            }
            leaf start-sid {
              type uint32 {
                range "0..65534";
              }
              mandatory true;
              description
                "Start of SID index range.";
            }
            leaf range {
              type uint16 {
                range "1..65535";
              }
              default "1";
              description
                "Number of allocated SIDs.";
            }
            leaf attach-flag {
              type boolean;
              default "false";
              description
                "Enable/disable the attach flag.";
            }
          }
        }
      }
      // NCS drop config false container 'static-label-blocks'
      // NCS drop config false container 'ipv4-state'
    }
  }
}
