submodule huawei-nqa-reflector {
  // Generated by yanger -t ncs
  tailf:mount-id "huawei-nc-1.0:huawei-nc-1.0";

  yang-version 1;
  belongs-to huawei-nqa {
    prefix nqa;
  }

  import huawei-pub-type {
    prefix pub-type;
  }
  import ietf-inet-types {
    prefix inet;
  }
  import ietf-yang-types {
    prefix yang;
  }
  import huawei-ifm {
    prefix ifm;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Description of submodule nqa-reflector.";

  revision 2020-02-29 {
    description
      "Modify range for PE-VLAN and CE-VLAN.";
    reference "Huawei private.";
  }
  revision 2019-10-25 {
    description
      "Initial revision.";
    reference "Huawei private.";
  }

  typedef ncs_template_reflect-type {
    type string;
    description
      "Description of reflect-type.";
  }

  typedef ncs_rpc_notif_reflect-type {
    type enumeration {
      enum "flow-general" {
        value 2;
        description
          "General flow.";
      }
    }
    description
      "Description of reflect-type.";
  }

  typedef live_ncs_reflect-type {
    type enumeration {
      enum "flow-general" {
        value 2;
        description
          "General flow.";
      }
    }
    description
      "Description of reflect-type.";
  }

  typedef reflect-type {
    type enumeration {
      enum "flow-general" {
        value 2;
        description
          "General flow.";
      }
    }
    description
      "Description of reflect-type.";
  }

  grouping ncs_template_reflectors-type {
    description
      "Reflector table.";
    list reflector {
      // NCS patched for predictable order
      ordered-by user;
      key "reflector-id";
      description
        "Configure reflector table.";
      leaf reflector-id {
        type string;
        description
          "Reflector ID.";
      }
      leaf if-name {
        type string;
        // NCS drop mandatory statement
        description
          "Reflector interface name.";
      }
      leaf reflector-type {
        type ncs_template_reflect-type;
        // NCS drop mandatory statement
        description
          "Reflector type.";
      }
      leaf exchange-port {
        type string;
        // NCS drop default statement
        description
          "Enable/disable reflector UDP port exchange.";
      }
      leaf pe-vlan {
        type string;
        // NCS drop must statement
        description
          "Reflector PE VLAN ID.";
      }
      leaf ce-vlan {
        type string;
        // NCS drop must statement
        description
          "Reflector CE VLAN ID.";
      }
      leaf source-port {
        type string;
        // NCS drop must statement
        // NCS drop default statement
        description
          "Reflector source port.";
      }
      leaf dest-port {
        type string;
        // NCS drop must statement
        // NCS drop default statement
        description
          "Reflector destination port.";
      }
      leaf end-time {
        type string;
        // NCS drop mandatory statement
        description
          "Absolute time of reflector aging, the value must not be earlier than the current system time plus 10s or later than the current system time plus 173400s.";
      }
      leaf share-mode {
        type string;
        // NCS drop must statement
        // NCS drop default statement
        description
          "Enable/disable the share mode on the reflector.";
      }
      choice address {
        description
          "Reflector address.";
        case ipv4-address {
          description
            "Reflector IPv4 address.";
          leaf ipv4-address {
            type string;
            // NCS drop must statement
            description
              "Reflector IPv4 address.";
          }
        }
        case simulate-ipv4-address {
          description
            "Reflector simulate IPv4 address.";
          leaf simulate-ipv4-address {
            type string;
            // NCS drop must statement
            description
              "Reflector simulate IPv4 address.";
          }
        }
        case mac-address {
          description
            "Reflector MAC address.";
          leaf mac-address {
            type pub-type:ncs_template_mac-address;
            // NCS drop must statement
            description
              "Reflector MAC address.";
          }
        }
      }
      // NCS drop config false leaf 'survival-time'
      // NCS drop config false leaf 'recommended-test-mac'
    }
  }

  grouping ncs_rpc_notif_reflectors-type {
    description
      "Reflector table.";
    list reflector {
      key "reflector-id";
      description
        "Configure reflector table.";
      leaf reflector-id {
        type uint32 {
          range "1..65535";
        }
        description
          "Reflector ID.";
      }
      leaf if-name {
        type string;
        mandatory true;
        description
          "Reflector interface name.";
      }
      leaf reflector-type {
        type ncs_rpc_notif_reflect-type;
        mandatory true;
        description
          "Reflector type.";
      }
      leaf exchange-port {
        type boolean;
        default "false";
        description
          "Enable/disable reflector UDP port exchange.";
      }
      leaf pe-vlan {
        type uint16 {
          range "1..4094";
        }
        must "../reflector-type='flow-general' and ../pe-vlan and ../ce-vlan" {
          tailf:xpath-root 3;
        }
        description
          "Reflector PE VLAN ID.";
      }
      leaf ce-vlan {
        type uint16 {
          range "1..4094";
        }
        must "../reflector-type='flow-general'" {
          tailf:xpath-root 3;
        }
        description
          "Reflector CE VLAN ID.";
      }
      leaf source-port {
        type uint16 {
          range "0..65535";
        }
        must "../reflector-type='flow-general'" {
          tailf:xpath-root 3;
        }
        default "49184";
        description
          "Reflector source port.";
      }
      leaf dest-port {
        type uint16 {
          range "0..65535";
        }
        must "../reflector-type='flow-general'" {
          tailf:xpath-root 3;
        }
        default "7";
        description
          "Reflector destination port.";
      }
      leaf end-time {
        type yang:date-and-time;
        mandatory true;
        description
          "Absolute time of reflector aging, the value must not be earlier than the current system time plus 10s or later than the current system time plus 173400s.";
      }
      leaf share-mode {
        type boolean;
        must "../share-mode = 'false' or ../reflector-type='flow-general'" {
          tailf:xpath-root 3;
        }
        default "false";
        description
          "Enable/disable the share mode on the reflector.";
      }
      choice address {
        description
          "Reflector address.";
        case ipv4-address {
          description
            "Reflector IPv4 address.";
          leaf ipv4-address {
            type inet:ipv4-address-no-zone;
            must "../reflector-type='flow-general'" {
              tailf:xpath-root 3;
            }
            description
              "Reflector IPv4 address.";
          }
        }
        case simulate-ipv4-address {
          description
            "Reflector simulate IPv4 address.";
          leaf simulate-ipv4-address {
            type inet:ipv4-address-no-zone;
            must "../reflector-type='flow-general'" {
              tailf:xpath-root 3;
            }
            description
              "Reflector simulate IPv4 address.";
          }
        }
        case mac-address {
          description
            "Reflector MAC address.";
          leaf mac-address {
            type pub-type:ncs_rpc_notif_mac-address;
            must "../reflector-type='flow-general'" {
              tailf:xpath-root 3;
            }
            description
              "Reflector MAC address.";
          }
        }
      }
      leaf survival-time {
        type uint32;
        units "s";
        config false;
        description
          "Reflector survival time.";
      }
      leaf recommended-test-mac {
        type pub-type:ncs_rpc_notif_mac-address;
        config false;
        description
          "Reflector recommended MAC address.";
      }
    }
  }

  grouping live_ncs_reflectors-type {
    description
      "Reflector table.";
    list reflector {
      key "reflector-id";
      description
        "Configure reflector table.";
      leaf reflector-id {
        type uint32 {
          range "1..65535";
        }
        description
          "Reflector ID.";
      }
      leaf if-name {
        type leafref {
          path "/ncs:devices/ncs:device/ncs:live-status/ifm:ifm/ifm:interfaces/ifm:interface/ifm:name" {
            tailf:xpath-root 3;
          }
        }
        // NCS drop mandatory statement
        description
          "Reflector interface name.";
      }
      leaf reflector-type {
        type live_ncs_reflect-type;
        // NCS drop mandatory statement
        description
          "Reflector type.";
      }
      leaf exchange-port {
        type boolean;
        // NCS drop default statement
        description
          "Enable/disable reflector UDP port exchange.";
      }
      leaf pe-vlan {
        type uint16 {
          range "1..4094";
        }
        // NCS drop must statement
        description
          "Reflector PE VLAN ID.";
      }
      leaf ce-vlan {
        type uint16 {
          range "1..4094";
        }
        // NCS drop must statement
        description
          "Reflector CE VLAN ID.";
      }
      leaf source-port {
        type uint16 {
          range "0..65535";
        }
        // NCS drop must statement
        // NCS drop default statement
        description
          "Reflector source port.";
      }
      leaf dest-port {
        type uint16 {
          range "0..65535";
        }
        // NCS drop must statement
        // NCS drop default statement
        description
          "Reflector destination port.";
      }
      leaf end-time {
        type yang:date-and-time;
        // NCS drop mandatory statement
        description
          "Absolute time of reflector aging, the value must not be earlier than the current system time plus 10s or later than the current system time plus 173400s.";
      }
      leaf share-mode {
        type boolean;
        // NCS drop must statement
        // NCS drop default statement
        description
          "Enable/disable the share mode on the reflector.";
      }
      choice address {
        description
          "Reflector address.";
        case ipv4-address {
          description
            "Reflector IPv4 address.";
          leaf ipv4-address {
            type inet:ipv4-address-no-zone;
            // NCS drop must statement
            description
              "Reflector IPv4 address.";
          }
        }
        case simulate-ipv4-address {
          description
            "Reflector simulate IPv4 address.";
          leaf simulate-ipv4-address {
            type inet:ipv4-address-no-zone;
            // NCS drop must statement
            description
              "Reflector simulate IPv4 address.";
          }
        }
        case mac-address {
          description
            "Reflector MAC address.";
          leaf mac-address {
            type pub-type:live_ncs_mac-address;
            // NCS drop must statement
            description
              "Reflector MAC address.";
          }
        }
      }
      leaf survival-time {
        type uint32;
        units "s";
        description
          "Reflector survival time.";
      }
      leaf recommended-test-mac {
        type pub-type:live_ncs_mac-address;
        description
          "Reflector recommended MAC address.";
      }
    }
  }

  grouping reflectors-type {
    description
      "Reflector table.";
    list reflector {
      key "reflector-id";
      description
        "Configure reflector table.";
      leaf reflector-id {
        type uint32 {
          range "1..65535";
        }
        description
          "Reflector ID.";
      }
      leaf if-name {
        type leafref {
          path "/ncs:devices/ncs:device/ncs:config/ifm:ifm/ifm:interfaces/ifm:interface/ifm:name" {
            tailf:xpath-root 3;
          }
        }
        mandatory true;
        description
          "Reflector interface name.";
      }
      leaf reflector-type {
        type reflect-type;
        mandatory true;
        description
          "Reflector type.";
      }
      leaf exchange-port {
        type boolean;
        default "false";
        description
          "Enable/disable reflector UDP port exchange.";
      }
      leaf pe-vlan {
        type uint16 {
          range "1..4094";
        }
        must "../reflector-type='flow-general' and ../pe-vlan and ../ce-vlan" {
          tailf:xpath-root 3;
        }
        description
          "Reflector PE VLAN ID.";
      }
      leaf ce-vlan {
        type uint16 {
          range "1..4094";
        }
        must "../reflector-type='flow-general'" {
          tailf:xpath-root 3;
        }
        description
          "Reflector CE VLAN ID.";
      }
      leaf source-port {
        type uint16 {
          range "0..65535";
        }
        must "../reflector-type='flow-general'" {
          tailf:xpath-root 3;
        }
        default "49184";
        description
          "Reflector source port.";
      }
      leaf dest-port {
        type uint16 {
          range "0..65535";
        }
        must "../reflector-type='flow-general'" {
          tailf:xpath-root 3;
        }
        default "7";
        description
          "Reflector destination port.";
      }
      leaf end-time {
        type yang:date-and-time;
        mandatory true;
        description
          "Absolute time of reflector aging, the value must not be earlier than the current system time plus 10s or later than the current system time plus 173400s.";
      }
      leaf share-mode {
        type boolean;
        must "../share-mode = 'false' or ../reflector-type='flow-general'" {
          tailf:xpath-root 3;
        }
        default "false";
        description
          "Enable/disable the share mode on the reflector.";
      }
      choice address {
        description
          "Reflector address.";
        case ipv4-address {
          description
            "Reflector IPv4 address.";
          leaf ipv4-address {
            type inet:ipv4-address-no-zone;
            must "../reflector-type='flow-general'" {
              tailf:xpath-root 3;
            }
            description
              "Reflector IPv4 address.";
          }
        }
        case simulate-ipv4-address {
          description
            "Reflector simulate IPv4 address.";
          leaf simulate-ipv4-address {
            type inet:ipv4-address-no-zone;
            must "../reflector-type='flow-general'" {
              tailf:xpath-root 3;
            }
            description
              "Reflector simulate IPv4 address.";
          }
        }
        case mac-address {
          description
            "Reflector MAC address.";
          leaf mac-address {
            type pub-type:mac-address;
            must "../reflector-type='flow-general'" {
              tailf:xpath-root 3;
            }
            description
              "Reflector MAC address.";
          }
        }
      }
      // NCS drop config false leaf 'survival-time'
      // NCS drop config false leaf 'recommended-test-mac'
    }
  }
}
