submodule huawei-nqa-global {
  // Generated by yanger -t ncs
  tailf:mount-id "huawei-nc-1.0:huawei-nc-1.0";

  yang-version 1;
  belongs-to huawei-nqa {
    prefix nqa;
  }

  import huawei-ifm {
    prefix ifm;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Description of submodule nqa-global.";

  revision 2020-07-04 {
    description
      "Add BIERv6 OAM.";
    reference "Huawei private.";
  }
  revision 2019-03-30 {
    description
      "Initial revision.";
    reference "Huawei private.";
  }

  grouping ncs_template_global-type {
    description
      "Global configuration.";
    leaf fec-validation-ldp-enable {
      type string;
      // NCS drop default statement
      description
        "Enable/disable LDP FEC validation.";
    }
    leaf fec-validation-sr-prefix-enable {
      type string;
      // NCS drop default statement
      description
        "Enable/disable sr-prefix FEC validation.";
    }
    leaf lspv-cpu-limit {
      type string;
      // NCS drop default statement
      description
        "Lspv cpu limit.";
    }
    leaf jitter-tag-version {
      type string;
      // NCS drop default statement
      description
        "Version number of jitter.";
    }
    leaf lbm-receive-enable {
      type string;
      // NCS drop default statement
      description
        "Enable/disable a device from receiving LBM packets.";
    }
    leaf ltm-receive-enable {
      type string;
      // NCS drop default statement
      description
        "Enable/disable a device from receiving LTM packets.";
    }
    leaf gmac-ltm-receive-enable {
      type string;
      // NCS drop default statement
      description
        "Enable/disable a device from receiving GMAC-LTM packets.";
    }
    leaf lspv-enable {
      type string;
      // NCS drop default statement
      description
        "Enable/disable a device to respond to MPLS echo request packets.";
    }
    leaf lspv-ipv6-enable {
      type string;
      // NCS drop default statement
      description
        "Enable/disable a device to respond to MPLS echo request IPv6 packets.";
    }
    leaf lspv-fec-compitable-enable {
      type string;
      // NCS drop default statement
      description
        "Enable/disable the LSPV's compatibility function, and reply response packets don't carry FEC information.";
    }
    leaf gmac-ping-enable {
      type string;
      // NCS drop default statement
      description
        "Enable/disable general GMAC ping function.";
    }
    leaf gmac-trace-enable {
      type string;
      // NCS drop default statement
      description
        "Enable/disable general GMAC trace function.";
    }
    container vxlan-echo-v4 {
      presence "If enabled vxlan echo IPv4";
      description
        "Enable/disable NQA VXLANECHO.";
      leaf port {
        type string;
        // NCS drop mandatory statement
        description
          "Port of NQA VXLANECHO server.";
      }
      leaf source-ip-if-name {
        type string;
        description
          "Source ip interface of VXLANECHO.";
      }
    }
    container bier6-oam {
      description
        "Configure BIERv6 OAM.";
      leaf dest-port {
        type string;
        // NCS drop default statement
        description
          "Destination UDP port of BIERv6 echo packet.";
      }
      leaf echo-reply-disable {
        type string;
        // NCS drop default statement
        description
          "Enable/disable BIERv6 reply function.";
      }
      leaf rate-limit {
        type string;
        units "pps";
        // NCS drop default statement
        description
          "BIERv6 receive rate limit.";
      }
    }
  }

  grouping ncs_rpc_notif_global-type {
    description
      "Global configuration.";
    leaf fec-validation-ldp-enable {
      type boolean;
      default "true";
      description
        "Enable/disable LDP FEC validation.";
    }
    leaf fec-validation-sr-prefix-enable {
      type boolean;
      default "true";
      description
        "Enable/disable sr-prefix FEC validation.";
    }
    leaf lspv-cpu-limit {
      type uint16 {
        range "10..65535";
      }
      default "1000";
      description
        "Lspv cpu limit.";
    }
    leaf jitter-tag-version {
      type uint32 {
        range "1..2";
      }
      default "1";
      description
        "Version number of jitter.";
    }
    leaf lbm-receive-enable {
      type boolean;
      default "true";
      description
        "Enable/disable a device from receiving LBM packets.";
    }
    leaf ltm-receive-enable {
      type boolean;
      default "true";
      description
        "Enable/disable a device from receiving LTM packets.";
    }
    leaf gmac-ltm-receive-enable {
      type boolean;
      default "true";
      description
        "Enable/disable a device from receiving GMAC-LTM packets.";
    }
    leaf lspv-enable {
      type boolean;
      default "true";
      description
        "Enable/disable a device to respond to MPLS echo request packets.";
    }
    leaf lspv-ipv6-enable {
      type boolean;
      default "true";
      description
        "Enable/disable a device to respond to MPLS echo request IPv6 packets.";
    }
    leaf lspv-fec-compitable-enable {
      type boolean;
      default "false";
      description
        "Enable/disable the LSPV's compatibility function, and reply response packets don't carry FEC information.";
    }
    leaf gmac-ping-enable {
      type boolean;
      default "false";
      description
        "Enable/disable general GMAC ping function.";
    }
    leaf gmac-trace-enable {
      type boolean;
      default "false";
      description
        "Enable/disable general GMAC trace function.";
    }
    container vxlan-echo-v4 {
      presence "If enabled vxlan echo IPv4";
      description
        "Enable/disable NQA VXLANECHO.";
      leaf port {
        type uint16 {
          range "1..65535";
        }
        mandatory true;
        description
          "Port of NQA VXLANECHO server.";
      }
      leaf source-ip-if-name {
        type string;
        description
          "Source ip interface of VXLANECHO.";
      }
    }
    container bier6-oam {
      description
        "Configure BIERv6 OAM.";
      leaf dest-port {
        type uint16 {
          range "1..65535";
        }
        default "49100";
        description
          "Destination UDP port of BIERv6 echo packet.";
      }
      leaf echo-reply-disable {
        type boolean;
        default "false";
        description
          "Enable/disable BIERv6 reply function.";
      }
      leaf rate-limit {
        type uint16 {
          range "10..65535";
        }
        units "pps";
        default "1000";
        description
          "BIERv6 receive rate limit.";
      }
    }
  }

  grouping live_ncs_global-type {
    description
      "Global configuration.";
    leaf fec-validation-ldp-enable {
      type boolean;
      // NCS drop default statement
      description
        "Enable/disable LDP FEC validation.";
    }
    leaf fec-validation-sr-prefix-enable {
      type boolean;
      // NCS drop default statement
      description
        "Enable/disable sr-prefix FEC validation.";
    }
    leaf lspv-cpu-limit {
      type uint16 {
        range "10..65535";
      }
      // NCS drop default statement
      description
        "Lspv cpu limit.";
    }
    leaf jitter-tag-version {
      type uint32 {
        range "1..2";
      }
      // NCS drop default statement
      description
        "Version number of jitter.";
    }
    leaf lbm-receive-enable {
      type boolean;
      // NCS drop default statement
      description
        "Enable/disable a device from receiving LBM packets.";
    }
    leaf ltm-receive-enable {
      type boolean;
      // NCS drop default statement
      description
        "Enable/disable a device from receiving LTM packets.";
    }
    leaf gmac-ltm-receive-enable {
      type boolean;
      // NCS drop default statement
      description
        "Enable/disable a device from receiving GMAC-LTM packets.";
    }
    leaf lspv-enable {
      type boolean;
      // NCS drop default statement
      description
        "Enable/disable a device to respond to MPLS echo request packets.";
    }
    leaf lspv-ipv6-enable {
      type boolean;
      // NCS drop default statement
      description
        "Enable/disable a device to respond to MPLS echo request IPv6 packets.";
    }
    leaf lspv-fec-compitable-enable {
      type boolean;
      // NCS drop default statement
      description
        "Enable/disable the LSPV's compatibility function, and reply response packets don't carry FEC information.";
    }
    leaf gmac-ping-enable {
      type boolean;
      // NCS drop default statement
      description
        "Enable/disable general GMAC ping function.";
    }
    leaf gmac-trace-enable {
      type boolean;
      // NCS drop default statement
      description
        "Enable/disable general GMAC trace function.";
    }
    container vxlan-echo-v4 {
      presence "If enabled vxlan echo IPv4";
      description
        "Enable/disable NQA VXLANECHO.";
      leaf port {
        type uint16 {
          range "1..65535";
        }
        // NCS drop mandatory statement
        description
          "Port of NQA VXLANECHO server.";
      }
      leaf source-ip-if-name {
        type leafref {
          path "/ncs:devices/ncs:device/ncs:live-status/ifm:ifm/ifm:interfaces/ifm:interface/ifm:name" {
            tailf:xpath-root 3;
          }
        }
        description
          "Source ip interface of VXLANECHO.";
      }
    }
    container bier6-oam {
      description
        "Configure BIERv6 OAM.";
      leaf dest-port {
        type uint16 {
          range "1..65535";
        }
        // NCS drop default statement
        description
          "Destination UDP port of BIERv6 echo packet.";
      }
      leaf echo-reply-disable {
        type boolean;
        // NCS drop default statement
        description
          "Enable/disable BIERv6 reply function.";
      }
      leaf rate-limit {
        type uint16 {
          range "10..65535";
        }
        units "pps";
        // NCS drop default statement
        description
          "BIERv6 receive rate limit.";
      }
    }
  }

  grouping global-type {
    description
      "Global configuration.";
    leaf fec-validation-ldp-enable {
      type boolean;
      default "true";
      description
        "Enable/disable LDP FEC validation.";
    }
    leaf fec-validation-sr-prefix-enable {
      type boolean;
      default "true";
      description
        "Enable/disable sr-prefix FEC validation.";
    }
    leaf lspv-cpu-limit {
      type uint16 {
        range "10..65535";
      }
      default "1000";
      description
        "Lspv cpu limit.";
    }
    leaf jitter-tag-version {
      type uint32 {
        range "1..2";
      }
      default "1";
      description
        "Version number of jitter.";
    }
    leaf lbm-receive-enable {
      type boolean;
      default "true";
      description
        "Enable/disable a device from receiving LBM packets.";
    }
    leaf ltm-receive-enable {
      type boolean;
      default "true";
      description
        "Enable/disable a device from receiving LTM packets.";
    }
    leaf gmac-ltm-receive-enable {
      type boolean;
      default "true";
      description
        "Enable/disable a device from receiving GMAC-LTM packets.";
    }
    leaf lspv-enable {
      type boolean;
      default "true";
      description
        "Enable/disable a device to respond to MPLS echo request packets.";
    }
    leaf lspv-ipv6-enable {
      type boolean;
      default "true";
      description
        "Enable/disable a device to respond to MPLS echo request IPv6 packets.";
    }
    leaf lspv-fec-compitable-enable {
      type boolean;
      default "false";
      description
        "Enable/disable the LSPV's compatibility function, and reply response packets don't carry FEC information.";
    }
    leaf gmac-ping-enable {
      type boolean;
      default "false";
      description
        "Enable/disable general GMAC ping function.";
    }
    leaf gmac-trace-enable {
      type boolean;
      default "false";
      description
        "Enable/disable general GMAC trace function.";
    }
    container vxlan-echo-v4 {
      presence "If enabled vxlan echo IPv4";
      description
        "Enable/disable NQA VXLANECHO.";
      leaf port {
        type uint16 {
          range "1..65535";
        }
        mandatory true;
        description
          "Port of NQA VXLANECHO server.";
      }
      leaf source-ip-if-name {
        type leafref {
          path "/ncs:devices/ncs:device/ncs:config/ifm:ifm/ifm:interfaces/ifm:interface/ifm:name" {
            tailf:xpath-root 3;
          }
        }
        description
          "Source ip interface of VXLANECHO.";
      }
    }
    container bier6-oam {
      description
        "Configure BIERv6 OAM.";
      leaf dest-port {
        type uint16 {
          range "1..65535";
        }
        default "49100";
        description
          "Destination UDP port of BIERv6 echo packet.";
      }
      leaf echo-reply-disable {
        type boolean;
        default "false";
        description
          "Enable/disable BIERv6 reply function.";
      }
      leaf rate-limit {
        type uint16 {
          range "10..65535";
        }
        units "pps";
        default "1000";
        description
          "BIERv6 receive rate limit.";
      }
    }
  }
}
