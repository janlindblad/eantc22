module huawei-srpolicy {
  // Generated by yanger -t ncs
  tailf:mount-id "huawei-nc-1.0:huawei-nc-1.0";
  tailf:ncs-device-type "netconf";

  namespace "urn:huawei:yang:huawei-srpolicy";
  prefix srpolicy;

  import huawei-extension {
    prefix ext;
  }
  import huawei-segment-routing {
    prefix sr;
  }
  import huawei-network-instance {
    prefix ni;
  }
  import ietf-inet-types {
    prefix inet;
  }
  import huawei-srv6 {
    prefix srv6;
  }
  import ietf-yang-types {
    prefix yang;
  }
  import huawei-pub-type {
    prefix pub-type;
  }
  include huawei-srpolicy-type;
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Segment Routing Policy.";

  revision 2020-09-14 {
    description
      "Increate the weight and BFD bypass and attribute template.";
    reference "Huawei private.";
  }
  revision 2020-08-14 {
    description
      "Increate sid compress.";
    reference "Huawei private.";
  }
  revision 2020-06-28 {
    description
      "Modify description information.";
    reference "Huawei private.";
  }
  revision 2020-06-20 {
    description
      "Modify the type of template info.";
    reference "Huawei private.";
  }
  revision 2020-06-01 {
    description
      "Increate the path verification.";
    reference "Huawei private.";
  }
  revision 2020-05-28 {
    description
      "Increate the policy-template.";
    reference "Huawei private.";
  }
  revision 2020-05-25 {
    description
      "Increate the policy-maps.";
    reference "Huawei private.";
  }
  revision 2020-05-20 {
    description
      "Modify the srpolicy, admin-state.";
    reference "Huawei private.";
  }
  revision 2020-03-26 {
    description
      "Modify description information by new rules.";
    reference "Huawei private.";
  }
  revision 2020-03-24 {
    description
      "Modify the policy-attributes.";
    reference "Huawei private.";
  }
  revision 2020-03-16 {
    description
      "Modify description information by new rules.";
    reference "Huawei private.";
  }
  revision 2020-02-28 {
    description
      "Modify description information.";
    reference "Huawei private.";
  }
  revision 2020-02-17 {
    description
      "Increate the path-mtu.";
    reference "Huawei private.";
  }
  revision 2020-01-03 {
    description
      "Modify description information.";
    reference "Huawei private.";
  }
  revision 2019-11-18 {
    description
      "Increate the SR-MPLS TE Policy group.";
    reference "Huawei private.";
  }
  revision 2019-04-04 {
    description
      "Init revision.";
    reference "Huawei private.";
  }
  ext:task-name "srpolicy";

  grouping ncs_template_bfd {
    description
      "SR Policy BFD configuration.";
    container bfd {
      description
        "Configure SR Policy BFD.";
      leaf enable {
        type ncs_template_bfd-enable-type;
        // NCS drop default statement
        description
          "Enable seamless-bfd for all SR Policies.";
      }
      leaf bypass {
        type ncs_template_bfd-bypass-type;
        // NCS drop default statement
        description
          "Enable BFD bypass for all SR policies.";
      }
      leaf min-tx {
        type string;
        units "ms";
        // NCS drop default statement
        description
          "Minimum interval for sending seamless-bfd packets to the peer end. The range and default are based on PAF.";
      }
      leaf min-rx {
        type string;
        units "ms";
        // NCS drop default statement
        description
          "Minimum interval for receiving seamless-bfd packets from the peer end. The range and default are based on PAF.";
      }
      leaf multi-num {
        type string;
        // NCS drop default statement
        description
          "Local detection multiplier.";
      }
      leaf backup-min-tx {
        type string;
        units "ms";
        description
          "Minimum interval for sending seamless-bfd packets to the peer end over the backup candidate path. The range and default are based on PAF.";
      }
      leaf backup-multi-num {
        type string;
        description
          "Local detection multiplier over the backup candidate path.";
      }
    }
  }

  grouping ncs_template_global-attributes {
    description
      "SR Policy global configuration.";
    leaf switch-delay {
      type string;
      units "ms";
      // NCS drop default statement
      description
        "MBB switch delay time.";
    }
    leaf delete-delay {
      type string;
      units "ms";
      // NCS drop default statement
      description
        "MBB delete delay time.";
    }
    leaf hsb-enable {
      type string;
      // NCS drop default statement
      description
        "Enable/disable hot standby.";
    }
    leaf traffic-statistics-enable {
      type string;
      // NCS drop default statement
      description
        "Enable/disable traffic statistics collection.";
    }
    leaf bgp-ls-enable {
      type string;
      // NCS drop default statement
      description
        "Enable/disable BGP-LS.";
    }
    leaf path-verification {
      type string;
      // NCS drop default statement
      description
        "Enable/disable path verification.";
    }
    leaf suppress-flapping {
      type string;
      // NCS drop default statement
      description
        "Enable/disable suppress flapping.";
    }
    leaf policy-threshold-upper {
      type string;
      // NCS drop must statement
      // NCS drop default statement
      description
        "SR Policy threshold upper limit.";
    }
    leaf policy-threshold-lower {
      type string;
      // NCS drop default statement
      description
        "SR Policy threshold lower limit.";
    }
    leaf list-threshold-upper {
      type string;
      // NCS drop must statement
      // NCS drop default statement
      description
        "Segment List threshold upper limit.";
    }
    leaf list-threshold-lower {
      type string;
      // NCS drop default statement
      description
        "Segment List threshold lower limit.";
    }
    leaf group-threshold-upper {
      type string;
      // NCS drop must statement
      // NCS drop default statement
      description
        "Upper threshold for the number of SR Policy groups.";
    }
    leaf group-threshold-lower {
      type string;
      // NCS drop default statement
      description
        "Lower threshold for the number of SR Policy groups.";
    }
    uses ncs_template_bfd;
  }

  grouping ncs_template_srv4-segment-lists {
    description
      "Global segment lists.";
    container segment-lists {
      description
        "List of global segment lists.";
      list segment-list {
        // NCS patched for predictable order
        ordered-by user;
        key "name";
        description
          "Configure a global segment list.";
        leaf name {
          type string;
          description
            "Global segment list name.";
        }
        container segments {
          description
            "List of segments in a global segment list.";
          list segment {
            // NCS patched for predictable order
            ordered-by user;
            key "index";
            // NCS drop max-elements statement
            description
              "Configure a segment in a global segment list.";
            leaf index {
              type string;
              description
                "The segment index.";
            }
            choice type {
              // NCS drop mandatory statement
              description
                "The segment type.";
              case segment-type-1 {
                description
                  "The segment is declared by MPLS label.";
                leaf sid-value-1 {
                  type string;
                  description
                    "MPLS label value.";
                }
              }
            }
          }
        }
      }
    }
  }

  grouping ncs_template_srv6-segment-lists {
    description
      "Global segment lists.";
    container segment-lists {
      description
        "List of global segment lists.";
      list segment-list {
        // NCS patched for predictable order
        ordered-by user;
        key "name";
        description
          "Configure a global segment list.";
        leaf name {
          type string;
          description
            "Global segment list name.";
        }
        container segments {
          description
            "List of segments in a global segment list.";
          list segment {
            // NCS patched for predictable order
            ordered-by user;
            key "index";
            // NCS drop max-elements statement
            description
              "Configure a segment in a global segment list.";
            leaf index {
              type string;
              description
                "The segment index.";
            }
            choice type {
              // NCS drop mandatory statement
              description
                "The segment type.";
              case segment-type-2 {
                description
                  "The segment is declared by SRv6 SID value.";
                leaf sid-value-2 {
                  type string;
                  // NCS drop mandatory statement
                  description
                    "SRv6 sid value.";
                }
                leaf block-length {
                  type string;
                  // NCS drop must statement
                  description
                    "SRv6 SID block length.";
                }
              }
            }
          }
        }
      }
    }
  }

  grouping ncs_template_srv6-policy-attributes {
    description
      "Grouping containing attributes applicable to all SR policies.";
    container policy-attributes {
      description
        "Configure attributes for all SR policies.";
      uses ncs_template_global-attributes;
      leaf locator {
        ext:operation-exclude "update";
        type string;
        description
          "Locator Name.";
      }
      uses ncs_template_srv6-segment-lists;
    }
  }

  grouping ncs_template_srv4-policy-attributes {
    description
      "Grouping containing attributes applicable to all SR policies.";
    container policy-attributes {
      description
        "Configure attributes for all SR policies.";
      uses ncs_template_global-attributes;
      uses ncs_template_srv4-segment-lists;
    }
  }

  grouping ncs_template_candidate-paths {
    description
      "Grouping containing candidate paths to all SR policies.";
    container candidate-paths {
      description
        "List of candidate paths in an SR Policy.";
      list candidate-path {
        // NCS patched for predictable order
        ordered-by user;
        // NCS drop must statement
        key "protocol-origin originator discriminator";
        // NCS drop max-elements statement
        description
          "Configure a candidate path.";
        leaf protocol-origin {
          type ncs_template_protocol-origin-type;
          // NCS drop must statement
          description
            "Candidate path protocol origin.";
        }
        leaf originator {
          type string;
          // NCS drop must statement
          description
            "Candidate path originator.";
        }
        leaf discriminator {
          type string;
          description
            "Candidate path discriminator.";
        }
        leaf preference {
          type string;
          // NCS drop mandatory statement
          description
            "Candidate path preference.";
        }
        choice type {
          description
            "Type of candidate paths.";
          case explicit {
            description
              "Candidate path with explicitly defined set/s of segment-lists.";
            container segment-lists {
              description
                "List of segment lists in a candidate path.";
              list segment-list {
                // NCS patched for predictable order
                ordered-by user;
                key "name";
                // NCS drop max-elements statement
                description
                  "Configure a segment list for a candidate path.";
                leaf name {
                  type string;
                  description
                    "Segment list name.";
                }
                leaf weight {
                  type string;
                  // NCS drop default statement
                  description
                    "Segment-list weighted loadshare.";
                }
                leaf path-mtu {
                  type string;
                  description
                    "Segment-list path-mtu.";
                }
              }
            }
          }
        }
        leaf template-id {
          type string;
          description
            "Attribute template ID.";
        }
        leaf network-slice-id {
          type string;
          description
            "Network slice ID of candidate path.";
        }
      }
    }
  }

  grouping ncs_template_srv4-policys {
    description
      "SR policy grouping.";
    container policys {
      description
        "List of SR Policies.";
      list policy {
        // NCS patched for predictable order
        ordered-by user;
        key "endpoint color";
        unique "name";
        unique "binding-sid/value";
        description
          "Configure an SR Policy.";
        leaf endpoint {
          type string;
          description
            "SR Policy endpoint address.";
        }
        leaf color {
          type string;
          description
            "SR Policy color.";
        }
        leaf name {
          type string;
          // NCS drop mandatory statement
          description
            "SR Policy name.";
        }
        container binding-sid {
          description
            "Configure a binding SID.";
          leaf dataplane {
            type ncs_template_dataplane-type;
            // NCS drop must statement
            description
              "Binding sid dataplane type.";
          }
          leaf value {
            // NCS drop when statement
            type ncs_template_sid-value-type;
            // NCS drop mandatory statement
            description
              "Binding sid value.";
          }
        }
        leaf admin-state {
          type ncs_template_admin-state-type;
          // NCS drop default statement
          description
            "Close the function of SR Policy.";
        }
        leaf mtu {
          type string;
          description
            "SR Policy mtu value.";
        }
        leaf hsb-enable {
          type ncs_template_enable-3types;
          // NCS drop default statement
          description
            "SR Policy hot standby.";
        }
        leaf bfd-enable {
          type ncs_template_policy-bfd-enable-type;
          // NCS drop default statement
          description
            "SR Policy BFD.";
        }
        leaf traffic-statistics-enable {
          type ncs_template_enable-3types;
          // NCS drop default statement
          description
            "SR Policy traffic statistics.";
        }
        container diffserv-mode {
          description
            "Configure the DiffServ mode in an SR Policy.";
          leaf pipe-mode {
            type ncs_template_pipe-mode-type;
            description
              "Specifies the pipe mode of SR Policy.";
          }
          leaf service-class {
            // NCS drop when statement
            type ncs_template_serv-class-types;
            // NCS drop mandatory statement
            description
              "Service class of SR Policy.";
          }
          leaf service-color {
            // NCS drop when statement
            type ncs_template_serv-color-types;
            // NCS drop mandatory statement
            description
              "Service color of SR Policy.";
          }
        }
        uses ncs_template_candidate-paths;
      }
    }
  }

  grouping ncs_template_srv6-policys {
    description
      "SR policy grouping.";
    container policys {
      description
        "List of SR Policies.";
      list policy {
        // NCS patched for predictable order
        ordered-by user;
        key "endpoint color";
        unique "name";
        unique "binding-sid/value";
        description
          "Configure an SR Policy.";
        leaf endpoint {
          type string;
          description
            "SR Policy endpoint address.";
        }
        leaf color {
          type string;
          description
            "SR Policy color.";
        }
        leaf name {
          type string;
          // NCS drop mandatory statement
          description
            "SR Policy name.";
        }
        container binding-sid {
          // NCS drop must statement
          description
            "Configure a binding SID.";
          leaf dataplane {
            type ncs_template_dataplane-type;
            // NCS drop must statement
            description
              "Binding sid dataplane type.";
          }
          leaf value {
            // NCS drop when statement
            type ncs_template_sid-value-type;
            // NCS drop mandatory statement
            description
              "Binding sid value.";
          }
        }
        leaf admin-state {
          type ncs_template_admin-state-type;
          // NCS drop default statement
          description
            "Close the function of SR Policy.";
        }
        leaf mtu {
          type string;
          description
            "SR Policy mtu value.";
        }
        leaf hsb-enable {
          type ncs_template_enable-3types;
          // NCS drop default statement
          description
            "SR Policy hot standby.";
        }
        leaf bfd-enable {
          type ncs_template_policy-bfd-enable-type;
          // NCS drop default statement
          description
            "SR Policy BFD.";
        }
        leaf bfd-bypass {
          type ncs_template_policy-bfd-bypass-type;
          // NCS drop default statement
          description
            "SR policy BFD bypass.";
        }
        leaf traffic-statistics-enable {
          type ncs_template_enable-3types;
          // NCS drop default statement
          description
            "SR Policy traffic statistics.";
        }
        leaf path-verification {
          type ncs_template_enable-3types;
          // NCS drop default statement
          description
            "SR Policy path verification.";
        }
        container diffserv-mode {
          description
            "Configure the DiffServ mode in an SR Policy.";
          leaf pipe-mode {
            type ncs_template_pipe-mode-type;
            description
              "Specifies the pipe mode of SR Policy.";
          }
          leaf service-class {
            // NCS drop when statement
            type ncs_template_serv-class-types;
            // NCS drop mandatory statement
            description
              "Service class of SR Policy.";
          }
          leaf service-color {
            // NCS drop when statement
            type ncs_template_serv-color-types;
            // NCS drop mandatory statement
            description
              "Service color of SR Policy.";
          }
        }
        uses ncs_template_candidate-paths;
      }
    }
  }

  grouping ncs_template_policy-groups {
    description
      "SR-MPLS TE Policy group grouping.";
    container policy-groups {
      description
        "List of SR-MPLS TE Policy groups.";
      list policy-group {
        // NCS patched for predictable order
        ordered-by user;
        key "index";
        description
          "Configure an SR-MPLS TE Policy group.";
        leaf index {
          type string;
          description
            "SR-MPLS TE Policy group id.";
        }
        leaf endpoint {
          type string;
          description
            "SR-MPLS TE Policy IPv4 endPoint address.";
        }
        // NCS drop config false leaf state
        // NCS drop config false leaf 'tunnel-id'
        // NCS drop config false leaf 'tunnel-type'
        // NCS drop config false leaf 'match-count'
        // NCS drop config false leaf 'up-match-count'
        container color-dscp-matchs {
          description
            "List of color-address family-DSCP mappings for an SR-MPLS TE Policy.";
          list color-dscp-match {
            // NCS patched for predictable order
            ordered-by user;
            key "color af-type";
            // NCS drop max-elements statement
            description
              "Configure a color-address family-DSCP mapping for an SR-MPLS TE Policy.";
            leaf color {
              type string;
              description
                "SR-MPLS TE Policy color.";
            }
            leaf af-type {
              type ncs_template_address-family-type;
              description
                "Address family.";
            }
            leaf default {
              type string;
              // NCS drop default statement
              description
                "Enable/disable the default SR-MPLS TE Policy.";
            }
            leaf dscp-value {
              // NCS drop when statement
              type pub-type:ncs_template_id-range;
              // NCS drop mandatory statement
              description
                "DSCP Value.";
            }
            // NCS drop config false leaf 'policy-tunnel-id'
          }
        }
      }
    }
  }

  grouping ncs_template_traffic-statistics {
    description
      "SR Policy traffic statistics grouping.";
    // NCS drop config false container 'policy-traffic-statistics'
    // NCS drop config false container 'list-traffic-statistics'
  }

  grouping ncs_template_srv6-policy-infos {
    description
      "SRv6 Policy infos grouping.";
    // NCS drop config false container 'policy-infos'
  }

  grouping ncs_template_srv4-policy-infos {
    description
      "SR-MPLS TE Policy infos grouping.";
    // NCS drop config false container 'policy-infos'
  }

  grouping ncs_template_sr-template-infos {
    description
      "SR Policy template infos.";
    // NCS drop config false container 'template-infos'
  }

  grouping ncs_template_srv6-source-sids {
    description
      "SRv6 TE Policy SID informations.";
    // NCS drop config false container 'source-sids'
  }

  grouping ncs_template_srv6-sid-statistics {
    description
      "SRv6 Policy SID statistics infos.";
    // NCS drop config false container 'sid-statistics'
  }

  grouping ncs_template_reset-traffic-statistics {
    description
      "Reset SR Policy traffic statistics.";
    leaf name {
      type string;
      description
        "SR Policy name.";
    }
    leaf endpoint {
      type string;
      description
        "SR Policy endpoint address.";
    }
    leaf color {
      type string;
      description
        "SR Policy color.";
    }
    leaf binding-sid {
      type ncs_template_sid-value-type;
      description
        "SR Policy binding sid.";
    }
  }

  grouping ncs_template_policy-maps {
    description
      "SR Policy mappings.";
    container sr-policy-maps {
      description
        "List of SR Policy mappings.";
      list sr-policy-map {
        // NCS patched for predictable order
        ordered-by user;
        // NCS drop must statement
        key "color af-type flow-priority-type";
        // NCS drop max-elements statement
        description
          "Configure an SR Policy mapping.";
        leaf color {
          type string;
          description
            "Color of an SR Policy.";
        }
        leaf af-type {
          type ncs_template_address-family-type;
          description
            "Address family type.";
        }
        leaf flow-priority-type {
          type ncs_template_flow-priority-type;
          description
            "Traffic priority type.";
        }
        leaf dscp-value {
          // NCS drop when statement
          type ncs_template_dscp-type;
          // NCS drop mandatory statement
          description
            "DSCP list.";
        }
      }
    }
  }

  grouping ncs_template_dynamic-policy-group {
    description
      "Dynamic SR Policy groups.";
    // NCS drop config false container 'dynamic-sr-policy-groups'
  }

  grouping ncs_template_dynamic-policy-group-down-reason {
    description
      "Dynamic SR Policy group down reason.";
    // NCS drop config false container 'dynamic-policy-group-down-reasons'
  }

  grouping ncs_template_policy-group-statistics {
    description
      "SR Policy group statistics.";
    // NCS drop config false container 'policy-group-statistic'
  }

  grouping ncs_rpc_notif_bfd {
    description
      "SR Policy BFD configuration.";
    container bfd {
      description
        "Configure SR Policy BFD.";
      leaf enable {
        type ncs_rpc_notif_bfd-enable-type;
        default "disable";
        description
          "Enable seamless-bfd for all SR Policies.";
      }
      leaf bypass {
        type ncs_rpc_notif_bfd-bypass-type;
        default "bypass";
        description
          "Enable BFD bypass for all SR policies.";
      }
      leaf min-tx {
        type uint32 {
          range "1..4294967295";
        }
        units "ms";
        default "10";
        description
          "Minimum interval for sending seamless-bfd packets to the peer end. The range and default are based on PAF.";
      }
      leaf min-rx {
        type uint32 {
          range "1..4294967295";
        }
        units "ms";
        default "10";
        description
          "Minimum interval for receiving seamless-bfd packets from the peer end. The range and default are based on PAF.";
      }
      leaf multi-num {
        type uint32 {
          range "3..50";
        }
        default "3";
        description
          "Local detection multiplier.";
      }
      leaf backup-min-tx {
        type uint32 {
          range "1..4294967295";
        }
        units "ms";
        description
          "Minimum interval for sending seamless-bfd packets to the peer end over the backup candidate path. The range and default are based on PAF.";
      }
      leaf backup-multi-num {
        type uint32 {
          range "3..50";
        }
        description
          "Local detection multiplier over the backup candidate path.";
      }
    }
  }

  grouping ncs_rpc_notif_global-attributes {
    description
      "SR Policy global configuration.";
    leaf switch-delay {
      type uint32 {
        range "0..600000";
      }
      units "ms";
      default "5000";
      description
        "MBB switch delay time.";
    }
    leaf delete-delay {
      type uint32 {
        range "0..600000";
      }
      units "ms";
      default "20000";
      description
        "MBB delete delay time.";
    }
    leaf hsb-enable {
      type boolean;
      default "false";
      description
        "Enable/disable hot standby.";
    }
    leaf traffic-statistics-enable {
      type boolean;
      default "false";
      description
        "Enable/disable traffic statistics collection.";
    }
    leaf bgp-ls-enable {
      type boolean;
      default "false";
      description
        "Enable/disable BGP-LS.";
    }
    leaf path-verification {
      type boolean;
      default "false";
      description
        "Enable/disable path verification.";
    }
    leaf suppress-flapping {
      type boolean;
      default "true";
      description
        "Enable/disable suppress flapping.";
    }
    leaf policy-threshold-upper {
      type uint32 {
        range "2..100";
      }
      must '(../policy-threshold-upper>../policy-threshold-lower)' {
        tailf:xpath-root 3;
      }
      default "80";
      description
        "SR Policy threshold upper limit.";
    }
    leaf policy-threshold-lower {
      type uint32 {
        range "1..99";
      }
      default "75";
      description
        "SR Policy threshold lower limit.";
    }
    leaf list-threshold-upper {
      type uint32 {
        range "2..100";
      }
      must '(../list-threshold-upper>../list-threshold-lower)' {
        tailf:xpath-root 3;
      }
      default "80";
      description
        "Segment List threshold upper limit.";
    }
    leaf list-threshold-lower {
      type uint32 {
        range "1..99";
      }
      default "75";
      description
        "Segment List threshold lower limit.";
    }
    leaf group-threshold-upper {
      type uint32 {
        range "2..100";
      }
      must '(../group-threshold-upper>../group-threshold-lower)' {
        tailf:xpath-root 3;
      }
      default "80";
      description
        "Upper threshold for the number of SR Policy groups.";
    }
    leaf group-threshold-lower {
      type uint32 {
        range "1..99";
      }
      default "75";
      description
        "Lower threshold for the number of SR Policy groups.";
    }
    uses ncs_rpc_notif_bfd;
  }

  grouping ncs_rpc_notif_srv4-segment-lists {
    description
      "Global segment lists.";
    container segment-lists {
      description
        "List of global segment lists.";
      list segment-list {
        key "name";
        description
          "Configure a global segment list.";
        leaf name {
          type string {
            length "1..31";
            pattern '[^ \?]*';
          }
          description
            "Global segment list name.";
        }
        container segments {
          description
            "List of segments in a global segment list.";
          list segment {
            key "index";
            max-elements 10;
            description
              "Configure a segment in a global segment list.";
            leaf index {
              type uint32 {
                range "0..4294967295";
              }
              description
                "The segment index.";
            }
            choice type {
              mandatory true;
              description
                "The segment type.";
              case segment-type-1 {
                description
                  "The segment is declared by MPLS label.";
                leaf sid-value-1 {
                  type uint32 {
                    range "16..1048575";
                  }
                  description
                    "MPLS label value.";
                }
              }
            }
          }
        }
      }
    }
  }

  grouping ncs_rpc_notif_srv6-segment-lists {
    description
      "Global segment lists.";
    container segment-lists {
      description
        "List of global segment lists.";
      list segment-list {
        key "name";
        description
          "Configure a global segment list.";
        leaf name {
          type string {
            length "1..31";
            pattern '[^ \?]*';
          }
          description
            "Global segment list name.";
        }
        container segments {
          description
            "List of segments in a global segment list.";
          list segment {
            key "index";
            max-elements 10;
            description
              "Configure a segment in a global segment list.";
            leaf index {
              type uint32 {
                range "0..4294967295";
              }
              description
                "The segment index.";
            }
            choice type {
              mandatory true;
              description
                "The segment type.";
              case segment-type-2 {
                description
                  "The segment is declared by SRv6 SID value.";
                leaf sid-value-2 {
                  type inet:ipv6-address-no-zone;
                  mandatory true;
                  description
                    "SRv6 sid value.";
                }
                leaf block-length {
                  type uint32 {
                    range "16..80";
                  }
                  must '((../block-length) mod 16 = 0)' {
                    tailf:xpath-root 3;
                  }
                  description
                    "SRv6 SID block length.";
                }
              }
            }
          }
        }
      }
    }
  }

  grouping ncs_rpc_notif_srv6-policy-attributes {
    description
      "Grouping containing attributes applicable to all SR policies.";
    container policy-attributes {
      description
        "Configure attributes for all SR policies.";
      uses ncs_rpc_notif_global-attributes;
      leaf locator {
        ext:operation-exclude "update";
        type string;
        description
          "Locator Name.";
      }
      uses ncs_rpc_notif_srv6-segment-lists;
    }
  }

  grouping ncs_rpc_notif_srv4-policy-attributes {
    description
      "Grouping containing attributes applicable to all SR policies.";
    container policy-attributes {
      description
        "Configure attributes for all SR policies.";
      uses ncs_rpc_notif_global-attributes;
      uses ncs_rpc_notif_srv4-segment-lists;
    }
  }

  grouping ncs_rpc_notif_candidate-paths {
    description
      "Grouping containing candidate paths to all SR policies.";
    container candidate-paths {
      description
        "List of candidate paths in an SR Policy.";
      list candidate-path {
        must '(discriminator=preference)' {
          tailf:xpath-root 3;
        }
        key "protocol-origin originator discriminator";
        max-elements 64;
        description
          "Configure a candidate path.";
        leaf protocol-origin {
          type ncs_rpc_notif_protocol-origin-type;
          must "(../protocol-origin='configuration')" {
            tailf:xpath-root 3;
          }
          description
            "Candidate path protocol origin.";
        }
        leaf originator {
          type string {
            length "1..60";
          }
          must "(../originator='0,0.0.0.0')" {
            tailf:xpath-root 3;
          }
          description
            "Candidate path originator.";
        }
        leaf discriminator {
          type uint32 {
            range "1..65535";
          }
          description
            "Candidate path discriminator.";
        }
        leaf preference {
          type uint32 {
            range "1..65535";
          }
          mandatory true;
          description
            "Candidate path preference.";
        }
        choice type {
          description
            "Type of candidate paths.";
          case explicit {
            description
              "Candidate path with explicitly defined set/s of segment-lists.";
            container segment-lists {
              description
                "List of segment lists in a candidate path.";
              list segment-list {
                key "name";
                max-elements 64;
                description
                  "Configure a segment list for a candidate path.";
                leaf name {
                  type leafref {
                    path "../../../../../../../policy-attributes/segment-lists/segment-list/name";
                  }
                  description
                    "Segment list name.";
                }
                leaf weight {
                  type uint32 {
                    range "0..4294967295";
                    ext:value-meaning {
                      ext:item "0" {
                        ext:meaning "Invalid";
                        description
                          "The segment list is invalid when weight is 0.";
                      }
                    }
                  }
                  default "1";
                  description
                    "Segment-list weighted loadshare.";
                }
                leaf path-mtu {
                  type uint32 {
                    range "1280..9600";
                  }
                  description
                    "Segment-list path-mtu.";
                }
              }
            }
          }
        }
        leaf template-id {
          type string;
          description
            "Attribute template ID.";
        }
        leaf network-slice-id {
          type uint32 {
            range "1..4294967295";
          }
          description
            "Network slice ID of candidate path.";
        }
      }
    }
  }

  grouping ncs_rpc_notif_srv4-policys {
    description
      "SR policy grouping.";
    container policys {
      description
        "List of SR Policies.";
      list policy {
        key "endpoint color";
        unique "name";
        unique "binding-sid/value";
        description
          "Configure an SR Policy.";
        leaf endpoint {
          type inet:ip-address;
          description
            "SR Policy endpoint address.";
        }
        leaf color {
          type uint32 {
            range "0..4294967295";
          }
          description
            "SR Policy color.";
        }
        leaf name {
          type string {
            length "1..31";
            pattern '[^ \?]*';
          }
          mandatory true;
          description
            "SR Policy name.";
        }
        container binding-sid {
          description
            "Configure a binding SID.";
          leaf dataplane {
            type ncs_rpc_notif_dataplane-type;
            must "(../dataplane='mpls')" {
              tailf:xpath-root 3;
            }
            description
              "Binding sid dataplane type.";
          }
          leaf value {
            when "(../dataplane='mpls')" {
              tailf:xpath-root 3;
            }
            type ncs_rpc_notif_sid-value-type;
            mandatory true;
            description
              "Binding sid value.";
          }
        }
        leaf admin-state {
          type ncs_rpc_notif_admin-state-type;
          default "up";
          description
            "Close the function of SR Policy.";
        }
        leaf mtu {
          type uint32 {
            range "512..9600";
          }
          description
            "SR Policy mtu value.";
        }
        leaf hsb-enable {
          type ncs_rpc_notif_enable-3types;
          default "not-configured";
          description
            "SR Policy hot standby.";
        }
        leaf bfd-enable {
          type ncs_rpc_notif_policy-bfd-enable-type;
          default "not-configured";
          description
            "SR Policy BFD.";
        }
        leaf traffic-statistics-enable {
          type ncs_rpc_notif_enable-3types;
          default "not-configured";
          description
            "SR Policy traffic statistics.";
        }
        container diffserv-mode {
          description
            "Configure the DiffServ mode in an SR Policy.";
          leaf pipe-mode {
            type ncs_rpc_notif_pipe-mode-type;
            description
              "Specifies the pipe mode of SR Policy.";
          }
          leaf service-class {
            when "../pipe-mode='pipe'" {
              tailf:xpath-root 3;
            }
            type ncs_rpc_notif_serv-class-types;
            mandatory true;
            description
              "Service class of SR Policy.";
          }
          leaf service-color {
            when "../pipe-mode='pipe'" {
              tailf:xpath-root 3;
            }
            type ncs_rpc_notif_serv-color-types;
            mandatory true;
            description
              "Service color of SR Policy.";
          }
        }
        uses ncs_rpc_notif_candidate-paths;
      }
    }
  }

  grouping ncs_rpc_notif_srv6-policys {
    description
      "SR policy grouping.";
    container policys {
      description
        "List of SR Policies.";
      list policy {
        key "endpoint color";
        unique "name";
        unique "binding-sid/value";
        description
          "Configure an SR Policy.";
        leaf endpoint {
          type inet:ip-address;
          description
            "SR Policy endpoint address.";
        }
        leaf color {
          type uint32 {
            range "0..4294967295";
          }
          description
            "SR Policy color.";
        }
        leaf name {
          type string {
            length "1..31";
            pattern '[^ \?]*';
          }
          mandatory true;
          description
            "SR Policy name.";
        }
        container binding-sid {
          must "(../../../policy-attributes/locator and /ni:network-instance/ni:instances/ni:instance[ni:name='_public_']/srv6:srv6/srv6:locators/srv6:locator[srv6:name=/ni:network-instance/ni:instances/ni:instance[ni:name='_public_']/srv6:srv6/srpolicy:srpolicy/srpolicy:policy-attributes/srpolicy:locator]/srv6:static-length>0)" {
            tailf:xpath-root 3;
          }
          description
            "Configure a binding SID.";
          leaf dataplane {
            type ncs_rpc_notif_dataplane-type;
            must "(../dataplane='srv6')" {
              tailf:xpath-root 3;
            }
            description
              "Binding sid dataplane type.";
          }
          leaf value {
            when "(../dataplane='srv6')" {
              tailf:xpath-root 3;
            }
            type ncs_rpc_notif_sid-value-type;
            mandatory true;
            description
              "Binding sid value.";
          }
        }
        leaf admin-state {
          type ncs_rpc_notif_admin-state-type;
          default "up";
          description
            "Close the function of SR Policy.";
        }
        leaf mtu {
          type uint32 {
            range "512..9600";
          }
          description
            "SR Policy mtu value.";
        }
        leaf hsb-enable {
          type ncs_rpc_notif_enable-3types;
          default "not-configured";
          description
            "SR Policy hot standby.";
        }
        leaf bfd-enable {
          type ncs_rpc_notif_policy-bfd-enable-type;
          default "not-configured";
          description
            "SR Policy BFD.";
        }
        leaf bfd-bypass {
          type ncs_rpc_notif_policy-bfd-bypass-type;
          default "not-configured";
          description
            "SR policy BFD bypass.";
        }
        leaf traffic-statistics-enable {
          type ncs_rpc_notif_enable-3types;
          default "not-configured";
          description
            "SR Policy traffic statistics.";
        }
        leaf path-verification {
          type ncs_rpc_notif_enable-3types;
          default "not-configured";
          description
            "SR Policy path verification.";
        }
        container diffserv-mode {
          description
            "Configure the DiffServ mode in an SR Policy.";
          leaf pipe-mode {
            type ncs_rpc_notif_pipe-mode-type;
            description
              "Specifies the pipe mode of SR Policy.";
          }
          leaf service-class {
            when "../pipe-mode='pipe'" {
              tailf:xpath-root 3;
            }
            type ncs_rpc_notif_serv-class-types;
            mandatory true;
            description
              "Service class of SR Policy.";
          }
          leaf service-color {
            when "../pipe-mode='pipe'" {
              tailf:xpath-root 3;
            }
            type ncs_rpc_notif_serv-color-types;
            mandatory true;
            description
              "Service color of SR Policy.";
          }
        }
        uses ncs_rpc_notif_candidate-paths;
      }
    }
  }

  grouping ncs_rpc_notif_policy-groups {
    description
      "SR-MPLS TE Policy group grouping.";
    container policy-groups {
      description
        "List of SR-MPLS TE Policy groups.";
      list policy-group {
        key "index";
        description
          "Configure an SR-MPLS TE Policy group.";
        leaf index {
          type uint32 {
            range "1..4294967295";
          }
          description
            "SR-MPLS TE Policy group id.";
        }
        leaf endpoint {
          type inet:ip-address;
          description
            "SR-MPLS TE Policy IPv4 endPoint address.";
        }
        leaf state {
          type ncs_rpc_notif_state-type;
          config false;
          description
            "SR-MPLS TE Policy group state.";
        }
        leaf tunnel-id {
          type uint32;
          config false;
          description
            "SR-MPLS TE Policy group tunnel id.";
        }
        leaf tunnel-type {
          type ncs_rpc_notif_tunnel-type;
          config false;
          description
            "SR-MPLS TE Policy group tunnel type.";
        }
        leaf match-count {
          type uint32;
          config false;
          description
            "SR-MPLS TE Policy group match count.";
        }
        leaf up-match-count {
          type uint32;
          config false;
          description
            "SR-MPLS TE Policy group up match count.";
        }
        container color-dscp-matchs {
          description
            "List of color-address family-DSCP mappings for an SR-MPLS TE Policy.";
          list color-dscp-match {
            key "color af-type";
            max-elements 128;
            description
              "Configure a color-address family-DSCP mapping for an SR-MPLS TE Policy.";
            leaf color {
              type uint32 {
                range "0..4294967295";
              }
              description
                "SR-MPLS TE Policy color.";
            }
            leaf af-type {
              type ncs_rpc_notif_address-family-type;
              description
                "Address family.";
            }
            leaf default {
              type boolean;
              default "false";
              description
                "Enable/disable the default SR-MPLS TE Policy.";
            }
            leaf dscp-value {
              when "not(../default='true')" {
                tailf:xpath-root 3;
              }
              type pub-type:ncs_rpc_notif_id-range;
              mandatory true;
              description
                "DSCP Value.";
            }
            leaf policy-tunnel-id {
              type uint32;
              config false;
              description
                "SR-MPLS TE Policy tunnel ID.";
            }
          }
        }
      }
    }
  }

  grouping ncs_rpc_notif_traffic-statistics {
    description
      "SR Policy traffic statistics grouping.";
    container policy-traffic-statistics {
      config false;
      description
        "List of traffic statistics for SR Policies.";
      list policy-traffic-statistic {
        key "endpoint color";
        description
          "Traffic statistics for an SR Policy.";
        leaf endpoint {
          type inet:ip-address-no-zone;
          description
            "Destination address of an SR Policy.";
        }
        leaf color {
          type uint32 {
            range "0..4294967295";
          }
          description
            "Color of an SR Policy.";
        }
        leaf name {
          type string {
            length "1..31";
          }
          ext:support-filter "true";
          description
            "Policy name.";
        }
        leaf binding-sid {
          type ncs_rpc_notif_sid-value-type;
          ext:support-filter "true";
          description
            "Binding SID of an SR Policy.";
        }
        leaf tunnel-id {
          type uint32;
          description
            "Tunnel ID of an SR Policy.";
        }
        leaf flow-period {
          type uint32 {
            range "0..4294967295";
          }
          units "s";
          description
            "Traffic statistics collection period.";
        }
        leaf last-period-byte-rate {
          type uint64 {
            range "0..18446744073709551615";
          }
          units "Byte/s";
          description
            "Byte rate in the latest period.";
        }
        leaf last-period-pkt-rate {
          type uint64 {
            range "0..18446744073709551615";
          }
          units "pps";
          description
            "Packet rate in the latest period.";
        }
        leaf display-interval {
          type uint64 {
            range "0..18446744073709551615";
          }
          units "s";
          description
            "Interval between two queries.";
        }
        leaf interval-byte-rate {
          type uint64 {
            range "0..18446744073709551615";
          }
          units "Byte/s";
          description
            "Byte rate between two queries.";
        }
        leaf interval-pkt-rate {
          type uint64 {
            range "0..18446744073709551615";
          }
          units "pps";
          description
            "Packet rate between two queries.";
        }
        leaf total-byte {
          type uint64 {
            range "0..18446744073709551615";
          }
          units "Byte";
          description
            "Total number of transmitted bytes.";
        }
        leaf total-packet {
          type uint64 {
            range "0..18446744073709551615";
          }
          units "packet";
          description
            "Total number of transmitted packets.";
        }
      }
    }
    container list-traffic-statistics {
      config false;
      description
        "List of traffic statistics for segment lists.";
      list list-traffic-statistic {
        key "segment-list-id";
        description
          "Traffic statistics for a segment list.";
        leaf segment-list-id {
          type uint32 {
            range "1..4294967295";
          }
          description
            "Segment list ID.";
        }
        leaf xc-index {
          type uint32;
          description
            "XC index.";
        }
        leaf policy-name {
          type string {
            length "1..31";
          }
          ext:support-filter "true";
          description
            "Policy name.";
        }
        leaf endpoint {
          type inet:ip-address-no-zone;
          ext:support-filter "true";
          description
            "Destination address of an SR Policy.";
        }
        leaf color {
          type uint32 {
            range "0..4294967295";
          }
          ext:support-filter "true";
          description
            "Color of an SR Policy.";
        }
        leaf binding-sid {
          type ncs_rpc_notif_sid-value-type;
          ext:support-filter "true";
          description
            "Binding SID of an SR Policy.";
        }
        leaf tunnel-id {
          type uint32;
          description
            "Tunnel ID of an SR Policy.";
        }
        leaf preference {
          type uint32 {
            range "0..4294967295";
          }
          description
            "Preference of a candidate path.";
        }
        leaf protocol-origin {
          type ncs_rpc_notif_protocol-origin-type;
          description
            "Protocol origin of a candidate path.";
        }
        leaf asn {
          type uint32;
          description
            "AS number.";
        }
        leaf node-address {
          type inet:ipv4-address-no-zone;
          description
            "Node address.";
        }
        leaf discriminator {
          type uint32 {
            range "0..4294967295";
          }
          description
            "Discriminator of a candidate path.";
        }
        leaf path-type {
          type ncs_rpc_notif_path-type;
          description
            "Type of a candidate path.";
        }
        container sids {
          description
            "List of SIDs.";
          list sid {
            key "index";
            max-elements 10;
            description
              "Operational data of SID.";
            leaf index {
              type uint32 {
                range "0..4294967295";
              }
              description
                "SID index.";
            }
            leaf value {
              type ncs_rpc_notif_sid-value-type;
              description
                "SID value.";
            }
          }
        }
        leaf flow-period {
          type uint32 {
            range "0..4294967295";
          }
          units "s";
          description
            "Traffic statistics collection period.";
        }
        leaf last-period-byte-rate {
          type uint64 {
            range "0..18446744073709551615";
          }
          units "Byte/s";
          description
            "Byte rate in the latest period.";
        }
        leaf last-period-pkt-rate {
          type uint64 {
            range "0..18446744073709551615";
          }
          units "pps";
          description
            "Packet rate in the latest period.";
        }
        leaf display-interval {
          type uint64 {
            range "0..18446744073709551615";
          }
          units "s";
          description
            "Interval between two queries.";
        }
        leaf interval-byte-rate {
          type uint64 {
            range "0..18446744073709551615";
          }
          units "Byte/s";
          description
            "Byte rate between two queries.";
        }
        leaf interval-pkt-rate {
          type uint64 {
            range "0..18446744073709551615";
          }
          units "pps";
          description
            "Packet rate between two queries.";
        }
        leaf total-byte {
          type uint64 {
            range "0..18446744073709551615";
          }
          units "Byte";
          description
            "Total number of transmitted bytes.";
        }
        leaf total-packet {
          type uint64 {
            range "0..18446744073709551615";
          }
          units "packet";
          description
            "Total number of transmitted packets.";
        }
        leaf no-resource-flag {
          type boolean;
          default "false";
          description
            "Flag indicating that no statistical resource exists.";
        }
      }
    }
  }

  grouping ncs_rpc_notif_srv6-policy-infos {
    description
      "SRv6 Policy infos grouping.";
    container policy-infos {
      config false;
      description
        "List of SRv6 TE Policies.";
      list policy-info {
        key "endpoint color";
        description
          "Operational state of an SRv6 TE Policy.";
        leaf endpoint {
          type inet:ipv6-address-no-zone;
          description
            "SR Policy endpoint address.";
        }
        leaf color {
          type uint32 {
            range "0..4294967295";
          }
          description
            "SR Policy color.";
        }
        leaf name {
          type string {
            length "1..31";
          }
          description
            "SR Policy name.";
          ext:support-filter "true";
        }
        leaf state {
          type string {
            length "1..31";
          }
          description
            "SR Policy states.";
        }
        leaf state-change-time {
          type yang:date-and-time;
          description
            "SR Policy state change time.";
        }
        leaf admin-state {
          type ncs_rpc_notif_admin-state-type;
          description
            "SR Policy admin states.";
        }
        leaf binding-sid {
          type inet:ipv6-address-no-zone;
          description
            "SR Policy binding SID.";
          ext:support-filter "true";
        }
        leaf tunnel-id {
          type uint32;
          description
            "SR Policy tunnel ID.";
        }
        leaf tunnel-type {
          type ncs_rpc_notif_tunnel-type;
          description
            "SR Policy tunnel type.";
        }
        leaf bfd-enable {
          type ncs_rpc_notif_bfd-enable-type;
          description
            "SR Policy BFD enable flag.";
        }
        leaf bfd-bypass {
          type ncs_rpc_notif_bfd-bypass-type;
          description
            "SR policy BFD bypass enable flag.";
        }
        leaf hsb-enable {
          type ncs_rpc_notif_enable-type;
          description
            "SR Policy HSB enable flag.";
        }
        leaf traffic-statistics-enable {
          type ncs_rpc_notif_enable-type;
          description
            "SR Policy traffic statistics enable flag.";
        }
        leaf candidate-path-count {
          type uint32;
          description
            "SR Policy candidate path count.";
        }
        container candidate-paths {
          description
            "List of candidate paths in an SRv6 TE Policy.";
          list candidate-path {
            key "protocol-origin asn node-address discriminator preference";
            max-elements 64;
            description
              "Operational state of a candidate path in an SRv6 TE Policy.";
            leaf protocol-origin {
              type ncs_rpc_notif_protocol-origin-type;
              description
                "Candidate path protocol origin.";
            }
            leaf asn {
              type uint32 {
                range "0..4294967295";
              }
              description
                "Candidate path AS No.";
            }
            leaf node-address {
              type inet:ip-address-no-zone;
              description
                "Candidate path nodeAddress.";
            }
            leaf discriminator {
              type uint32 {
                range "1..65535";
              }
              description
                "Candidate path discriminator.";
            }
            leaf preference {
              type uint32 {
                range "1..65535";
              }
              description
                "Candidate path preference.";
            }
            leaf network-slice-id {
              type uint32 {
                range "1..4294967295";
              }
              description
                "Network slice ID of candidate path.";
            }
            leaf path-state {
              type string {
                length "1..31";
              }
              description
                "Candidate path state.";
            }
            leaf path-type {
              type ncs_rpc_notif_path-type;
              description
                "Candidate path type.";
            }
            leaf binding-sid {
              type inet:ipv6-address-no-zone;
              description
                "Candidate path binding SID.";
            }
            leaf group-id {
              type uint32;
              description
                "Candidate path groupId.";
            }
            leaf policy-name {
              type string {
                length "1..31";
              }
              description
                "Candidate path policy name.";
            }
            leaf path-verification {
              type ncs_rpc_notif_enable-type;
              description
                "SR Policy path verification enable flag.";
            }
            leaf delay-timer-remain {
              type uint32;
              units "ms";
              description
                "Delay Timer Remain.";
            }
            leaf template-id {
              type uint32;
              description
                "Candidate path template ID.";
            }
            leaf segment-list-count {
              type uint32;
              description
                "Candidate path segment list count.";
            }
            container segment-lists {
              description
                "List of segment list information in a candidate path.";
              list segment-list {
                key "id";
                max-elements 64;
                description
                  "Operational state of a segment list in a candidate path.";
                leaf id {
                  type uint32;
                  description
                    "Segment list ID.";
                }
                leaf name {
                  type string {
                    length "1..31";
                  }
                  description
                    "Segment list name.";
                }
                leaf xc-index {
                  type uint32;
                  description
                    "XC index.";
                }
                leaf network-slice-id {
                  type uint32 {
                    range "1..4294967295";
                  }
                  description
                    "Network slice ID of segment list.";
                }
                leaf delay-timer-remain {
                  type uint32;
                  units "ms";
                  description
                    "Delay timer remain.";
                }
                leaf state {
                  type string {
                    length "1..31";
                  }
                  description
                    "Segment list state.";
                }
                leaf weight {
                  type uint32 {
                    range "0..4294967295";
                    ext:value-meaning {
                      ext:item "0" {
                        ext:meaning "Invalid";
                        description
                          "The segment list is invalid when weight is 0.";
                      }
                    }
                  }
                  description
                    "Segment-list weighted loadshare.";
                }
                leaf verification-state {
                  type string {
                    length "1..31";
                  }
                  description
                    "Segment list state afer enable path verification.";
                }
                leaf suppress-time-remain {
                  type uint32;
                  description
                    "The delay up time of segment list afer enable path verification.";
                }
                leaf path-mtu {
                  type uint32 {
                    range "1280..9600";
                  }
                  description
                    "Segment-list path mtu.";
                }
                leaf active-path-mtu {
                  type uint32 {
                    range "1280..9600";
                  }
                  description
                    "Segment-list active path mtu.";
                }
                leaf bfd-state {
                  type string {
                    length "1..31";
                  }
                  description
                    "Segment list BFD state.";
                }
                container sids {
                  description
                    "List of SIDs.";
                  list sid {
                    key "index";
                    max-elements 10;
                    description
                      "Operational data of SID.";
                    leaf index {
                      type uint32 {
                        range "0..4294967295";
                      }
                      description
                        "Id.";
                    }
                    leaf value {
                      type inet:ipv6-address-no-zone;
                      description
                        "Val.";
                    }
                    leaf block-length {
                      type uint32 {
                        range "16..80";
                      }
                      description
                        "Block length.";
                    }
                    leaf compress-length {
                      type uint32 {
                        range "32";
                      }
                      description
                        "Compress SID length.";
                    }
                  }
                }
              }
            }
          }
        }
      }
    }
  }

  grouping ncs_rpc_notif_srv4-policy-infos {
    description
      "SR-MPLS TE Policy infos grouping.";
    container policy-infos {
      config false;
      description
        "List of SR-MPLS TE Policies.";
      list policy-info {
        key "endpoint color";
        description
          "Operational state of an SR-MPLS TE Policy.";
        leaf endpoint {
          type inet:ipv4-address-no-zone;
          description
            "SR Policy endpoint address.";
        }
        leaf color {
          type uint32 {
            range "1..4294967295";
          }
          description
            "SR Policy color.";
        }
        leaf name {
          type string {
            length "1..31";
          }
          description
            "SR Policy name.";
          ext:support-filter "true";
        }
        leaf state {
          type string {
            length "1..31";
          }
          description
            "SR Policy state.";
        }
        leaf admin-state {
          type ncs_rpc_notif_admin-state-type;
          description
            "SR Policy admin state.";
        }
        leaf binding-sid {
          type uint32;
          description
            "SR Policy binding SID.";
          ext:support-filter "true";
        }
        leaf mtu {
          type uint32 {
            range "512..9600";
          }
          description
            "SR Policy mtu value.";
        }
        leaf tunnel-id {
          type uint32;
          description
            "SR Policy tunnel ID.";
        }
        leaf tunnel-type {
          type ncs_rpc_notif_tunnel-type;
          description
            "SR Policy tunnel type.";
        }
        leaf pipe-mode {
          type ncs_rpc_notif_pipe-mode-type;
          description
            "Pipe mode of SR Policy.";
        }
        leaf service-class {
          type ncs_rpc_notif_serv-class-disp-types;
          description
            "Service class of SR Policy.";
        }
        leaf service-color {
          type ncs_rpc_notif_serv-color-disp-types;
          description
            "Service color of SR Policy.";
        }
        leaf bfd-enable {
          type ncs_rpc_notif_bfd-enable-type;
          description
            "SR Policy BFD enable flag.";
        }
        leaf hsb-enable {
          type ncs_rpc_notif_enable-type;
          description
            "SR Policy HSB enable flag.";
        }
        leaf traffic-statistics-enable {
          type ncs_rpc_notif_enable-type;
          description
            "SR Policy traffic statistics enable flag.";
        }
        leaf state-change-time {
          type yang:date-and-time;
          description
            "SR Policy state change time.";
        }
        leaf candidate-path-count {
          type uint32;
          description
            "SR Policy candidate path count.";
        }
        container candidate-paths {
          description
            "List of candidate paths in an SR-MPLS TE Policy.";
          list candidate-path {
            key "protocol-origin asn node-address discriminator preference";
            max-elements 64;
            description
              "Operational state of a candidate path in an SR-MPLS TE Policy.";
            leaf protocol-origin {
              type ncs_rpc_notif_protocol-origin-type;
              description
                "Candidate path protocol origin.";
            }
            leaf asn {
              type uint32 {
                range "0..4294967295";
              }
              description
                "Candidate path AS No.";
            }
            leaf node-address {
              type inet:ipv4-address-no-zone;
              description
                "Candidate path nodeAddress.";
            }
            leaf discriminator {
              type uint32 {
                range "1..65535";
              }
              description
                "Candidate path discriminator.";
            }
            leaf preference {
              type uint32 {
                range "1..65535";
              }
              description
                "Candidate path preference.";
            }
            leaf path-state {
              type string {
                length "1..31";
              }
              description
                "Candidate path state.";
            }
            leaf path-type {
              type ncs_rpc_notif_path-type;
              description
                "Candidate path type.";
            }
            leaf binding-sid {
              type uint32;
              description
                "Candidate path binding SID.";
            }
            leaf group-id {
              type uint32;
              description
                "Candidate path groupId.";
            }
            leaf policy-name {
              type string {
                length "1..31";
              }
              description
                "Candidate path policy name.";
            }
            leaf template-id {
              type uint32;
              description
                "Candidate path template Id.";
            }
            leaf segment-list-count {
              type uint32;
              description
                "Candidate path segment list count.";
            }
            container segment-lists {
              description
                "List of segment list information in a candidate path.";
              list segment-list {
                key "id";
                max-elements 64;
                description
                  "Operational state of a segment list in a candidate path.";
                leaf id {
                  type uint32;
                  description
                    "Segment list ID.";
                }
                leaf name {
                  type string {
                    length "1..31";
                  }
                  description
                    "Segment list name.";
                }
                leaf xc-index {
                  type uint32;
                  description
                    "XC index.";
                }
                leaf delay-time-remain {
                  type uint32;
                  units "ms";
                  description
                    "Delay delete timer remain.";
                }
                leaf state {
                  type string {
                    length "1..31";
                  }
                  description
                    "Segment list state.";
                }
                leaf weight {
                  type uint32 {
                    range "0..4294967295";
                    ext:value-meaning {
                      ext:item "0" {
                        ext:meaning "Invalid";
                        description
                          "The segment list is invalid when weight is 0.";
                      }
                    }
                  }
                  description
                    "Segment-list weighted loadshare.";
                }
                leaf bfd-state {
                  type string {
                    length "1..31";
                  }
                  description
                    "Segment list BFD state.";
                }
                leaf exp-value {
                  type uint32;
                  description
                    "EXP value.";
                }
                leaf ttl-value {
                  type uint32;
                  description
                    "TTL value.";
                }
                container sids {
                  description
                    "List of SIDs.";
                  list sid {
                    key "index";
                    max-elements 10;
                    description
                      "Operational data of SID.";
                    leaf index {
                      type uint32 {
                        range "0..4294967295";
                      }
                      description
                        "Index.";
                    }
                    leaf value {
                      type uint32 {
                        range "16..1048575";
                      }
                      description
                        "Value.";
                    }
                  }
                }
              }
            }
          }
        }
      }
    }
  }

  grouping ncs_rpc_notif_sr-template-infos {
    description
      "SR Policy template infos.";
    container template-infos {
      config false;
      description
        "List of SR Policy template information.";
      list template-info {
        key "template-id";
        description
          "Operational state of SR Policy template.";
        leaf template-id {
          type uint32 {
            range "1..4294967295";
          }
          description
            "The template ID.";
        }
        leaf bfd-enable {
          type ncs_rpc_notif_template-enable-type;
          description
            "Enable/disable Seamless-BFD.";
        }
        leaf hsb-enable {
          type ncs_rpc_notif_template-enable-type;
          description
            "Enable/disable hot standby.";
        }
        leaf traffic-statistics-enable {
          type ncs_rpc_notif_template-enable-type;
          description
            "Enable/disable traffic statistics.";
        }
      }
    }
  }

  grouping ncs_rpc_notif_srv6-source-sids {
    description
      "SRv6 TE Policy SID informations.";
    container source-sids {
      config false;
      description
        "List of SRv6 TE Policy SID informations.";
      list source-sid {
        key "sid-value topology";
        description
          "Operational state of SRv6 TE Policy SID information.";
        leaf sid-value {
          type inet:ipv6-address-no-zone;
          description
            "The SRv6 TE Policy SID value.";
        }
        leaf topology {
          type uint32 {
            range "0..2";
          }
          description
            "The SRv6 TE Policy SID topology.";
        }
        leaf func-type {
          type ncs_rpc_notif_function-type;
          ext:support-filter "true";
          description
            "The SRv6 TE Policy SID type.";
        }
        leaf overload {
          type boolean;
          description
            "The SRv6 TE Policy SID overload flag.";
        }
        container sources {
          description
            "List of SRv6 TE Policy SID source informations.";
          list source {
            key "protocol process sub-process";
            description
              "Operational state of SRv6 TE Policy SID source information.";
            leaf protocol {
              type ncs_rpc_notif_protocol-type;
              description
                "The origin protocol.";
            }
            leaf process {
              type uint32 {
                range "1..4294967295";
              }
              description
                "The origin protocol process.";
            }
            leaf sub-process {
              type ncs_rpc_notif_sub-process-type;
              description
                "The origin protocol sub process.";
            }
            leaf node {
              type string {
                length "1..48";
              }
              description
                "Node information.";
            }
            leaf local {
              type string {
                length "1..48";
              }
              description
                "Local information.";
            }
            leaf peer {
              type string {
                length "1..48";
              }
              description
                "Peer information.";
            }
          }
        }
      }
    }
  }

  grouping ncs_rpc_notif_srv6-sid-statistics {
    description
      "SRv6 Policy SID statistics infos.";
    container sid-statistics {
      config false;
      description
        "Operational state of SRv6 Policy SID statistics infos.";
      leaf endx-total-num {
        type uint32 {
          range "0..4294967295";
        }
        description
          "SRv6 Policy End.X SID statistics.";
      }
      leaf end-total-num {
        type uint32 {
          range "0..4294967295";
        }
        description
          "SRv6 Policy End SID statistics.";
      }
      container sid-nums {
        description
          "List of SRv6 Policy SID num.";
        list sid-num {
          key "protocol process sub-process";
          description
            "Operational state of SRv6 Policy SID num.";
          leaf protocol {
            type ncs_rpc_notif_protocol-type;
            description
              "The origin protocol.";
          }
          leaf process {
            type uint32 {
              range "1..4294967295";
            }
            description
              "The origin protocol process.";
          }
          leaf sub-process {
            type ncs_rpc_notif_sub-process-type;
            description
              "The origin protocol sub process.";
          }
          leaf endx-num {
            type uint32 {
              range "0..4294967295";
            }
            description
              "The End.X SID num.";
          }
          leaf end-num {
            type uint32 {
              range "0..4294967295";
            }
            description
              "The End SID num.";
          }
        }
      }
    }
  }

  grouping ncs_rpc_notif_reset-traffic-statistics {
    description
      "Reset SR Policy traffic statistics.";
    leaf name {
      type string {
        length "1..31";
      }
      description
        "SR Policy name.";
    }
    leaf endpoint {
      type inet:ip-address;
      description
        "SR Policy endpoint address.";
    }
    leaf color {
      type uint32 {
        range "0..4294967295";
      }
      description
        "SR Policy color.";
    }
    leaf binding-sid {
      type ncs_rpc_notif_sid-value-type;
      description
        "SR Policy binding sid.";
    }
  }

  grouping ncs_rpc_notif_policy-maps {
    description
      "SR Policy mappings.";
    container sr-policy-maps {
      description
        "List of SR Policy mappings.";
      list sr-policy-map {
        must "(../../srv6:type='sr-policy-dscp')" {
          tailf:xpath-root 3;
        }
        key "color af-type flow-priority-type";
        max-elements 128;
        description
          "Configure an SR Policy mapping.";
        leaf color {
          type uint32 {
            range "0..4294967295";
          }
          description
            "Color of an SR Policy.";
        }
        leaf af-type {
          type ncs_rpc_notif_address-family-type;
          description
            "Address family type.";
        }
        leaf flow-priority-type {
          type ncs_rpc_notif_flow-priority-type;
          description
            "Traffic priority type.";
        }
        leaf dscp-value {
          when "../flow-priority-type='dscp'" {
            tailf:xpath-root 3;
          }
          type ncs_rpc_notif_dscp-type;
          mandatory true;
          description
            "DSCP list.";
        }
      }
    }
  }

  grouping ncs_rpc_notif_dynamic-policy-group {
    description
      "Dynamic SR Policy groups.";
    container dynamic-sr-policy-groups {
      config false;
      description
        "List of dynamic SR Policy groups.";
      list dynamic-sr-policy-group {
        key "endpoint color";
        description
          "Operational state of a dynamic SR Policy group.";
        leaf endpoint {
          type inet:ip-address;
          description
            "Endpoint of a dynamic SR Policy group.";
        }
        leaf color {
          type uint32;
          description
            "Color of a dynamic SR Policy group.";
        }
        leaf tunnel-id {
          type uint32;
          description
            "Tunnel ID.";
        }
        leaf tunnel-type {
          type ncs_rpc_notif_tunnel-type;
          description
            "Tunnel type.";
        }
        leaf state {
          type ncs_rpc_notif_group-state-type;
          description
            "State of a dynamic SR Policy group.";
        }
        leaf state-change-time {
          type yang:date-and-time;
          description
            "Date and time when the state of a dynamic SR Policy group changed.";
        }
        leaf delay-timer-remain {
          type uint32;
          units "ms";
          description
            "Remaining time of the delay timer.";
        }
        leaf map-count {
          type uint32;
          description
            "Number of mappings in a dynamic SR Policy group.";
        }
        leaf up-map-count {
          type uint32;
          description
            "Number of mappings that are up in a dynamic SR Policy group.";
        }
        container maps {
          description
            "List of mappings in a dynamic SR Policy group.";
          list map {
            key "color af-type flow-priority-type";
            max-elements 128;
            description
              "Operational state of a mapping in a dynamic SR Policy group.";
            leaf color {
              type uint32;
              description
                "Color of an SR Policy.";
            }
            leaf af-type {
              type ncs_rpc_notif_address-family-type;
              description
                "Address family type.";
            }
            leaf flow-priority-type {
              type ncs_rpc_notif_flow-priority-type;
              description
                "Traffic priority type.";
            }
            leaf flow-priority-list {
              type string {
                length "1..64";
              }
              description
                "Priority list.";
            }
            leaf policy-tunnel-id {
              type uint32;
              description
                "Tunnel ID of an SR Policy.";
            }
            leaf policy-tunnel-type {
              type ncs_rpc_notif_tunnel-type;
              description
                "Tunnel type of an SR Policy.";
            }
          }
        }
      }
    }
  }

  grouping ncs_rpc_notif_dynamic-policy-group-down-reason {
    description
      "Dynamic SR Policy group down reason.";
    container dynamic-policy-group-down-reasons {
      config false;
      description
        "List of down records of dynamic SR Policy groups.";
      list dynamic-policy-group-down-reason {
        key "endpoint color up-time up-millisecond";
        description
          "Operational state of down record of a dynamic SR Policy group.";
        leaf endpoint {
          type inet:ip-address;
          description
            "Endpoint of an SR Policy group.";
        }
        leaf color {
          type uint32 {
            range "0..4294967295";
          }
          description
            "Color of an SR Policy group.";
        }
        leaf up-time {
          type yang:date-and-time;
          description
            "Date and time when a dynamic SR Policy group went up.";
        }
        leaf up-millisecond {
          type uint32 {
            range "0..1000";
          }
          description
            "Millisecond value of the time when a dynamic SR Policy group went up.";
        }
        leaf tunnel-id {
          type uint32;
          description
            "Tunnel ID.";
        }
        leaf tunnel-type {
          type ncs_rpc_notif_tunnel-type;
          description
            "Tunnel type.";
        }
        leaf create-time {
          type yang:date-and-time;
          description
            "Date and time when a dynamic SR Policy group was created.";
        }
        leaf down-time {
          type yang:date-and-time;
          description
            "Date and time when a dynamic SR Policy group went down.";
        }
        leaf down-reason {
          type ncs_rpc_notif_group-down-reason-type;
          description
            "Reason why a dynamic SR Policy group went down.";
        }
        container map-down-reasons {
          description
            "List of reason why mappings went down.";
          list map-down-reason {
            key "sr-policy-color af-type up-time up-millisecond";
            max-elements 64;
            description
              "Operational state of reason why a mapping went down.";
            leaf sr-policy-color {
              type uint32 {
                range "0..4294967295";
              }
              description
                "Color of an SR Policy.";
            }
            leaf af-type {
              type ncs_rpc_notif_address-family-type;
              description
                "Address family type.";
            }
            leaf up-time {
              type yang:date-and-time;
              description
                "Date and time when a mapping went up.";
            }
            leaf up-millisecond {
              type uint32 {
                range "0..1000";
              }
              description
                "Millisecond value of the time when a mapping went up.";
            }
            leaf down-time {
              type yang:date-and-time;
              description
                "Date and time when a mapping went down.";
            }
            leaf down-reason {
              type ncs_rpc_notif_map-down-reason-type;
              description
                "Reason why a mapping went down.";
            }
          }
        }
      }
    }
  }

  grouping ncs_rpc_notif_policy-group-statistics {
    description
      "SR Policy group statistics.";
    container policy-group-statistic {
      config false;
      description
        "Statistics of SR Policy groups.";
      leaf mapping-policy {
        type uint32 {
          range "0..4294967295";
        }
        description
          "Number of mapping policies.";
      }
      leaf sr-policy-group {
        type uint32 {
          range "0..4294967295";
        }
        description
          "Number of SR Policy groups.";
      }
      leaf sr-policy-group-up {
        type uint32 {
          range "0..4294967295";
        }
        description
          "Number of SR Policy groups that are up.";
      }
      leaf dscp-map {
        type uint32 {
          range "0..4294967295";
        }
        description
          "Number of DSCP mappings.";
      }
      leaf dscp-map-up {
        type uint32 {
          range "0..4294967295";
        }
        description
          "Number of DSCP mappings that are up.";
      }
    }
  }

  grouping live_ncs_bfd {
    description
      "SR Policy BFD configuration.";
    container bfd {
      description
        "Configure SR Policy BFD.";
      leaf enable {
        type live_ncs_bfd-enable-type;
        // NCS drop default statement
        description
          "Enable seamless-bfd for all SR Policies.";
      }
      leaf bypass {
        type live_ncs_bfd-bypass-type;
        // NCS drop default statement
        description
          "Enable BFD bypass for all SR policies.";
      }
      leaf min-tx {
        type uint32 {
          range "1..4294967295";
        }
        units "ms";
        // NCS drop default statement
        description
          "Minimum interval for sending seamless-bfd packets to the peer end. The range and default are based on PAF.";
      }
      leaf min-rx {
        type uint32 {
          range "1..4294967295";
        }
        units "ms";
        // NCS drop default statement
        description
          "Minimum interval for receiving seamless-bfd packets from the peer end. The range and default are based on PAF.";
      }
      leaf multi-num {
        type uint32 {
          range "3..50";
        }
        // NCS drop default statement
        description
          "Local detection multiplier.";
      }
      leaf backup-min-tx {
        type uint32 {
          range "1..4294967295";
        }
        units "ms";
        description
          "Minimum interval for sending seamless-bfd packets to the peer end over the backup candidate path. The range and default are based on PAF.";
      }
      leaf backup-multi-num {
        type uint32 {
          range "3..50";
        }
        description
          "Local detection multiplier over the backup candidate path.";
      }
    }
  }

  grouping live_ncs_global-attributes {
    description
      "SR Policy global configuration.";
    leaf switch-delay {
      type uint32 {
        range "0..600000";
      }
      units "ms";
      // NCS drop default statement
      description
        "MBB switch delay time.";
    }
    leaf delete-delay {
      type uint32 {
        range "0..600000";
      }
      units "ms";
      // NCS drop default statement
      description
        "MBB delete delay time.";
    }
    leaf hsb-enable {
      type boolean;
      // NCS drop default statement
      description
        "Enable/disable hot standby.";
    }
    leaf traffic-statistics-enable {
      type boolean;
      // NCS drop default statement
      description
        "Enable/disable traffic statistics collection.";
    }
    leaf bgp-ls-enable {
      type boolean;
      // NCS drop default statement
      description
        "Enable/disable BGP-LS.";
    }
    leaf path-verification {
      type boolean;
      // NCS drop default statement
      description
        "Enable/disable path verification.";
    }
    leaf suppress-flapping {
      type boolean;
      // NCS drop default statement
      description
        "Enable/disable suppress flapping.";
    }
    leaf policy-threshold-upper {
      type uint32 {
        range "2..100";
      }
      // NCS drop must statement
      // NCS drop default statement
      description
        "SR Policy threshold upper limit.";
    }
    leaf policy-threshold-lower {
      type uint32 {
        range "1..99";
      }
      // NCS drop default statement
      description
        "SR Policy threshold lower limit.";
    }
    leaf list-threshold-upper {
      type uint32 {
        range "2..100";
      }
      // NCS drop must statement
      // NCS drop default statement
      description
        "Segment List threshold upper limit.";
    }
    leaf list-threshold-lower {
      type uint32 {
        range "1..99";
      }
      // NCS drop default statement
      description
        "Segment List threshold lower limit.";
    }
    leaf group-threshold-upper {
      type uint32 {
        range "2..100";
      }
      // NCS drop must statement
      // NCS drop default statement
      description
        "Upper threshold for the number of SR Policy groups.";
    }
    leaf group-threshold-lower {
      type uint32 {
        range "1..99";
      }
      // NCS drop default statement
      description
        "Lower threshold for the number of SR Policy groups.";
    }
    uses live_ncs_bfd;
  }

  grouping live_ncs_srv4-segment-lists {
    description
      "Global segment lists.";
    container segment-lists {
      description
        "List of global segment lists.";
      list segment-list {
        key "name";
        description
          "Configure a global segment list.";
        leaf name {
          type string {
            length "1..31";
            pattern '[^ \?]*';
          }
          description
            "Global segment list name.";
        }
        container segments {
          description
            "List of segments in a global segment list.";
          list segment {
            key "index";
            // NCS drop max-elements statement
            description
              "Configure a segment in a global segment list.";
            leaf index {
              type uint32 {
                range "0..4294967295";
              }
              description
                "The segment index.";
            }
            choice type {
              // NCS drop mandatory statement
              description
                "The segment type.";
              case segment-type-1 {
                description
                  "The segment is declared by MPLS label.";
                leaf sid-value-1 {
                  type uint32 {
                    range "16..1048575";
                  }
                  description
                    "MPLS label value.";
                }
              }
            }
          }
        }
      }
    }
  }

  grouping live_ncs_srv6-segment-lists {
    description
      "Global segment lists.";
    container segment-lists {
      description
        "List of global segment lists.";
      list segment-list {
        key "name";
        description
          "Configure a global segment list.";
        leaf name {
          type string {
            length "1..31";
            pattern '[^ \?]*';
          }
          description
            "Global segment list name.";
        }
        container segments {
          description
            "List of segments in a global segment list.";
          list segment {
            key "index";
            // NCS drop max-elements statement
            description
              "Configure a segment in a global segment list.";
            leaf index {
              type uint32 {
                range "0..4294967295";
              }
              description
                "The segment index.";
            }
            choice type {
              // NCS drop mandatory statement
              description
                "The segment type.";
              case segment-type-2 {
                description
                  "The segment is declared by SRv6 SID value.";
                leaf sid-value-2 {
                  type inet:ipv6-address-no-zone;
                  // NCS drop mandatory statement
                  description
                    "SRv6 sid value.";
                }
                leaf block-length {
                  type uint32 {
                    range "16..80";
                  }
                  // NCS drop must statement
                  description
                    "SRv6 SID block length.";
                }
              }
            }
          }
        }
      }
    }
  }

  grouping live_ncs_srv6-policy-attributes {
    description
      "Grouping containing attributes applicable to all SR policies.";
    container policy-attributes {
      description
        "Configure attributes for all SR policies.";
      uses live_ncs_global-attributes;
      leaf locator {
        ext:operation-exclude "update";
        type leafref {
          path "/ncs:devices/ncs:device/ncs:live-status/ni:network-instance/ni:instances/ni:instance/srv6:srv6/srv6:locators/srv6:locator/srv6:name" {
            tailf:xpath-root 3;
          }
        }
        description
          "Locator Name.";
      }
      uses live_ncs_srv6-segment-lists;
    }
  }

  grouping live_ncs_srv4-policy-attributes {
    description
      "Grouping containing attributes applicable to all SR policies.";
    container policy-attributes {
      description
        "Configure attributes for all SR policies.";
      uses live_ncs_global-attributes;
      uses live_ncs_srv4-segment-lists;
    }
  }

  grouping live_ncs_candidate-paths {
    description
      "Grouping containing candidate paths to all SR policies.";
    container candidate-paths {
      description
        "List of candidate paths in an SR Policy.";
      list candidate-path {
        // NCS drop must statement
        key "protocol-origin originator discriminator";
        // NCS drop max-elements statement
        description
          "Configure a candidate path.";
        leaf protocol-origin {
          type live_ncs_protocol-origin-type;
          // NCS drop must statement
          description
            "Candidate path protocol origin.";
        }
        leaf originator {
          type string {
            length "1..60";
          }
          // NCS drop must statement
          description
            "Candidate path originator.";
        }
        leaf discriminator {
          type uint32 {
            range "1..65535";
          }
          description
            "Candidate path discriminator.";
        }
        leaf preference {
          type uint32 {
            range "1..65535";
          }
          // NCS drop mandatory statement
          description
            "Candidate path preference.";
        }
        choice type {
          description
            "Type of candidate paths.";
          case explicit {
            description
              "Candidate path with explicitly defined set/s of segment-lists.";
            container segment-lists {
              description
                "List of segment lists in a candidate path.";
              list segment-list {
                key "name";
                // NCS drop max-elements statement
                description
                  "Configure a segment list for a candidate path.";
                leaf name {
                  type leafref {
                    path "../../../../../../../policy-attributes/segment-lists/segment-list/name";
                  }
                  description
                    "Segment list name.";
                }
                leaf weight {
                  type uint32 {
                    range "0..4294967295";
                    ext:value-meaning {
                      ext:item "0" {
                        ext:meaning "Invalid";
                        description
                          "The segment list is invalid when weight is 0.";
                      }
                    }
                  }
                  // NCS drop default statement
                  description
                    "Segment-list weighted loadshare.";
                }
                leaf path-mtu {
                  type uint32 {
                    range "1280..9600";
                  }
                  description
                    "Segment-list path-mtu.";
                }
              }
            }
          }
        }
        leaf template-id {
          type leafref {
            path "/ncs:devices/ncs:device/ncs:live-status/srpolicy:srpolicy/srpolicy:attribute-templates/srpolicy:attribute-template/srpolicy:id" {
              tailf:xpath-root 3;
            }
          }
          description
            "Attribute template ID.";
        }
        leaf network-slice-id {
          type uint32 {
            range "1..4294967295";
          }
          description
            "Network slice ID of candidate path.";
        }
      }
    }
  }

  grouping live_ncs_srv4-policys {
    description
      "SR policy grouping.";
    container policys {
      description
        "List of SR Policies.";
      list policy {
        key "endpoint color";
        unique "name";
        unique "binding-sid/value";
        description
          "Configure an SR Policy.";
        leaf endpoint {
          type inet:ip-address;
          description
            "SR Policy endpoint address.";
        }
        leaf color {
          type uint32 {
            range "0..4294967295";
          }
          description
            "SR Policy color.";
        }
        leaf name {
          type string {
            length "1..31";
            pattern '[^ \?]*';
          }
          // NCS drop mandatory statement
          description
            "SR Policy name.";
        }
        container binding-sid {
          description
            "Configure a binding SID.";
          leaf dataplane {
            type live_ncs_dataplane-type;
            // NCS drop must statement
            description
              "Binding sid dataplane type.";
          }
          leaf value {
            // NCS drop when statement
            type live_ncs_sid-value-type;
            // NCS drop mandatory statement
            description
              "Binding sid value.";
          }
        }
        leaf admin-state {
          type live_ncs_admin-state-type;
          // NCS drop default statement
          description
            "Close the function of SR Policy.";
        }
        leaf mtu {
          type uint32 {
            range "512..9600";
          }
          description
            "SR Policy mtu value.";
        }
        leaf hsb-enable {
          type live_ncs_enable-3types;
          // NCS drop default statement
          description
            "SR Policy hot standby.";
        }
        leaf bfd-enable {
          type live_ncs_policy-bfd-enable-type;
          // NCS drop default statement
          description
            "SR Policy BFD.";
        }
        leaf traffic-statistics-enable {
          type live_ncs_enable-3types;
          // NCS drop default statement
          description
            "SR Policy traffic statistics.";
        }
        container diffserv-mode {
          description
            "Configure the DiffServ mode in an SR Policy.";
          leaf pipe-mode {
            type live_ncs_pipe-mode-type;
            description
              "Specifies the pipe mode of SR Policy.";
          }
          leaf service-class {
            // NCS drop when statement
            type live_ncs_serv-class-types;
            // NCS drop mandatory statement
            description
              "Service class of SR Policy.";
          }
          leaf service-color {
            // NCS drop when statement
            type live_ncs_serv-color-types;
            // NCS drop mandatory statement
            description
              "Service color of SR Policy.";
          }
        }
        uses live_ncs_candidate-paths;
      }
    }
  }

  grouping live_ncs_srv6-policys {
    description
      "SR policy grouping.";
    container policys {
      description
        "List of SR Policies.";
      list policy {
        key "endpoint color";
        unique "name";
        unique "binding-sid/value";
        description
          "Configure an SR Policy.";
        leaf endpoint {
          type inet:ip-address;
          description
            "SR Policy endpoint address.";
        }
        leaf color {
          type uint32 {
            range "0..4294967295";
          }
          description
            "SR Policy color.";
        }
        leaf name {
          type string {
            length "1..31";
            pattern '[^ \?]*';
          }
          // NCS drop mandatory statement
          description
            "SR Policy name.";
        }
        container binding-sid {
          // NCS drop must statement
          description
            "Configure a binding SID.";
          leaf dataplane {
            type live_ncs_dataplane-type;
            // NCS drop must statement
            description
              "Binding sid dataplane type.";
          }
          leaf value {
            // NCS drop when statement
            type live_ncs_sid-value-type;
            // NCS drop mandatory statement
            description
              "Binding sid value.";
          }
        }
        leaf admin-state {
          type live_ncs_admin-state-type;
          // NCS drop default statement
          description
            "Close the function of SR Policy.";
        }
        leaf mtu {
          type uint32 {
            range "512..9600";
          }
          description
            "SR Policy mtu value.";
        }
        leaf hsb-enable {
          type live_ncs_enable-3types;
          // NCS drop default statement
          description
            "SR Policy hot standby.";
        }
        leaf bfd-enable {
          type live_ncs_policy-bfd-enable-type;
          // NCS drop default statement
          description
            "SR Policy BFD.";
        }
        leaf bfd-bypass {
          type live_ncs_policy-bfd-bypass-type;
          // NCS drop default statement
          description
            "SR policy BFD bypass.";
        }
        leaf traffic-statistics-enable {
          type live_ncs_enable-3types;
          // NCS drop default statement
          description
            "SR Policy traffic statistics.";
        }
        leaf path-verification {
          type live_ncs_enable-3types;
          // NCS drop default statement
          description
            "SR Policy path verification.";
        }
        container diffserv-mode {
          description
            "Configure the DiffServ mode in an SR Policy.";
          leaf pipe-mode {
            type live_ncs_pipe-mode-type;
            description
              "Specifies the pipe mode of SR Policy.";
          }
          leaf service-class {
            // NCS drop when statement
            type live_ncs_serv-class-types;
            // NCS drop mandatory statement
            description
              "Service class of SR Policy.";
          }
          leaf service-color {
            // NCS drop when statement
            type live_ncs_serv-color-types;
            // NCS drop mandatory statement
            description
              "Service color of SR Policy.";
          }
        }
        uses live_ncs_candidate-paths;
      }
    }
  }

  grouping live_ncs_policy-groups {
    description
      "SR-MPLS TE Policy group grouping.";
    container policy-groups {
      description
        "List of SR-MPLS TE Policy groups.";
      list policy-group {
        key "index";
        description
          "Configure an SR-MPLS TE Policy group.";
        leaf index {
          type uint32 {
            range "1..4294967295";
          }
          description
            "SR-MPLS TE Policy group id.";
        }
        leaf endpoint {
          type inet:ip-address;
          description
            "SR-MPLS TE Policy IPv4 endPoint address.";
        }
        leaf state {
          type live_ncs_state-type;
          description
            "SR-MPLS TE Policy group state.";
        }
        leaf tunnel-id {
          type uint32;
          description
            "SR-MPLS TE Policy group tunnel id.";
        }
        leaf tunnel-type {
          type live_ncs_tunnel-type;
          description
            "SR-MPLS TE Policy group tunnel type.";
        }
        leaf match-count {
          type uint32;
          description
            "SR-MPLS TE Policy group match count.";
        }
        leaf up-match-count {
          type uint32;
          description
            "SR-MPLS TE Policy group up match count.";
        }
        container color-dscp-matchs {
          description
            "List of color-address family-DSCP mappings for an SR-MPLS TE Policy.";
          list color-dscp-match {
            key "color af-type";
            // NCS drop max-elements statement
            description
              "Configure a color-address family-DSCP mapping for an SR-MPLS TE Policy.";
            leaf color {
              type uint32 {
                range "0..4294967295";
              }
              description
                "SR-MPLS TE Policy color.";
            }
            leaf af-type {
              type live_ncs_address-family-type;
              description
                "Address family.";
            }
            leaf default {
              type boolean;
              // NCS drop default statement
              description
                "Enable/disable the default SR-MPLS TE Policy.";
            }
            leaf dscp-value {
              // NCS drop when statement
              type pub-type:live_ncs_id-range;
              // NCS drop mandatory statement
              description
                "DSCP Value.";
            }
            leaf policy-tunnel-id {
              type uint32;
              description
                "SR-MPLS TE Policy tunnel ID.";
            }
          }
        }
      }
    }
  }

  grouping live_ncs_traffic-statistics {
    description
      "SR Policy traffic statistics grouping.";
    container policy-traffic-statistics {
      description
        "List of traffic statistics for SR Policies.";
      list policy-traffic-statistic {
        key "endpoint color";
        description
          "Traffic statistics for an SR Policy.";
        leaf endpoint {
          type inet:ip-address-no-zone;
          description
            "Destination address of an SR Policy.";
        }
        leaf color {
          type uint32 {
            range "0..4294967295";
          }
          description
            "Color of an SR Policy.";
        }
        leaf name {
          type string {
            length "1..31";
          }
          ext:support-filter "true";
          description
            "Policy name.";
        }
        leaf binding-sid {
          type live_ncs_sid-value-type;
          ext:support-filter "true";
          description
            "Binding SID of an SR Policy.";
        }
        leaf tunnel-id {
          type uint32;
          description
            "Tunnel ID of an SR Policy.";
        }
        leaf flow-period {
          type uint32 {
            range "0..4294967295";
          }
          units "s";
          description
            "Traffic statistics collection period.";
        }
        leaf last-period-byte-rate {
          type uint64 {
            range "0..18446744073709551615";
          }
          units "Byte/s";
          description
            "Byte rate in the latest period.";
        }
        leaf last-period-pkt-rate {
          type uint64 {
            range "0..18446744073709551615";
          }
          units "pps";
          description
            "Packet rate in the latest period.";
        }
        leaf display-interval {
          type uint64 {
            range "0..18446744073709551615";
          }
          units "s";
          description
            "Interval between two queries.";
        }
        leaf interval-byte-rate {
          type uint64 {
            range "0..18446744073709551615";
          }
          units "Byte/s";
          description
            "Byte rate between two queries.";
        }
        leaf interval-pkt-rate {
          type uint64 {
            range "0..18446744073709551615";
          }
          units "pps";
          description
            "Packet rate between two queries.";
        }
        leaf total-byte {
          type uint64 {
            range "0..18446744073709551615";
          }
          units "Byte";
          description
            "Total number of transmitted bytes.";
        }
        leaf total-packet {
          type uint64 {
            range "0..18446744073709551615";
          }
          units "packet";
          description
            "Total number of transmitted packets.";
        }
      }
    }
    container list-traffic-statistics {
      description
        "List of traffic statistics for segment lists.";
      list list-traffic-statistic {
        key "segment-list-id";
        description
          "Traffic statistics for a segment list.";
        leaf segment-list-id {
          type uint32 {
            range "1..4294967295";
          }
          description
            "Segment list ID.";
        }
        leaf xc-index {
          type uint32;
          description
            "XC index.";
        }
        leaf policy-name {
          type string {
            length "1..31";
          }
          ext:support-filter "true";
          description
            "Policy name.";
        }
        leaf endpoint {
          type inet:ip-address-no-zone;
          ext:support-filter "true";
          description
            "Destination address of an SR Policy.";
        }
        leaf color {
          type uint32 {
            range "0..4294967295";
          }
          ext:support-filter "true";
          description
            "Color of an SR Policy.";
        }
        leaf binding-sid {
          type live_ncs_sid-value-type;
          ext:support-filter "true";
          description
            "Binding SID of an SR Policy.";
        }
        leaf tunnel-id {
          type uint32;
          description
            "Tunnel ID of an SR Policy.";
        }
        leaf preference {
          type uint32 {
            range "0..4294967295";
          }
          description
            "Preference of a candidate path.";
        }
        leaf protocol-origin {
          type live_ncs_protocol-origin-type;
          description
            "Protocol origin of a candidate path.";
        }
        leaf asn {
          type uint32;
          description
            "AS number.";
        }
        leaf node-address {
          type inet:ipv4-address-no-zone;
          description
            "Node address.";
        }
        leaf discriminator {
          type uint32 {
            range "0..4294967295";
          }
          description
            "Discriminator of a candidate path.";
        }
        leaf path-type {
          type live_ncs_path-type;
          description
            "Type of a candidate path.";
        }
        container sids {
          description
            "List of SIDs.";
          list sid {
            key "index";
            // NCS drop max-elements statement
            description
              "Operational data of SID.";
            leaf index {
              type uint32 {
                range "0..4294967295";
              }
              description
                "SID index.";
            }
            leaf value {
              type live_ncs_sid-value-type;
              description
                "SID value.";
            }
          }
        }
        leaf flow-period {
          type uint32 {
            range "0..4294967295";
          }
          units "s";
          description
            "Traffic statistics collection period.";
        }
        leaf last-period-byte-rate {
          type uint64 {
            range "0..18446744073709551615";
          }
          units "Byte/s";
          description
            "Byte rate in the latest period.";
        }
        leaf last-period-pkt-rate {
          type uint64 {
            range "0..18446744073709551615";
          }
          units "pps";
          description
            "Packet rate in the latest period.";
        }
        leaf display-interval {
          type uint64 {
            range "0..18446744073709551615";
          }
          units "s";
          description
            "Interval between two queries.";
        }
        leaf interval-byte-rate {
          type uint64 {
            range "0..18446744073709551615";
          }
          units "Byte/s";
          description
            "Byte rate between two queries.";
        }
        leaf interval-pkt-rate {
          type uint64 {
            range "0..18446744073709551615";
          }
          units "pps";
          description
            "Packet rate between two queries.";
        }
        leaf total-byte {
          type uint64 {
            range "0..18446744073709551615";
          }
          units "Byte";
          description
            "Total number of transmitted bytes.";
        }
        leaf total-packet {
          type uint64 {
            range "0..18446744073709551615";
          }
          units "packet";
          description
            "Total number of transmitted packets.";
        }
        leaf no-resource-flag {
          type boolean;
          // NCS drop default statement
          description
            "Flag indicating that no statistical resource exists.";
        }
      }
    }
  }

  grouping live_ncs_srv6-policy-infos {
    description
      "SRv6 Policy infos grouping.";
    container policy-infos {
      description
        "List of SRv6 TE Policies.";
      list policy-info {
        key "endpoint color";
        description
          "Operational state of an SRv6 TE Policy.";
        leaf endpoint {
          type inet:ipv6-address-no-zone;
          description
            "SR Policy endpoint address.";
        }
        leaf color {
          type uint32 {
            range "0..4294967295";
          }
          description
            "SR Policy color.";
        }
        leaf name {
          type string {
            length "1..31";
          }
          description
            "SR Policy name.";
          ext:support-filter "true";
        }
        leaf state {
          type string {
            length "1..31";
          }
          description
            "SR Policy states.";
        }
        leaf state-change-time {
          type yang:date-and-time;
          description
            "SR Policy state change time.";
        }
        leaf admin-state {
          type live_ncs_admin-state-type;
          description
            "SR Policy admin states.";
        }
        leaf binding-sid {
          type inet:ipv6-address-no-zone;
          description
            "SR Policy binding SID.";
          ext:support-filter "true";
        }
        leaf tunnel-id {
          type uint32;
          description
            "SR Policy tunnel ID.";
        }
        leaf tunnel-type {
          type live_ncs_tunnel-type;
          description
            "SR Policy tunnel type.";
        }
        leaf bfd-enable {
          type live_ncs_bfd-enable-type;
          description
            "SR Policy BFD enable flag.";
        }
        leaf bfd-bypass {
          type live_ncs_bfd-bypass-type;
          description
            "SR policy BFD bypass enable flag.";
        }
        leaf hsb-enable {
          type live_ncs_enable-type;
          description
            "SR Policy HSB enable flag.";
        }
        leaf traffic-statistics-enable {
          type live_ncs_enable-type;
          description
            "SR Policy traffic statistics enable flag.";
        }
        leaf candidate-path-count {
          type uint32;
          description
            "SR Policy candidate path count.";
        }
        container candidate-paths {
          description
            "List of candidate paths in an SRv6 TE Policy.";
          list candidate-path {
            key "protocol-origin asn node-address discriminator preference";
            // NCS drop max-elements statement
            description
              "Operational state of a candidate path in an SRv6 TE Policy.";
            leaf protocol-origin {
              type live_ncs_protocol-origin-type;
              description
                "Candidate path protocol origin.";
            }
            leaf asn {
              type uint32 {
                range "0..4294967295";
              }
              description
                "Candidate path AS No.";
            }
            leaf node-address {
              type inet:ip-address-no-zone;
              description
                "Candidate path nodeAddress.";
            }
            leaf discriminator {
              type uint32 {
                range "1..65535";
              }
              description
                "Candidate path discriminator.";
            }
            leaf preference {
              type uint32 {
                range "1..65535";
              }
              description
                "Candidate path preference.";
            }
            leaf network-slice-id {
              type uint32 {
                range "1..4294967295";
              }
              description
                "Network slice ID of candidate path.";
            }
            leaf path-state {
              type string {
                length "1..31";
              }
              description
                "Candidate path state.";
            }
            leaf path-type {
              type live_ncs_path-type;
              description
                "Candidate path type.";
            }
            leaf binding-sid {
              type inet:ipv6-address-no-zone;
              description
                "Candidate path binding SID.";
            }
            leaf group-id {
              type uint32;
              description
                "Candidate path groupId.";
            }
            leaf policy-name {
              type string {
                length "1..31";
              }
              description
                "Candidate path policy name.";
            }
            leaf path-verification {
              type live_ncs_enable-type;
              description
                "SR Policy path verification enable flag.";
            }
            leaf delay-timer-remain {
              type uint32;
              units "ms";
              description
                "Delay Timer Remain.";
            }
            leaf template-id {
              type uint32;
              description
                "Candidate path template ID.";
            }
            leaf segment-list-count {
              type uint32;
              description
                "Candidate path segment list count.";
            }
            container segment-lists {
              description
                "List of segment list information in a candidate path.";
              list segment-list {
                key "id";
                // NCS drop max-elements statement
                description
                  "Operational state of a segment list in a candidate path.";
                leaf id {
                  type uint32;
                  description
                    "Segment list ID.";
                }
                leaf name {
                  type string {
                    length "1..31";
                  }
                  description
                    "Segment list name.";
                }
                leaf xc-index {
                  type uint32;
                  description
                    "XC index.";
                }
                leaf network-slice-id {
                  type uint32 {
                    range "1..4294967295";
                  }
                  description
                    "Network slice ID of segment list.";
                }
                leaf delay-timer-remain {
                  type uint32;
                  units "ms";
                  description
                    "Delay timer remain.";
                }
                leaf state {
                  type string {
                    length "1..31";
                  }
                  description
                    "Segment list state.";
                }
                leaf weight {
                  type uint32 {
                    range "0..4294967295";
                    ext:value-meaning {
                      ext:item "0" {
                        ext:meaning "Invalid";
                        description
                          "The segment list is invalid when weight is 0.";
                      }
                    }
                  }
                  description
                    "Segment-list weighted loadshare.";
                }
                leaf verification-state {
                  type string {
                    length "1..31";
                  }
                  description
                    "Segment list state afer enable path verification.";
                }
                leaf suppress-time-remain {
                  type uint32;
                  description
                    "The delay up time of segment list afer enable path verification.";
                }
                leaf path-mtu {
                  type uint32 {
                    range "1280..9600";
                  }
                  description
                    "Segment-list path mtu.";
                }
                leaf active-path-mtu {
                  type uint32 {
                    range "1280..9600";
                  }
                  description
                    "Segment-list active path mtu.";
                }
                leaf bfd-state {
                  type string {
                    length "1..31";
                  }
                  description
                    "Segment list BFD state.";
                }
                container sids {
                  description
                    "List of SIDs.";
                  list sid {
                    key "index";
                    // NCS drop max-elements statement
                    description
                      "Operational data of SID.";
                    leaf index {
                      type uint32 {
                        range "0..4294967295";
                      }
                      description
                        "Id.";
                    }
                    leaf value {
                      type inet:ipv6-address-no-zone;
                      description
                        "Val.";
                    }
                    leaf block-length {
                      type uint32 {
                        range "16..80";
                      }
                      description
                        "Block length.";
                    }
                    leaf compress-length {
                      type uint32 {
                        range "32";
                      }
                      description
                        "Compress SID length.";
                    }
                  }
                }
              }
            }
          }
        }
      }
    }
  }

  grouping live_ncs_srv4-policy-infos {
    description
      "SR-MPLS TE Policy infos grouping.";
    container policy-infos {
      description
        "List of SR-MPLS TE Policies.";
      list policy-info {
        key "endpoint color";
        description
          "Operational state of an SR-MPLS TE Policy.";
        leaf endpoint {
          type inet:ipv4-address-no-zone;
          description
            "SR Policy endpoint address.";
        }
        leaf color {
          type uint32 {
            range "1..4294967295";
          }
          description
            "SR Policy color.";
        }
        leaf name {
          type string {
            length "1..31";
          }
          description
            "SR Policy name.";
          ext:support-filter "true";
        }
        leaf state {
          type string {
            length "1..31";
          }
          description
            "SR Policy state.";
        }
        leaf admin-state {
          type live_ncs_admin-state-type;
          description
            "SR Policy admin state.";
        }
        leaf binding-sid {
          type uint32;
          description
            "SR Policy binding SID.";
          ext:support-filter "true";
        }
        leaf mtu {
          type uint32 {
            range "512..9600";
          }
          description
            "SR Policy mtu value.";
        }
        leaf tunnel-id {
          type uint32;
          description
            "SR Policy tunnel ID.";
        }
        leaf tunnel-type {
          type live_ncs_tunnel-type;
          description
            "SR Policy tunnel type.";
        }
        leaf pipe-mode {
          type live_ncs_pipe-mode-type;
          description
            "Pipe mode of SR Policy.";
        }
        leaf service-class {
          type live_ncs_serv-class-disp-types;
          description
            "Service class of SR Policy.";
        }
        leaf service-color {
          type live_ncs_serv-color-disp-types;
          description
            "Service color of SR Policy.";
        }
        leaf bfd-enable {
          type live_ncs_bfd-enable-type;
          description
            "SR Policy BFD enable flag.";
        }
        leaf hsb-enable {
          type live_ncs_enable-type;
          description
            "SR Policy HSB enable flag.";
        }
        leaf traffic-statistics-enable {
          type live_ncs_enable-type;
          description
            "SR Policy traffic statistics enable flag.";
        }
        leaf state-change-time {
          type yang:date-and-time;
          description
            "SR Policy state change time.";
        }
        leaf candidate-path-count {
          type uint32;
          description
            "SR Policy candidate path count.";
        }
        container candidate-paths {
          description
            "List of candidate paths in an SR-MPLS TE Policy.";
          list candidate-path {
            key "protocol-origin asn node-address discriminator preference";
            // NCS drop max-elements statement
            description
              "Operational state of a candidate path in an SR-MPLS TE Policy.";
            leaf protocol-origin {
              type live_ncs_protocol-origin-type;
              description
                "Candidate path protocol origin.";
            }
            leaf asn {
              type uint32 {
                range "0..4294967295";
              }
              description
                "Candidate path AS No.";
            }
            leaf node-address {
              type inet:ipv4-address-no-zone;
              description
                "Candidate path nodeAddress.";
            }
            leaf discriminator {
              type uint32 {
                range "1..65535";
              }
              description
                "Candidate path discriminator.";
            }
            leaf preference {
              type uint32 {
                range "1..65535";
              }
              description
                "Candidate path preference.";
            }
            leaf path-state {
              type string {
                length "1..31";
              }
              description
                "Candidate path state.";
            }
            leaf path-type {
              type live_ncs_path-type;
              description
                "Candidate path type.";
            }
            leaf binding-sid {
              type uint32;
              description
                "Candidate path binding SID.";
            }
            leaf group-id {
              type uint32;
              description
                "Candidate path groupId.";
            }
            leaf policy-name {
              type string {
                length "1..31";
              }
              description
                "Candidate path policy name.";
            }
            leaf template-id {
              type uint32;
              description
                "Candidate path template Id.";
            }
            leaf segment-list-count {
              type uint32;
              description
                "Candidate path segment list count.";
            }
            container segment-lists {
              description
                "List of segment list information in a candidate path.";
              list segment-list {
                key "id";
                // NCS drop max-elements statement
                description
                  "Operational state of a segment list in a candidate path.";
                leaf id {
                  type uint32;
                  description
                    "Segment list ID.";
                }
                leaf name {
                  type string {
                    length "1..31";
                  }
                  description
                    "Segment list name.";
                }
                leaf xc-index {
                  type uint32;
                  description
                    "XC index.";
                }
                leaf delay-time-remain {
                  type uint32;
                  units "ms";
                  description
                    "Delay delete timer remain.";
                }
                leaf state {
                  type string {
                    length "1..31";
                  }
                  description
                    "Segment list state.";
                }
                leaf weight {
                  type uint32 {
                    range "0..4294967295";
                    ext:value-meaning {
                      ext:item "0" {
                        ext:meaning "Invalid";
                        description
                          "The segment list is invalid when weight is 0.";
                      }
                    }
                  }
                  description
                    "Segment-list weighted loadshare.";
                }
                leaf bfd-state {
                  type string {
                    length "1..31";
                  }
                  description
                    "Segment list BFD state.";
                }
                leaf exp-value {
                  type uint32;
                  description
                    "EXP value.";
                }
                leaf ttl-value {
                  type uint32;
                  description
                    "TTL value.";
                }
                container sids {
                  description
                    "List of SIDs.";
                  list sid {
                    key "index";
                    // NCS drop max-elements statement
                    description
                      "Operational data of SID.";
                    leaf index {
                      type uint32 {
                        range "0..4294967295";
                      }
                      description
                        "Index.";
                    }
                    leaf value {
                      type uint32 {
                        range "16..1048575";
                      }
                      description
                        "Value.";
                    }
                  }
                }
              }
            }
          }
        }
      }
    }
  }

  grouping live_ncs_sr-template-infos {
    description
      "SR Policy template infos.";
    container template-infos {
      description
        "List of SR Policy template information.";
      list template-info {
        key "template-id";
        description
          "Operational state of SR Policy template.";
        leaf template-id {
          type uint32 {
            range "1..4294967295";
          }
          description
            "The template ID.";
        }
        leaf bfd-enable {
          type live_ncs_template-enable-type;
          description
            "Enable/disable Seamless-BFD.";
        }
        leaf hsb-enable {
          type live_ncs_template-enable-type;
          description
            "Enable/disable hot standby.";
        }
        leaf traffic-statistics-enable {
          type live_ncs_template-enable-type;
          description
            "Enable/disable traffic statistics.";
        }
      }
    }
  }

  grouping live_ncs_srv6-source-sids {
    description
      "SRv6 TE Policy SID informations.";
    container source-sids {
      description
        "List of SRv6 TE Policy SID informations.";
      list source-sid {
        key "sid-value topology";
        description
          "Operational state of SRv6 TE Policy SID information.";
        leaf sid-value {
          type inet:ipv6-address-no-zone;
          description
            "The SRv6 TE Policy SID value.";
        }
        leaf topology {
          type uint32 {
            range "0..2";
          }
          description
            "The SRv6 TE Policy SID topology.";
        }
        leaf func-type {
          type live_ncs_function-type;
          ext:support-filter "true";
          description
            "The SRv6 TE Policy SID type.";
        }
        leaf overload {
          type boolean;
          description
            "The SRv6 TE Policy SID overload flag.";
        }
        container sources {
          description
            "List of SRv6 TE Policy SID source informations.";
          list source {
            key "protocol process sub-process";
            description
              "Operational state of SRv6 TE Policy SID source information.";
            leaf protocol {
              type live_ncs_protocol-type;
              description
                "The origin protocol.";
            }
            leaf process {
              type uint32 {
                range "1..4294967295";
              }
              description
                "The origin protocol process.";
            }
            leaf sub-process {
              type live_ncs_sub-process-type;
              description
                "The origin protocol sub process.";
            }
            leaf node {
              type string {
                length "1..48";
              }
              description
                "Node information.";
            }
            leaf local {
              type string {
                length "1..48";
              }
              description
                "Local information.";
            }
            leaf peer {
              type string {
                length "1..48";
              }
              description
                "Peer information.";
            }
          }
        }
      }
    }
  }

  grouping live_ncs_srv6-sid-statistics {
    description
      "SRv6 Policy SID statistics infos.";
    container sid-statistics {
      description
        "Operational state of SRv6 Policy SID statistics infos.";
      leaf endx-total-num {
        type uint32 {
          range "0..4294967295";
        }
        description
          "SRv6 Policy End.X SID statistics.";
      }
      leaf end-total-num {
        type uint32 {
          range "0..4294967295";
        }
        description
          "SRv6 Policy End SID statistics.";
      }
      container sid-nums {
        description
          "List of SRv6 Policy SID num.";
        list sid-num {
          key "protocol process sub-process";
          description
            "Operational state of SRv6 Policy SID num.";
          leaf protocol {
            type live_ncs_protocol-type;
            description
              "The origin protocol.";
          }
          leaf process {
            type uint32 {
              range "1..4294967295";
            }
            description
              "The origin protocol process.";
          }
          leaf sub-process {
            type live_ncs_sub-process-type;
            description
              "The origin protocol sub process.";
          }
          leaf endx-num {
            type uint32 {
              range "0..4294967295";
            }
            description
              "The End.X SID num.";
          }
          leaf end-num {
            type uint32 {
              range "0..4294967295";
            }
            description
              "The End SID num.";
          }
        }
      }
    }
  }

  grouping live_ncs_reset-traffic-statistics {
    description
      "Reset SR Policy traffic statistics.";
    leaf name {
      type string {
        length "1..31";
      }
      description
        "SR Policy name.";
    }
    leaf endpoint {
      type inet:ip-address;
      description
        "SR Policy endpoint address.";
    }
    leaf color {
      type uint32 {
        range "0..4294967295";
      }
      description
        "SR Policy color.";
    }
    leaf binding-sid {
      type live_ncs_sid-value-type;
      description
        "SR Policy binding sid.";
    }
  }

  grouping live_ncs_policy-maps {
    description
      "SR Policy mappings.";
    container sr-policy-maps {
      description
        "List of SR Policy mappings.";
      list sr-policy-map {
        // NCS drop must statement
        key "color af-type flow-priority-type";
        // NCS drop max-elements statement
        description
          "Configure an SR Policy mapping.";
        leaf color {
          type uint32 {
            range "0..4294967295";
          }
          description
            "Color of an SR Policy.";
        }
        leaf af-type {
          type live_ncs_address-family-type;
          description
            "Address family type.";
        }
        leaf flow-priority-type {
          type live_ncs_flow-priority-type;
          description
            "Traffic priority type.";
        }
        leaf dscp-value {
          // NCS drop when statement
          type live_ncs_dscp-type;
          // NCS drop mandatory statement
          description
            "DSCP list.";
        }
      }
    }
  }

  grouping live_ncs_dynamic-policy-group {
    description
      "Dynamic SR Policy groups.";
    container dynamic-sr-policy-groups {
      description
        "List of dynamic SR Policy groups.";
      list dynamic-sr-policy-group {
        key "endpoint color";
        description
          "Operational state of a dynamic SR Policy group.";
        leaf endpoint {
          type inet:ip-address;
          description
            "Endpoint of a dynamic SR Policy group.";
        }
        leaf color {
          type uint32;
          description
            "Color of a dynamic SR Policy group.";
        }
        leaf tunnel-id {
          type uint32;
          description
            "Tunnel ID.";
        }
        leaf tunnel-type {
          type live_ncs_tunnel-type;
          description
            "Tunnel type.";
        }
        leaf state {
          type live_ncs_group-state-type;
          description
            "State of a dynamic SR Policy group.";
        }
        leaf state-change-time {
          type yang:date-and-time;
          description
            "Date and time when the state of a dynamic SR Policy group changed.";
        }
        leaf delay-timer-remain {
          type uint32;
          units "ms";
          description
            "Remaining time of the delay timer.";
        }
        leaf map-count {
          type uint32;
          description
            "Number of mappings in a dynamic SR Policy group.";
        }
        leaf up-map-count {
          type uint32;
          description
            "Number of mappings that are up in a dynamic SR Policy group.";
        }
        container maps {
          description
            "List of mappings in a dynamic SR Policy group.";
          list map {
            key "color af-type flow-priority-type";
            // NCS drop max-elements statement
            description
              "Operational state of a mapping in a dynamic SR Policy group.";
            leaf color {
              type uint32;
              description
                "Color of an SR Policy.";
            }
            leaf af-type {
              type live_ncs_address-family-type;
              description
                "Address family type.";
            }
            leaf flow-priority-type {
              type live_ncs_flow-priority-type;
              description
                "Traffic priority type.";
            }
            leaf flow-priority-list {
              type string {
                length "1..64";
              }
              description
                "Priority list.";
            }
            leaf policy-tunnel-id {
              type uint32;
              description
                "Tunnel ID of an SR Policy.";
            }
            leaf policy-tunnel-type {
              type live_ncs_tunnel-type;
              description
                "Tunnel type of an SR Policy.";
            }
          }
        }
      }
    }
  }

  grouping live_ncs_dynamic-policy-group-down-reason {
    description
      "Dynamic SR Policy group down reason.";
    container dynamic-policy-group-down-reasons {
      description
        "List of down records of dynamic SR Policy groups.";
      list dynamic-policy-group-down-reason {
        key "endpoint color up-time up-millisecond";
        description
          "Operational state of down record of a dynamic SR Policy group.";
        leaf endpoint {
          type inet:ip-address;
          description
            "Endpoint of an SR Policy group.";
        }
        leaf color {
          type uint32 {
            range "0..4294967295";
          }
          description
            "Color of an SR Policy group.";
        }
        leaf up-time {
          type yang:date-and-time;
          description
            "Date and time when a dynamic SR Policy group went up.";
        }
        leaf up-millisecond {
          type uint32 {
            range "0..1000";
          }
          description
            "Millisecond value of the time when a dynamic SR Policy group went up.";
        }
        leaf tunnel-id {
          type uint32;
          description
            "Tunnel ID.";
        }
        leaf tunnel-type {
          type live_ncs_tunnel-type;
          description
            "Tunnel type.";
        }
        leaf create-time {
          type yang:date-and-time;
          description
            "Date and time when a dynamic SR Policy group was created.";
        }
        leaf down-time {
          type yang:date-and-time;
          description
            "Date and time when a dynamic SR Policy group went down.";
        }
        leaf down-reason {
          type live_ncs_group-down-reason-type;
          description
            "Reason why a dynamic SR Policy group went down.";
        }
        container map-down-reasons {
          description
            "List of reason why mappings went down.";
          list map-down-reason {
            key "sr-policy-color af-type up-time up-millisecond";
            // NCS drop max-elements statement
            description
              "Operational state of reason why a mapping went down.";
            leaf sr-policy-color {
              type uint32 {
                range "0..4294967295";
              }
              description
                "Color of an SR Policy.";
            }
            leaf af-type {
              type live_ncs_address-family-type;
              description
                "Address family type.";
            }
            leaf up-time {
              type yang:date-and-time;
              description
                "Date and time when a mapping went up.";
            }
            leaf up-millisecond {
              type uint32 {
                range "0..1000";
              }
              description
                "Millisecond value of the time when a mapping went up.";
            }
            leaf down-time {
              type yang:date-and-time;
              description
                "Date and time when a mapping went down.";
            }
            leaf down-reason {
              type live_ncs_map-down-reason-type;
              description
                "Reason why a mapping went down.";
            }
          }
        }
      }
    }
  }

  grouping live_ncs_policy-group-statistics {
    description
      "SR Policy group statistics.";
    container policy-group-statistic {
      description
        "Statistics of SR Policy groups.";
      leaf mapping-policy {
        type uint32 {
          range "0..4294967295";
        }
        description
          "Number of mapping policies.";
      }
      leaf sr-policy-group {
        type uint32 {
          range "0..4294967295";
        }
        description
          "Number of SR Policy groups.";
      }
      leaf sr-policy-group-up {
        type uint32 {
          range "0..4294967295";
        }
        description
          "Number of SR Policy groups that are up.";
      }
      leaf dscp-map {
        type uint32 {
          range "0..4294967295";
        }
        description
          "Number of DSCP mappings.";
      }
      leaf dscp-map-up {
        type uint32 {
          range "0..4294967295";
        }
        description
          "Number of DSCP mappings that are up.";
      }
    }
  }

  grouping bfd {
    description
      "SR Policy BFD configuration.";
    container bfd {
      description
        "Configure SR Policy BFD.";
      leaf enable {
        type bfd-enable-type;
        default "disable";
        description
          "Enable seamless-bfd for all SR Policies.";
      }
      leaf bypass {
        type bfd-bypass-type;
        default "bypass";
        description
          "Enable BFD bypass for all SR policies.";
      }
      leaf min-tx {
        type uint32 {
          range "1..4294967295";
        }
        units "ms";
        default "10";
        description
          "Minimum interval for sending seamless-bfd packets to the peer end. The range and default are based on PAF.";
      }
      leaf min-rx {
        type uint32 {
          range "1..4294967295";
        }
        units "ms";
        default "10";
        description
          "Minimum interval for receiving seamless-bfd packets from the peer end. The range and default are based on PAF.";
      }
      leaf multi-num {
        type uint32 {
          range "3..50";
        }
        default "3";
        description
          "Local detection multiplier.";
      }
      leaf backup-min-tx {
        type uint32 {
          range "1..4294967295";
        }
        units "ms";
        description
          "Minimum interval for sending seamless-bfd packets to the peer end over the backup candidate path. The range and default are based on PAF.";
      }
      leaf backup-multi-num {
        type uint32 {
          range "3..50";
        }
        description
          "Local detection multiplier over the backup candidate path.";
      }
    }
  }

  grouping global-attributes {
    description
      "SR Policy global configuration.";
    leaf switch-delay {
      type uint32 {
        range "0..600000";
      }
      units "ms";
      default "5000";
      description
        "MBB switch delay time.";
    }
    leaf delete-delay {
      type uint32 {
        range "0..600000";
      }
      units "ms";
      default "20000";
      description
        "MBB delete delay time.";
    }
    leaf hsb-enable {
      type boolean;
      default "false";
      description
        "Enable/disable hot standby.";
    }
    leaf traffic-statistics-enable {
      type boolean;
      default "false";
      description
        "Enable/disable traffic statistics collection.";
    }
    leaf bgp-ls-enable {
      type boolean;
      default "false";
      description
        "Enable/disable BGP-LS.";
    }
    leaf path-verification {
      type boolean;
      default "false";
      description
        "Enable/disable path verification.";
    }
    leaf suppress-flapping {
      type boolean;
      default "true";
      description
        "Enable/disable suppress flapping.";
    }
    leaf policy-threshold-upper {
      type uint32 {
        range "2..100";
      }
      must '(../policy-threshold-upper>../policy-threshold-lower)' {
        tailf:xpath-root 3;
      }
      default "80";
      description
        "SR Policy threshold upper limit.";
    }
    leaf policy-threshold-lower {
      type uint32 {
        range "1..99";
      }
      default "75";
      description
        "SR Policy threshold lower limit.";
    }
    leaf list-threshold-upper {
      type uint32 {
        range "2..100";
      }
      must '(../list-threshold-upper>../list-threshold-lower)' {
        tailf:xpath-root 3;
      }
      default "80";
      description
        "Segment List threshold upper limit.";
    }
    leaf list-threshold-lower {
      type uint32 {
        range "1..99";
      }
      default "75";
      description
        "Segment List threshold lower limit.";
    }
    leaf group-threshold-upper {
      type uint32 {
        range "2..100";
      }
      must '(../group-threshold-upper>../group-threshold-lower)' {
        tailf:xpath-root 3;
      }
      default "80";
      description
        "Upper threshold for the number of SR Policy groups.";
    }
    leaf group-threshold-lower {
      type uint32 {
        range "1..99";
      }
      default "75";
      description
        "Lower threshold for the number of SR Policy groups.";
    }
    uses bfd;
  }

  grouping srv4-segment-lists {
    description
      "Global segment lists.";
    container segment-lists {
      description
        "List of global segment lists.";
      list segment-list {
        key "name";
        description
          "Configure a global segment list.";
        leaf name {
          type string {
            length "1..31";
            pattern '[^ \?]*';
          }
          description
            "Global segment list name.";
        }
        container segments {
          description
            "List of segments in a global segment list.";
          list segment {
            key "index";
            max-elements 10;
            description
              "Configure a segment in a global segment list.";
            leaf index {
              type uint32 {
                range "0..4294967295";
              }
              description
                "The segment index.";
            }
            choice type {
              mandatory true;
              description
                "The segment type.";
              case segment-type-1 {
                description
                  "The segment is declared by MPLS label.";
                leaf sid-value-1 {
                  type uint32 {
                    range "16..1048575";
                  }
                  description
                    "MPLS label value.";
                }
              }
            }
          }
        }
      }
    }
  }

  grouping srv6-segment-lists {
    description
      "Global segment lists.";
    container segment-lists {
      description
        "List of global segment lists.";
      list segment-list {
        key "name";
        description
          "Configure a global segment list.";
        leaf name {
          type string {
            length "1..31";
            pattern '[^ \?]*';
          }
          description
            "Global segment list name.";
        }
        container segments {
          description
            "List of segments in a global segment list.";
          list segment {
            key "index";
            max-elements 10;
            description
              "Configure a segment in a global segment list.";
            leaf index {
              type uint32 {
                range "0..4294967295";
              }
              description
                "The segment index.";
            }
            choice type {
              mandatory true;
              description
                "The segment type.";
              case segment-type-2 {
                description
                  "The segment is declared by SRv6 SID value.";
                leaf sid-value-2 {
                  type inet:ipv6-address-no-zone;
                  mandatory true;
                  description
                    "SRv6 sid value.";
                }
                leaf block-length {
                  type uint32 {
                    range "16..80";
                  }
                  must '((../block-length) mod 16 = 0)' {
                    tailf:xpath-root 3;
                  }
                  description
                    "SRv6 SID block length.";
                }
              }
            }
          }
        }
      }
    }
  }

  grouping srv6-policy-attributes {
    description
      "Grouping containing attributes applicable to all SR policies.";
    container policy-attributes {
      description
        "Configure attributes for all SR policies.";
      uses global-attributes;
      leaf locator {
        ext:operation-exclude "update";
        type leafref {
          path "/ncs:devices/ncs:device/ncs:config/ni:network-instance/ni:instances/ni:instance/srv6:srv6/srv6:locators/srv6:locator/srv6:name" {
            tailf:xpath-root 3;
          }
        }
        description
          "Locator Name.";
      }
      uses srv6-segment-lists;
    }
  }

  grouping srv4-policy-attributes {
    description
      "Grouping containing attributes applicable to all SR policies.";
    container policy-attributes {
      description
        "Configure attributes for all SR policies.";
      uses global-attributes;
      uses srv4-segment-lists;
    }
  }

  grouping candidate-paths {
    description
      "Grouping containing candidate paths to all SR policies.";
    container candidate-paths {
      description
        "List of candidate paths in an SR Policy.";
      list candidate-path {
        must '(discriminator=preference)' {
          tailf:xpath-root 3;
        }
        key "protocol-origin originator discriminator";
        max-elements 64;
        description
          "Configure a candidate path.";
        leaf protocol-origin {
          type protocol-origin-type;
          must "(../protocol-origin='configuration')" {
            tailf:xpath-root 3;
          }
          description
            "Candidate path protocol origin.";
        }
        leaf originator {
          type string {
            length "1..60";
          }
          must "(../originator='0,0.0.0.0')" {
            tailf:xpath-root 3;
          }
          description
            "Candidate path originator.";
        }
        leaf discriminator {
          type uint32 {
            range "1..65535";
          }
          description
            "Candidate path discriminator.";
        }
        leaf preference {
          type uint32 {
            range "1..65535";
          }
          mandatory true;
          description
            "Candidate path preference.";
        }
        choice type {
          description
            "Type of candidate paths.";
          case explicit {
            description
              "Candidate path with explicitly defined set/s of segment-lists.";
            container segment-lists {
              description
                "List of segment lists in a candidate path.";
              list segment-list {
                key "name";
                max-elements 64;
                description
                  "Configure a segment list for a candidate path.";
                leaf name {
                  type leafref {
                    path "../../../../../../../policy-attributes/segment-lists/segment-list/name";
                  }
                  description
                    "Segment list name.";
                }
                leaf weight {
                  type uint32 {
                    range "0..4294967295";
                    ext:value-meaning {
                      ext:item "0" {
                        ext:meaning "Invalid";
                        description
                          "The segment list is invalid when weight is 0.";
                      }
                    }
                  }
                  default "1";
                  description
                    "Segment-list weighted loadshare.";
                }
                leaf path-mtu {
                  type uint32 {
                    range "1280..9600";
                  }
                  description
                    "Segment-list path-mtu.";
                }
              }
            }
          }
        }
        leaf template-id {
          type leafref {
            path "/ncs:devices/ncs:device/ncs:config/srpolicy:srpolicy/srpolicy:attribute-templates/srpolicy:attribute-template/srpolicy:id" {
              tailf:xpath-root 3;
            }
          }
          description
            "Attribute template ID.";
        }
        leaf network-slice-id {
          type uint32 {
            range "1..4294967295";
          }
          description
            "Network slice ID of candidate path.";
        }
      }
    }
  }

  grouping srv4-policys {
    description
      "SR policy grouping.";
    container policys {
      description
        "List of SR Policies.";
      list policy {
        key "endpoint color";
        unique "name";
        unique "binding-sid/value";
        description
          "Configure an SR Policy.";
        leaf endpoint {
          type inet:ip-address;
          description
            "SR Policy endpoint address.";
        }
        leaf color {
          type uint32 {
            range "0..4294967295";
          }
          description
            "SR Policy color.";
        }
        leaf name {
          type string {
            length "1..31";
            pattern '[^ \?]*';
          }
          mandatory true;
          description
            "SR Policy name.";
        }
        container binding-sid {
          description
            "Configure a binding SID.";
          leaf dataplane {
            type dataplane-type;
            must "(../dataplane='mpls')" {
              tailf:xpath-root 3;
            }
            description
              "Binding sid dataplane type.";
          }
          leaf value {
            when "(../dataplane='mpls')" {
              tailf:xpath-root 3;
            }
            type sid-value-type;
            mandatory true;
            description
              "Binding sid value.";
          }
        }
        leaf admin-state {
          type admin-state-type;
          default "up";
          description
            "Close the function of SR Policy.";
        }
        leaf mtu {
          type uint32 {
            range "512..9600";
          }
          description
            "SR Policy mtu value.";
        }
        leaf hsb-enable {
          type enable-3types;
          default "not-configured";
          description
            "SR Policy hot standby.";
        }
        leaf bfd-enable {
          type policy-bfd-enable-type;
          default "not-configured";
          description
            "SR Policy BFD.";
        }
        leaf traffic-statistics-enable {
          type enable-3types;
          default "not-configured";
          description
            "SR Policy traffic statistics.";
        }
        container diffserv-mode {
          description
            "Configure the DiffServ mode in an SR Policy.";
          leaf pipe-mode {
            type pipe-mode-type;
            description
              "Specifies the pipe mode of SR Policy.";
          }
          leaf service-class {
            when "../pipe-mode='pipe'" {
              tailf:xpath-root 3;
            }
            type serv-class-types;
            mandatory true;
            description
              "Service class of SR Policy.";
          }
          leaf service-color {
            when "../pipe-mode='pipe'" {
              tailf:xpath-root 3;
            }
            type serv-color-types;
            mandatory true;
            description
              "Service color of SR Policy.";
          }
        }
        uses candidate-paths;
      }
    }
  }

  grouping srv6-policys {
    description
      "SR policy grouping.";
    container policys {
      description
        "List of SR Policies.";
      list policy {
        key "endpoint color";
        unique "name";
        unique "binding-sid/value";
        description
          "Configure an SR Policy.";
        leaf endpoint {
          type inet:ip-address;
          description
            "SR Policy endpoint address.";
        }
        leaf color {
          type uint32 {
            range "0..4294967295";
          }
          description
            "SR Policy color.";
        }
        leaf name {
          type string {
            length "1..31";
            pattern '[^ \?]*';
          }
          mandatory true;
          description
            "SR Policy name.";
        }
        container binding-sid {
          must "(../../../policy-attributes/locator and /ni:network-instance/ni:instances/ni:instance[ni:name='_public_']/srv6:srv6/srv6:locators/srv6:locator[srv6:name=/ni:network-instance/ni:instances/ni:instance[ni:name='_public_']/srv6:srv6/srpolicy:srpolicy/srpolicy:policy-attributes/srpolicy:locator]/srv6:static-length>0)" {
            tailf:xpath-root 3;
          }
          description
            "Configure a binding SID.";
          leaf dataplane {
            type dataplane-type;
            must "(../dataplane='srv6')" {
              tailf:xpath-root 3;
            }
            description
              "Binding sid dataplane type.";
          }
          leaf value {
            when "(../dataplane='srv6')" {
              tailf:xpath-root 3;
            }
            type sid-value-type;
            mandatory true;
            description
              "Binding sid value.";
          }
        }
        leaf admin-state {
          type admin-state-type;
          default "up";
          description
            "Close the function of SR Policy.";
        }
        leaf mtu {
          type uint32 {
            range "512..9600";
          }
          description
            "SR Policy mtu value.";
        }
        leaf hsb-enable {
          type enable-3types;
          default "not-configured";
          description
            "SR Policy hot standby.";
        }
        leaf bfd-enable {
          type policy-bfd-enable-type;
          default "not-configured";
          description
            "SR Policy BFD.";
        }
        leaf bfd-bypass {
          type policy-bfd-bypass-type;
          default "not-configured";
          description
            "SR policy BFD bypass.";
        }
        leaf traffic-statistics-enable {
          type enable-3types;
          default "not-configured";
          description
            "SR Policy traffic statistics.";
        }
        leaf path-verification {
          type enable-3types;
          default "not-configured";
          description
            "SR Policy path verification.";
        }
        container diffserv-mode {
          description
            "Configure the DiffServ mode in an SR Policy.";
          leaf pipe-mode {
            type pipe-mode-type;
            description
              "Specifies the pipe mode of SR Policy.";
          }
          leaf service-class {
            when "../pipe-mode='pipe'" {
              tailf:xpath-root 3;
            }
            type serv-class-types;
            mandatory true;
            description
              "Service class of SR Policy.";
          }
          leaf service-color {
            when "../pipe-mode='pipe'" {
              tailf:xpath-root 3;
            }
            type serv-color-types;
            mandatory true;
            description
              "Service color of SR Policy.";
          }
        }
        uses candidate-paths;
      }
    }
  }

  grouping policy-groups {
    description
      "SR-MPLS TE Policy group grouping.";
    container policy-groups {
      description
        "List of SR-MPLS TE Policy groups.";
      list policy-group {
        key "index";
        description
          "Configure an SR-MPLS TE Policy group.";
        leaf index {
          type uint32 {
            range "1..4294967295";
          }
          description
            "SR-MPLS TE Policy group id.";
        }
        leaf endpoint {
          type inet:ip-address;
          description
            "SR-MPLS TE Policy IPv4 endPoint address.";
        }
        // NCS drop config false leaf state
        // NCS drop config false leaf 'tunnel-id'
        // NCS drop config false leaf 'tunnel-type'
        // NCS drop config false leaf 'match-count'
        // NCS drop config false leaf 'up-match-count'
        container color-dscp-matchs {
          description
            "List of color-address family-DSCP mappings for an SR-MPLS TE Policy.";
          list color-dscp-match {
            key "color af-type";
            max-elements 128;
            description
              "Configure a color-address family-DSCP mapping for an SR-MPLS TE Policy.";
            leaf color {
              type uint32 {
                range "0..4294967295";
              }
              description
                "SR-MPLS TE Policy color.";
            }
            leaf af-type {
              type address-family-type;
              description
                "Address family.";
            }
            leaf default {
              type boolean;
              default "false";
              description
                "Enable/disable the default SR-MPLS TE Policy.";
            }
            leaf dscp-value {
              when "not(../default='true')" {
                tailf:xpath-root 3;
              }
              type pub-type:id-range {
                ext:value-range "0..63";
              }
              mandatory true;
              description
                "DSCP Value.";
            }
            // NCS drop config false leaf 'policy-tunnel-id'
          }
        }
      }
    }
  }

  grouping traffic-statistics {
    description
      "SR Policy traffic statistics grouping.";
    // NCS drop config false container 'policy-traffic-statistics'
    // NCS drop config false container 'list-traffic-statistics'
  }

  grouping srv6-policy-infos {
    description
      "SRv6 Policy infos grouping.";
    // NCS drop config false container 'policy-infos'
  }

  grouping srv4-policy-infos {
    description
      "SR-MPLS TE Policy infos grouping.";
    // NCS drop config false container 'policy-infos'
  }

  grouping sr-template-infos {
    description
      "SR Policy template infos.";
    // NCS drop config false container 'template-infos'
  }

  grouping srv6-source-sids {
    description
      "SRv6 TE Policy SID informations.";
    // NCS drop config false container 'source-sids'
  }

  grouping srv6-sid-statistics {
    description
      "SRv6 Policy SID statistics infos.";
    // NCS drop config false container 'sid-statistics'
  }

  grouping reset-traffic-statistics {
    description
      "Reset SR Policy traffic statistics.";
    leaf name {
      type string {
        length "1..31";
      }
      description
        "SR Policy name.";
    }
    leaf endpoint {
      type inet:ip-address;
      description
        "SR Policy endpoint address.";
    }
    leaf color {
      type uint32 {
        range "0..4294967295";
      }
      description
        "SR Policy color.";
    }
    leaf binding-sid {
      type sid-value-type;
      description
        "SR Policy binding sid.";
    }
  }

  grouping policy-maps {
    description
      "SR Policy mappings.";
    container sr-policy-maps {
      description
        "List of SR Policy mappings.";
      list sr-policy-map {
        must "(../../srv6:type='sr-policy-dscp')" {
          tailf:xpath-root 3;
        }
        key "color af-type flow-priority-type";
        max-elements 128;
        description
          "Configure an SR Policy mapping.";
        leaf color {
          type uint32 {
            range "0..4294967295";
          }
          description
            "Color of an SR Policy.";
        }
        leaf af-type {
          type address-family-type;
          description
            "Address family type.";
        }
        leaf flow-priority-type {
          type flow-priority-type;
          description
            "Traffic priority type.";
        }
        leaf dscp-value {
          when "../flow-priority-type='dscp'" {
            tailf:xpath-root 3;
          }
          type dscp-type;
          mandatory true;
          description
            "DSCP list.";
        }
      }
    }
  }

  grouping dynamic-policy-group {
    description
      "Dynamic SR Policy groups.";
    // NCS drop config false container 'dynamic-sr-policy-groups'
  }

  grouping dynamic-policy-group-down-reason {
    description
      "Dynamic SR Policy group down reason.";
    // NCS drop config false container 'dynamic-policy-group-down-reasons'
  }

  grouping policy-group-statistics {
    description
      "SR Policy group statistics.";
    // NCS drop config false container 'policy-group-statistic'
  }

  augment "/ncs:devices/ncs:device/ncs:rpc" {
    container rpc-reset-sr-mpls-te-policy-traffic-statistics {
      tailf:ncs-device-type "netconf";
      tailf:display-when "not(../../ncs:module) or ../../ncs:module[ncs:name='huawei-srpolicy']";
      tailf:action reset-sr-mpls-te-policy-traffic-statistics {
        tailf:actionpoint ncsproxy {
          tailf:internal;
        }
        description
          "Reset SR-MPLS TE Policy traffic statistics.";
        input {
          uses ncs_rpc_notif_reset-traffic-statistics;
        }
      }
    }
  }
  augment "/ncs:devices/ncs:device-group/ncs:ned-id/ncs:rpc" {
    container rpc-reset-sr-mpls-te-policy-traffic-statistics {
      tailf:ncs-device-type "netconf";
      tailf:display-when "/ncs:devices/ncs:device[ncs:name=current()/../../../ncs:member]/ncs:module[ncs:name='huawei-srpolicy']";
      tailf:action reset-sr-mpls-te-policy-traffic-statistics {
        tailf:actionpoint ncsproxy {
          tailf:internal;
        }
        description
          "Reset SR-MPLS TE Policy traffic statistics.";
        input {
          uses ncs_rpc_notif_reset-traffic-statistics;
        }
      }
    }
  }
  augment "/ncs:devices/ncs:device/ncs:rpc" {
    container rpc-reset-srv6-te-policy-traffic-statistics {
      tailf:ncs-device-type "netconf";
      tailf:display-when "not(../../ncs:module) or ../../ncs:module[ncs:name='huawei-srpolicy']";
      tailf:action reset-srv6-te-policy-traffic-statistics {
        tailf:actionpoint ncsproxy {
          tailf:internal;
        }
        description
          "Reset SRv6 TE Policy traffic statistics.";
        input {
          uses ncs_rpc_notif_reset-traffic-statistics;
        }
      }
    }
  }
  augment "/ncs:devices/ncs:device-group/ncs:ned-id/ncs:rpc" {
    container rpc-reset-srv6-te-policy-traffic-statistics {
      tailf:ncs-device-type "netconf";
      tailf:display-when "/ncs:devices/ncs:device[ncs:name=current()/../../../ncs:member]/ncs:module[ncs:name='huawei-srpolicy']";
      tailf:action reset-srv6-te-policy-traffic-statistics {
        tailf:actionpoint ncsproxy {
          tailf:internal;
        }
        description
          "Reset SRv6 TE Policy traffic statistics.";
        input {
          uses ncs_rpc_notif_reset-traffic-statistics;
        }
      }
    }
  }
  augment "/ncs:devices/ncs:device/ncs:config" {
    container srpolicy {
      tailf:ncs-device-type "netconf";
      tailf:display-when "not(../../ncs:module) or ../../ncs:module[ncs:name='huawei-srpolicy']";
      description
        "Configure SR Policy parameters.";
      container attribute-templates {
        description
          "List of SR Policy template attribute.";
        list attribute-template {
          key "id";
          description
            "Configure SR Policy template attribute.";
          leaf id {
            type uint32 {
              range "1..4294967269";
            }
            description
              "The template ID.";
          }
          leaf description {
            type string {
              length "1..242";
            }
            description
              "The template description.";
          }
          leaf bfd-enable {
            type enable-3types;
            default "not-configured";
            description
              "The template BFD flag.";
          }
          leaf sbfd-bypass {
            type enable-3types;
            default "not-configured";
            description
              "The template SBFD bypass flag.";
          }
          leaf hsb-enable {
            type enable-3types;
            default "not-configured";
            description
              "The template hot standby flag.";
          }
          leaf traffic-statistics-enable {
            type enable-3types;
            default "not-configured";
            description
              "The template traffic statistics flag.";
          }
          leaf path-verification-enable {
            type enable-3types;
            default "not-configured";
            description
              "The template path verification flag.";
          }
        }
      }
      // NCS drop config false container 'attribute-template-infos'
    }
  }
  augment "/ncs:devices/ncs:device/ncs:live-status" {
    container srpolicy {
      tailf:ncs-device-type "netconf";
      tailf:display-when "not(../../ncs:module) or ../../ncs:module[ncs:name='huawei-srpolicy'] or (../../ncs:live-status-protocol[not(ncs:capability)]) or (../../ncs:live-status-protocol/ncs:capability/ncs:module[.='huawei-srpolicy'])";
      description
        "Configure SR Policy parameters.";
      container attribute-templates {
        description
          "List of SR Policy template attribute.";
        list attribute-template {
          key "id";
          description
            "Configure SR Policy template attribute.";
          leaf id {
            type uint32 {
              range "1..4294967269";
            }
            description
              "The template ID.";
          }
          leaf description {
            type string {
              length "1..242";
            }
            description
              "The template description.";
          }
          leaf bfd-enable {
            type live_ncs_enable-3types;
            // NCS drop default statement
            description
              "The template BFD flag.";
          }
          leaf sbfd-bypass {
            type live_ncs_enable-3types;
            // NCS drop default statement
            description
              "The template SBFD bypass flag.";
          }
          leaf hsb-enable {
            type live_ncs_enable-3types;
            // NCS drop default statement
            description
              "The template hot standby flag.";
          }
          leaf traffic-statistics-enable {
            type live_ncs_enable-3types;
            // NCS drop default statement
            description
              "The template traffic statistics flag.";
          }
          leaf path-verification-enable {
            type live_ncs_enable-3types;
            // NCS drop default statement
            description
              "The template path verification flag.";
          }
        }
      }
      container attribute-template-infos {
        description
          "List of SR Policy attribute template informations.";
        list attribute-template-info {
          key "id";
          description
            "Operational state of SR Policy attribute template.";
          leaf id {
            type uint32 {
              range "1..4294967295";
            }
            description
              "The template ID.";
          }
          leaf description {
            type string {
              length "1..242";
            }
            description
              "The template description.";
          }
          leaf bfd-enable {
            type live_ncs_enable-3types;
            description
              "Enable/disable Seamless-BFD.";
          }
          leaf sbfd-bypass {
            type live_ncs_enable-3types;
            description
              "Enable/disable Seamless-BFD bypass.";
          }
          leaf hsb-enable {
            type live_ncs_enable-3types;
            description
              "Enable/disable hot standby.";
          }
          leaf path-verification-enable {
            type live_ncs_enable-3types;
            description
              "Enable/disable path verification.";
          }
          leaf traffic-statistics-enable {
            type live_ncs_enable-3types;
            description
              "Enable/disable traffic statistics.";
          }
          leaf configuratin-path-refcnt {
            type uint32 {
              range "0..4294967295";
            }
            description
              "The configuratin path reference count.";
          }
          leaf bgp-path-refcnt {
            type uint32 {
              range "0..4294967295";
            }
            description
              "The BGP path reference count.";
          }
        }
      }
    }
  }
  augment "/ncs:devices/ncs:template/ncs:ned-id/ncs:config" {
    container srpolicy {
      description
        "Configure SR Policy parameters.";
      container attribute-templates {
        description
          "List of SR Policy template attribute.";
        list attribute-template {
          // NCS patched for predictable order
          ordered-by user;
          key "id";
          description
            "Configure SR Policy template attribute.";
          leaf id {
            type string;
            description
              "The template ID.";
          }
          leaf description {
            type string;
            description
              "The template description.";
          }
          leaf bfd-enable {
            type ncs_template_enable-3types;
            // NCS drop default statement
            description
              "The template BFD flag.";
          }
          leaf sbfd-bypass {
            type ncs_template_enable-3types;
            // NCS drop default statement
            description
              "The template SBFD bypass flag.";
          }
          leaf hsb-enable {
            type ncs_template_enable-3types;
            // NCS drop default statement
            description
              "The template hot standby flag.";
          }
          leaf traffic-statistics-enable {
            type ncs_template_enable-3types;
            // NCS drop default statement
            description
              "The template traffic statistics flag.";
          }
          leaf path-verification-enable {
            type ncs_template_enable-3types;
            // NCS drop default statement
            description
              "The template path verification flag.";
          }
        }
      }
      // NCS drop config false container 'attribute-template-infos'
    }
  }
  augment "/ncs:devices/ncs:template/ncs:ned-id/ncs:config/ni:network-instance/ni:instances/ni:instance/srv6:srv6" {
    description
      "Augment for Segment Routing Policy.";
    container srpolicy {
      // NCS drop when statement
      description
        "Configure SR Policy parameters.";
      uses ncs_template_srv6-policy-attributes;
      uses ncs_template_srv6-policys;
      uses ncs_template_traffic-statistics;
      uses ncs_template_srv6-policy-infos;
      uses ncs_template_dynamic-policy-group;
      uses ncs_template_dynamic-policy-group-down-reason;
      uses ncs_template_policy-group-statistics;
      uses ncs_template_sr-template-infos;
      uses ncs_template_srv6-source-sids;
      uses ncs_template_srv6-sid-statistics;
    }
  }
  augment "/ncs:devices/ncs:device/ncs:live-status/ni:network-instance/ni:instances/ni:instance/srv6:srv6" {
    description
      "Augment for Segment Routing Policy.";
    container srpolicy {
      tailf:ncs-device-type "netconf";
      tailf:display-when "not(../../../../../../ncs:module) or ../../../../../../ncs:module[ncs:name='huawei-srpolicy'] or (../../../../../../ncs:live-status-protocol[not(ncs:capability)]) or (../../../../../../ncs:live-status-protocol/ncs:capability/ncs:module[.='huawei-srpolicy'])";
      // NCS drop when statement
      description
        "Configure SR Policy parameters.";
      uses live_ncs_srv6-policy-attributes;
      uses live_ncs_srv6-policys;
      uses live_ncs_traffic-statistics;
      uses live_ncs_srv6-policy-infos;
      uses live_ncs_dynamic-policy-group;
      uses live_ncs_dynamic-policy-group-down-reason;
      uses live_ncs_policy-group-statistics;
      uses live_ncs_sr-template-infos;
      uses live_ncs_srv6-source-sids;
      uses live_ncs_srv6-sid-statistics;
    }
  }
  augment "/ncs:devices/ncs:device/ncs:config/ni:network-instance/ni:instances/ni:instance/srv6:srv6" {
    description
      "Augment for Segment Routing Policy.";
    container srpolicy {
      tailf:ncs-device-type "netconf";
      tailf:display-when "not(../../../../../../ncs:module) or ../../../../../../ncs:module[ncs:name='huawei-srpolicy']";
      when "../srv6:enable='true'" {
        tailf:xpath-root 3;
      }
      description
        "Configure SR Policy parameters.";
      uses srv6-policy-attributes;
      uses srv6-policys;
      uses traffic-statistics;
      uses srv6-policy-infos;
      uses dynamic-policy-group;
      uses dynamic-policy-group-down-reason;
      uses policy-group-statistics;
      uses sr-template-infos;
      uses srv6-source-sids;
      uses srv6-sid-statistics;
    }
  }
  augment "/ncs:devices/ncs:template/ncs:ned-id/ncs:config/ni:network-instance/ni:instances/ni:instance/sr:segment-routing" {
    description
      "Augment for SR Policy.";
    container srpolicy {
      // NCS drop when statement
      description
        "Configure SR Policy parameters.";
      uses ncs_template_srv4-policy-attributes;
      uses ncs_template_srv4-policys;
      uses ncs_template_srv4-policy-infos;
      uses ncs_template_policy-groups;
      uses ncs_template_traffic-statistics;
      uses ncs_template_sr-template-infos;
    }
  }
  augment "/ncs:devices/ncs:device/ncs:live-status/ni:network-instance/ni:instances/ni:instance/sr:segment-routing" {
    description
      "Augment for SR Policy.";
    container srpolicy {
      tailf:ncs-device-type "netconf";
      tailf:display-when "not(../../../../../../ncs:module) or ../../../../../../ncs:module[ncs:name='huawei-srpolicy'] or (../../../../../../ncs:live-status-protocol[not(ncs:capability)]) or (../../../../../../ncs:live-status-protocol/ncs:capability/ncs:module[.='huawei-srpolicy'])";
      // NCS drop when statement
      description
        "Configure SR Policy parameters.";
      uses live_ncs_srv4-policy-attributes;
      uses live_ncs_srv4-policys;
      uses live_ncs_srv4-policy-infos;
      uses live_ncs_policy-groups;
      uses live_ncs_traffic-statistics;
      uses live_ncs_sr-template-infos;
    }
  }
  augment "/ncs:devices/ncs:device/ncs:config/ni:network-instance/ni:instances/ni:instance/sr:segment-routing" {
    description
      "Augment for SR Policy.";
    container srpolicy {
      tailf:ncs-device-type "netconf";
      tailf:display-when "not(../../../../../../ncs:module) or ../../../../../../ncs:module[ncs:name='huawei-srpolicy']";
      when "../sr:enable='true'" {
        tailf:xpath-root 3;
      }
      description
        "Configure SR Policy parameters.";
      uses srv4-policy-attributes;
      uses srv4-policys;
      uses srv4-policy-infos;
      uses policy-groups;
      uses traffic-statistics;
      uses sr-template-infos;
    }
  }
  augment "/ncs:devices/ncs:template/ncs:ned-id/ncs:config/ni:network-instance/ni:instances/ni:instance/srv6:srv6/srv6:mapping-policys/srv6:mapping-policy" {
    description
      "Augment for SR Policy mappings.";
    uses ncs_template_policy-maps;
  }
  augment "/ncs:devices/ncs:device/ncs:live-status/ni:network-instance/ni:instances/ni:instance/srv6:srv6/srv6:mapping-policys/srv6:mapping-policy" {
    description
      "Augment for SR Policy mappings.";
    uses live_ncs_policy-maps {
      refine sr-policy-maps {
        tailf:ncs-device-type "netconf";
        tailf:display-when "not(../../../../../../../../ncs:module) or ../../../../../../../../ncs:module[ncs:name='huawei-srpolicy'] or (../../../../../../../../ncs:live-status-protocol[not(ncs:capability)]) or (../../../../../../../../ncs:live-status-protocol/ncs:capability/ncs:module[.='huawei-srpolicy'])";
      }
    }
  }
  augment "/ncs:devices/ncs:device/ncs:config/ni:network-instance/ni:instances/ni:instance/srv6:srv6/srv6:mapping-policys/srv6:mapping-policy" {
    description
      "Augment for SR Policy mappings.";
    uses policy-maps {
      refine sr-policy-maps {
        tailf:ncs-device-type "netconf";
        tailf:display-when "not(../../../../../../../../ncs:module) or ../../../../../../../../ncs:module[ncs:name='huawei-srpolicy']";
      }
    }
  }
}
