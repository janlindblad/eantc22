module huawei-mac-fwd {
  // Generated by yanger -t ncs
  tailf:mount-id "huawei-nc-1.0:huawei-nc-1.0";
  tailf:ncs-device-type "netconf";

  namespace "urn:huawei:yang:huawei-mac-fwd";
  prefix mac-fwd;

  import huawei-extension {
    prefix ext;
  }
  import huawei-devm {
    prefix devm;
  }
  import huawei-vlan {
    prefix vlan;
  }
  import huawei-l2vpn {
    prefix l2vpn;
  }
  import huawei-bd {
    prefix bd;
  }
  import huawei-mac {
    prefix mac;
  }
  import huawei-ifm {
    prefix ifm;
  }
  import huawei-mac-flapping {
    prefix mac-flapping;
  }
  import huawei-pub-type {
    prefix pub-type;
  }
  import ietf-inet-types {
    prefix inet;
  }
  ext:task-name "mac";

  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Forwarding MAC service.";

  revision 2020-01-22 {
    description
      "Modify description.";
    reference "Huawei private.";
  }
  revision 2019-04-15 {
    description
      "Initial revision.";
    reference "Huawei private.";
  }

  typedef ncs_template_alarm-state {
    type string;
    description
      "MAC flapping alarm enable.";
  }

  typedef ncs_rpc_notif_alarm-state {
    type enumeration {
      enum "disable" {
        value 0;
        description
          "Disable the MAC flapping alarm function.";
      }
      enum "enable" {
        value 1;
        description
          "Enable the MAC flapping alarm function.";
      }
    }
    description
      "MAC flapping alarm enable.";
  }

  typedef live_ncs_alarm-state {
    type enumeration {
      enum "disable" {
        value 0;
        description
          "Disable the MAC flapping alarm function.";
      }
      enum "enable" {
        value 1;
        description
          "Enable the MAC flapping alarm function.";
      }
    }
    description
      "MAC flapping alarm enable.";
  }

  typedef alarm-state {
    type enumeration {
      enum "disable" {
        value 0;
        description
          "Disable the MAC flapping alarm function.";
      }
      enum "enable" {
        value 1;
        description
          "Enable the MAC flapping alarm function.";
      }
    }
    description
      "MAC flapping alarm enable.";
  }

  augment "/ncs:devices/ncs:device/ncs:rpc" {
    container rpc-reset-vsi-machop-all {
      tailf:ncs-device-type "netconf";
      tailf:display-when "not(../../ncs:module) or ../../ncs:module[ncs:name='huawei-mac-fwd']";
      tailf:action reset-vsi-machop-all {
        tailf:actionpoint ncsproxy {
          tailf:internal;
        }
        description
          "Reset MAC hop info.";
        ext:node-ref "/l2vpn:l2vpn/l2vpn:instances/l2vpn:instance/l2vpn:vpls/mac-fwd:mac-hops/mac-fwd:mac-hop";
      }
    }
  }
  augment "/ncs:devices/ncs:device-group/ncs:ned-id/ncs:rpc" {
    container rpc-reset-vsi-machop-all {
      tailf:ncs-device-type "netconf";
      tailf:display-when "/ncs:devices/ncs:device[ncs:name=current()/../../../ncs:member]/ncs:module[ncs:name='huawei-mac-fwd']";
      tailf:action reset-vsi-machop-all {
        tailf:actionpoint ncsproxy {
          tailf:internal;
        }
        description
          "Reset MAC hop info.";
        ext:node-ref "/l2vpn:l2vpn/l2vpn:instances/l2vpn:instance/l2vpn:vpls/mac-fwd:mac-hops/mac-fwd:mac-hop";
      }
    }
  }
  augment "/ncs:devices/ncs:device/ncs:rpc" {
    container rpc-reset-vsi-machop {
      tailf:ncs-device-type "netconf";
      tailf:display-when "not(../../ncs:module) or ../../ncs:module[ncs:name='huawei-mac-fwd']";
      tailf:action reset-vsi-machop {
        tailf:actionpoint ncsproxy {
          tailf:internal;
        }
        description
          "Reset MAC hop info by VSI name.";
        ext:node-ref "/l2vpn:l2vpn/l2vpn:instances/l2vpn:instance/l2vpn:vpls/mac-fwd:mac-hops/mac-fwd:mac-hop";
        input {
          leaf name {
            type string {
              length "1..31";
            }
            mandatory true;
            description
              "VSI name.";
          }
        }
      }
    }
  }
  augment "/ncs:devices/ncs:device-group/ncs:ned-id/ncs:rpc" {
    container rpc-reset-vsi-machop {
      tailf:ncs-device-type "netconf";
      tailf:display-when "/ncs:devices/ncs:device[ncs:name=current()/../../../ncs:member]/ncs:module[ncs:name='huawei-mac-fwd']";
      tailf:action reset-vsi-machop {
        tailf:actionpoint ncsproxy {
          tailf:internal;
        }
        description
          "Reset MAC hop info by VSI name.";
        ext:node-ref "/l2vpn:l2vpn/l2vpn:instances/l2vpn:instance/l2vpn:vpls/mac-fwd:mac-hops/mac-fwd:mac-hop";
        input {
          leaf name {
            type string {
              length "1..31";
            }
            mandatory true;
            description
              "VSI name.";
          }
        }
      }
    }
  }
  augment "/ncs:devices/ncs:device/ncs:rpc" {
    container rpc-reset-vlan-machop-all {
      tailf:ncs-device-type "netconf";
      tailf:display-when "not(../../ncs:module) or ../../ncs:module[ncs:name='huawei-mac-fwd']";
      tailf:action reset-vlan-machop-all {
        tailf:actionpoint ncsproxy {
          tailf:internal;
        }
        description
          "Reset MAC hop info.";
        ext:node-ref "/vlan:vlan/vlan:vlans/vlan:vlan/mac-fwd:mac-hops/mac-fwd:mac-hop";
      }
    }
  }
  augment "/ncs:devices/ncs:device-group/ncs:ned-id/ncs:rpc" {
    container rpc-reset-vlan-machop-all {
      tailf:ncs-device-type "netconf";
      tailf:display-when "/ncs:devices/ncs:device[ncs:name=current()/../../../ncs:member]/ncs:module[ncs:name='huawei-mac-fwd']";
      tailf:action reset-vlan-machop-all {
        tailf:actionpoint ncsproxy {
          tailf:internal;
        }
        description
          "Reset MAC hop info.";
        ext:node-ref "/vlan:vlan/vlan:vlans/vlan:vlan/mac-fwd:mac-hops/mac-fwd:mac-hop";
      }
    }
  }
  augment "/ncs:devices/ncs:device/ncs:rpc" {
    container rpc-reset-vlan-machop {
      tailf:ncs-device-type "netconf";
      tailf:display-when "not(../../ncs:module) or ../../ncs:module[ncs:name='huawei-mac-fwd']";
      tailf:action reset-vlan-machop {
        tailf:actionpoint ncsproxy {
          tailf:internal;
        }
        description
          "Reset MAC hop info by VLAN ID.";
        ext:node-ref "/vlan:vlan/vlan:vlans/vlan:vlan/mac-fwd:mac-hops/mac-fwd:mac-hop";
        input {
          leaf vlan-id {
            type uint32 {
              range "1..4094";
            }
            mandatory true;
            description
              "VLAN ID.";
          }
        }
      }
    }
  }
  augment "/ncs:devices/ncs:device-group/ncs:ned-id/ncs:rpc" {
    container rpc-reset-vlan-machop {
      tailf:ncs-device-type "netconf";
      tailf:display-when "/ncs:devices/ncs:device[ncs:name=current()/../../../ncs:member]/ncs:module[ncs:name='huawei-mac-fwd']";
      tailf:action reset-vlan-machop {
        tailf:actionpoint ncsproxy {
          tailf:internal;
        }
        description
          "Reset MAC hop info by VLAN ID.";
        ext:node-ref "/vlan:vlan/vlan:vlans/vlan:vlan/mac-fwd:mac-hops/mac-fwd:mac-hop";
        input {
          leaf vlan-id {
            type uint32 {
              range "1..4094";
            }
            mandatory true;
            description
              "VLAN ID.";
          }
        }
      }
    }
  }
  augment "/ncs:devices/ncs:device/ncs:rpc" {
    container rpc-reset-bd-machop-all {
      tailf:ncs-device-type "netconf";
      tailf:display-when "not(../../ncs:module) or ../../ncs:module[ncs:name='huawei-mac-fwd']";
      tailf:action reset-bd-machop-all {
        tailf:actionpoint ncsproxy {
          tailf:internal;
        }
        description
          "Reset MAC hop info.";
        ext:node-ref "/bd:bd/bd:instances/bd:instance/mac-fwd:mac-hops/mac-fwd:mac-hop";
      }
    }
  }
  augment "/ncs:devices/ncs:device-group/ncs:ned-id/ncs:rpc" {
    container rpc-reset-bd-machop-all {
      tailf:ncs-device-type "netconf";
      tailf:display-when "/ncs:devices/ncs:device[ncs:name=current()/../../../ncs:member]/ncs:module[ncs:name='huawei-mac-fwd']";
      tailf:action reset-bd-machop-all {
        tailf:actionpoint ncsproxy {
          tailf:internal;
        }
        description
          "Reset MAC hop info.";
        ext:node-ref "/bd:bd/bd:instances/bd:instance/mac-fwd:mac-hops/mac-fwd:mac-hop";
      }
    }
  }
  augment "/ncs:devices/ncs:device/ncs:rpc" {
    container rpc-reset-bd-machop {
      tailf:ncs-device-type "netconf";
      tailf:display-when "not(../../ncs:module) or ../../ncs:module[ncs:name='huawei-mac-fwd']";
      tailf:action reset-bd-machop {
        tailf:actionpoint ncsproxy {
          tailf:internal;
        }
        description
          "Reset MAC hop info by BD ID.";
        ext:node-ref "/bd:bd/bd:instances/bd:instance/mac-fwd:mac-hops/mac-fwd:mac-hop";
        input {
          leaf bd-id {
            type uint32 {
              range "1..16777215";
            }
            mandatory true;
            description
              "BD ID.";
          }
        }
      }
    }
  }
  augment "/ncs:devices/ncs:device-group/ncs:ned-id/ncs:rpc" {
    container rpc-reset-bd-machop {
      tailf:ncs-device-type "netconf";
      tailf:display-when "/ncs:devices/ncs:device[ncs:name=current()/../../../ncs:member]/ncs:module[ncs:name='huawei-mac-fwd']";
      tailf:action reset-bd-machop {
        tailf:actionpoint ncsproxy {
          tailf:internal;
        }
        description
          "Reset MAC hop info by BD ID.";
        ext:node-ref "/bd:bd/bd:instances/bd:instance/mac-fwd:mac-hops/mac-fwd:mac-hop";
        input {
          leaf bd-id {
            type uint32 {
              range "1..16777215";
            }
            mandatory true;
            description
              "BD ID.";
          }
        }
      }
    }
  }
  augment "/ncs:devices/ncs:template/ncs:ned-id/ncs:config/devm:devm/devm:lpu-boards/devm:lpu-board" {
    description
      "Slot MAC synchronize.";
    container mac-sync {
      description
        "Configure MAC synchronize.";
      leaf enable {
        type string;
        // NCS drop default statement
        description
          "Enable/disable MAC synchronize.";
      }
    }
  }
  augment "/ncs:devices/ncs:device/ncs:live-status/devm:devm/devm:lpu-boards/devm:lpu-board" {
    description
      "Slot MAC synchronize.";
    container mac-sync {
      tailf:ncs-device-type "netconf";
      tailf:display-when "not(../../../../../ncs:module) or ../../../../../ncs:module[ncs:name='huawei-mac-fwd'] or (../../../../../ncs:live-status-protocol[not(ncs:capability)]) or (../../../../../ncs:live-status-protocol/ncs:capability/ncs:module[.='huawei-mac-fwd'])";
      description
        "Configure MAC synchronize.";
      leaf enable {
        type boolean;
        // NCS drop default statement
        description
          "Enable/disable MAC synchronize.";
      }
    }
  }
  augment "/ncs:devices/ncs:device/ncs:config/devm:devm/devm:lpu-boards/devm:lpu-board" {
    description
      "Slot MAC synchronize.";
    container mac-sync {
      tailf:ncs-device-type "netconf";
      tailf:display-when "not(../../../../../ncs:module) or ../../../../../ncs:module[ncs:name='huawei-mac-fwd']";
      description
        "Configure MAC synchronize.";
      leaf enable {
        type boolean;
        default "false";
        description
          "Enable/disable MAC synchronize.";
      }
    }
  }
  augment "/ncs:devices/ncs:template/ncs:ned-id/ncs:config/bd:bd/bd:instances/bd:instance" {
    description
      "BD MAC hop info.";
    // NCS drop config false container 'mac-hops'
  }
  augment "/ncs:devices/ncs:device/ncs:live-status/bd:bd/bd:instances/bd:instance" {
    description
      "BD MAC hop info.";
    container mac-hops {
      tailf:ncs-device-type "netconf";
      tailf:display-when "not(../../../../../ncs:module) or ../../../../../ncs:module[ncs:name='huawei-mac-fwd'] or (../../../../../ncs:live-status-protocol[not(ncs:capability)]) or (../../../../../ncs:live-status-protocol/ncs:capability/ncs:module[.='huawei-mac-fwd'])";
      description
        "List of the bridge domain MAC hop info.";
      list mac-hop {
        key "mac-address interface-name peer-ip";
        description
          "Operational data of the bridge domain MAC hop info.";
        leaf mac-address {
          type pub-type:live_ncs_mac-address;
          description
            "MAC address.";
        }
        leaf interface-name {
          type leafref {
            path "/ncs:devices/ncs:device/ncs:live-status/ifm:ifm/ifm:interfaces/ifm:interface/ifm:name" {
              tailf:xpath-root 3;
            }
          }
          description
            "Interface name.";
        }
        leaf peer-ip {
          type inet:ipv4-address-no-zone;
          description
            "Remote peer IP information.";
        }
        leaf detect-time {
          type string {
            length "1..20";
          }
          description
            "Detect time.";
        }
      }
    }
  }
  augment "/ncs:devices/ncs:device/ncs:config/bd:bd/bd:instances/bd:instance" {
    description
      "BD MAC hop info.";
    // NCS drop config false container 'mac-hops'
  }
  augment "/ncs:devices/ncs:template/ncs:ned-id/ncs:config/vlan:vlan/vlan:vlans/vlan:vlan" {
    description
      "VLAN MAC hop info.";
    // NCS drop config false container 'mac-hops'
    // NCS drop config false container 'loop-detect-suppression'
  }
  augment "/ncs:devices/ncs:device/ncs:live-status/vlan:vlan/vlan:vlans/vlan:vlan" {
    description
      "VLAN MAC hop info.";
    container mac-hops {
      tailf:ncs-device-type "netconf";
      tailf:display-when "not(../../../../../ncs:module) or ../../../../../ncs:module[ncs:name='huawei-mac-fwd'] or (../../../../../ncs:live-status-protocol[not(ncs:capability)]) or (../../../../../ncs:live-status-protocol/ncs:capability/ncs:module[.='huawei-mac-fwd'])";
      description
        "List of the VLAN MAC hop info.";
      list mac-hop {
        key "mac-address interface-name";
        description
          "Operational data of VLAN MAC hop info.";
        leaf mac-address {
          type pub-type:live_ncs_mac-address;
          description
            "MAC address.";
        }
        leaf interface-name {
          type leafref {
            path "/ncs:devices/ncs:device/ncs:live-status/ifm:ifm/ifm:interfaces/ifm:interface/ifm:name" {
              tailf:xpath-root 3;
            }
          }
          description
            "Interface name.";
        }
        leaf detect-time {
          type string {
            length "1..20";
          }
          description
            "Detect time.";
        }
      }
    }
    container loop-detect-suppression {
      tailf:ncs-device-type "netconf";
      tailf:display-when "not(../../../../../ncs:module) or ../../../../../ncs:module[ncs:name='huawei-mac-fwd'] or (../../../../../ncs:live-status-protocol[not(ncs:capability)]) or (../../../../../ncs:live-status-protocol/ncs:capability/ncs:module[.='huawei-mac-fwd'])";
      description
        "Statistics of the VLAN suppression.";
      leaf interface-name {
        type leafref {
          path "/ncs:devices/ncs:device/ncs:live-status/ifm:ifm/ifm:interfaces/ifm:interface/ifm:name" {
            tailf:xpath-root 3;
          }
        }
        description
          "Interface name.";
      }
      leaf cir {
        type uint32;
        description
          "Committed information rate.";
      }
      leaf time {
        type string {
          length "1..20";
        }
        description
          "Suppression generation time.";
      }
      leaf state {
        type string {
          length "1..15";
        }
        description
          "Suppression state.";
      }
      leaf slot {
        type string {
          length "1..20";
        }
        description
          "Slot ID.";
      }
    }
  }
  augment "/ncs:devices/ncs:device/ncs:config/vlan:vlan/vlan:vlans/vlan:vlan" {
    description
      "VLAN MAC hop info.";
    // NCS drop config false container 'mac-hops'
    // NCS drop config false container 'loop-detect-suppression'
  }
  augment "/ncs:devices/ncs:template/ncs:ned-id/ncs:config/l2vpn:l2vpn/l2vpn:instances/l2vpn:instance/l2vpn:vpls" {
    description
      "VPLS MAC hop info.";
    // NCS drop config false container 'mac-hops'
    // NCS drop config false container 'loop-detect-suppression'
  }
  augment "/ncs:devices/ncs:device/ncs:live-status/l2vpn:l2vpn/l2vpn:instances/l2vpn:instance/l2vpn:vpls" {
    description
      "VPLS MAC hop info.";
    container mac-hops {
      tailf:ncs-device-type "netconf";
      tailf:display-when "not(../../../../../../ncs:module) or ../../../../../../ncs:module[ncs:name='huawei-mac-fwd'] or (../../../../../../ncs:live-status-protocol[not(ncs:capability)]) or (../../../../../../ncs:live-status-protocol/ncs:capability/ncs:module[.='huawei-mac-fwd'])";
      description
        "List of the VPLS MAC hop info.";
      list mac-hop {
        key "mac-address interface-name peer-ip";
        description
          "Operational data of VPLS MAC hop info.";
        leaf mac-address {
          type pub-type:live_ncs_mac-address;
          description
            "MAC address.";
        }
        leaf interface-name {
          type leafref {
            path "/ncs:devices/ncs:device/ncs:live-status/ifm:ifm/ifm:interfaces/ifm:interface/ifm:name" {
              tailf:xpath-root 3;
            }
          }
          description
            "Interface name.";
        }
        leaf peer-ip {
          type inet:ipv4-address-no-zone;
          description
            "Remote peer IP information.";
        }
        leaf pw-id {
          type uint32;
          description
            "Remote PW ID information.";
        }
        leaf detect-time {
          type string {
            length "1..20";
          }
          description
            "Detect time.";
        }
      }
    }
    container loop-detect-suppression {
      tailf:ncs-device-type "netconf";
      tailf:display-when "not(../../../../../../ncs:module) or ../../../../../../ncs:module[ncs:name='huawei-mac-fwd'] or (../../../../../../ncs:live-status-protocol[not(ncs:capability)]) or (../../../../../../ncs:live-status-protocol/ncs:capability/ncs:module[.='huawei-mac-fwd'])";
      description
        "Statistics of the VSI suppression.";
      leaf interface-name {
        type leafref {
          path "/ncs:devices/ncs:device/ncs:live-status/ifm:ifm/ifm:interfaces/ifm:interface/ifm:name" {
            tailf:xpath-root 3;
          }
        }
        description
          "Interface name.";
      }
      leaf peer-ip {
        type string {
          length "1..20";
        }
        description
          "Remote peer IP information.";
      }
      leaf vc-lable {
        type uint32;
        description
          "Remote PW ID information.";
      }
      leaf cir {
        type uint32;
        description
          "Committed information rate.";
      }
      leaf time {
        type string {
          length "1..20";
        }
        description
          "Suppression generation time.";
      }
      leaf state {
        type string {
          length "1..15";
        }
        description
          "Suppression state.";
      }
      leaf slot {
        type string {
          length "1..20";
        }
        description
          "Slot ID.";
      }
    }
  }
  augment "/ncs:devices/ncs:device/ncs:config/l2vpn:l2vpn/l2vpn:instances/l2vpn:instance/l2vpn:vpls" {
    description
      "VPLS MAC hop info.";
    // NCS drop config false container 'mac-hops'
    // NCS drop config false container 'loop-detect-suppression'
  }
  augment "/ncs:devices/ncs:template/ncs:ned-id/ncs:config/mac:mac/mac:global-attribute" {
    description
      "Forwarding MAC global attribute.";
    container mac-fwd {
      description
        "Configure forwarding MAC global attribute.";
      leaf mac-synchronize {
        type string;
        // NCS drop default statement
        description
          "Enable/disable global MAC address synchronization.";
      }
      leaf learn-first-packet {
        type string;
        // NCS drop default statement
        description
          "Enable/disable MAC limit since-first-packet.";
      }
    }
  }
  augment "/ncs:devices/ncs:device/ncs:live-status/mac:mac/mac:global-attribute" {
    description
      "Forwarding MAC global attribute.";
    container mac-fwd {
      tailf:ncs-device-type "netconf";
      tailf:display-when "not(../../../../ncs:module) or ../../../../ncs:module[ncs:name='huawei-mac-fwd'] or (../../../../ncs:live-status-protocol[not(ncs:capability)]) or (../../../../ncs:live-status-protocol/ncs:capability/ncs:module[.='huawei-mac-fwd'])";
      description
        "Configure forwarding MAC global attribute.";
      leaf mac-synchronize {
        type boolean;
        // NCS drop default statement
        description
          "Enable/disable global MAC address synchronization.";
      }
      leaf learn-first-packet {
        type boolean;
        // NCS drop default statement
        description
          "Enable/disable MAC limit since-first-packet.";
      }
    }
  }
  augment "/ncs:devices/ncs:device/ncs:config/mac:mac/mac:global-attribute" {
    description
      "Forwarding MAC global attribute.";
    container mac-fwd {
      tailf:ncs-device-type "netconf";
      tailf:display-when "not(../../../../ncs:module) or ../../../../ncs:module[ncs:name='huawei-mac-fwd']";
      description
        "Configure forwarding MAC global attribute.";
      leaf mac-synchronize {
        type boolean;
        default "false";
        description
          "Enable/disable global MAC address synchronization.";
      }
      leaf learn-first-packet {
        type boolean;
        default "false";
        description
          "Enable/disable MAC limit since-first-packet.";
      }
    }
  }
  augment "/ncs:devices/ncs:template/ncs:ned-id/ncs:config/mac-flapping:mac-flapping/mac-flapping:global-attribute" {
    description
      "MAC flapping alarm parameter.";
    container alarm-para {
      description
        "Configure MAC flapping alarm parameter.";
      leaf loop-times {
        type string;
        // NCS drop default statement
        description
          "Number of MAC address flappings.";
      }
      leaf detect-cycle {
        type string;
        units "s";
        // NCS drop default statement
        description
          "Detection cycle.";
      }
      leaf cycles {
        type string;
        // NCS drop default statement
        description
          "Number of cycles.";
      }
      leaf alarm-state {
        type ncs_template_alarm-state;
        // NCS drop default statement
        description
          "MAC flapping alarm status.";
      }
    }
  }
  augment "/ncs:devices/ncs:device/ncs:live-status/mac-flapping:mac-flapping/mac-flapping:global-attribute" {
    description
      "MAC flapping alarm parameter.";
    container alarm-para {
      tailf:ncs-device-type "netconf";
      tailf:display-when "not(../../../../ncs:module) or ../../../../ncs:module[ncs:name='huawei-mac-fwd'] or (../../../../ncs:live-status-protocol[not(ncs:capability)]) or (../../../../ncs:live-status-protocol/ncs:capability/ncs:module[.='huawei-mac-fwd'])";
      description
        "Configure MAC flapping alarm parameter.";
      leaf loop-times {
        type uint32 {
          range "3..1000";
        }
        // NCS drop default statement
        description
          "Number of MAC address flappings.";
      }
      leaf detect-cycle {
        type uint16 {
          range "10..30";
        }
        units "s";
        // NCS drop default statement
        description
          "Detection cycle.";
      }
      leaf cycles {
        type uint16 {
          range "3..15";
        }
        // NCS drop default statement
        description
          "Number of cycles.";
      }
      leaf alarm-state {
        type live_ncs_alarm-state;
        // NCS drop default statement
        description
          "MAC flapping alarm status.";
      }
    }
  }
  augment "/ncs:devices/ncs:device/ncs:config/mac-flapping:mac-flapping/mac-flapping:global-attribute" {
    description
      "MAC flapping alarm parameter.";
    container alarm-para {
      tailf:ncs-device-type "netconf";
      tailf:display-when "not(../../../../ncs:module) or ../../../../ncs:module[ncs:name='huawei-mac-fwd']";
      description
        "Configure MAC flapping alarm parameter.";
      leaf loop-times {
        type uint32 {
          range "3..1000";
        }
        default "3";
        description
          "Number of MAC address flappings.";
      }
      leaf detect-cycle {
        type uint16 {
          range "10..30";
        }
        units "s";
        default "10";
        description
          "Detection cycle.";
      }
      leaf cycles {
        type uint16 {
          range "3..15";
        }
        default "3";
        description
          "Number of cycles.";
      }
      leaf alarm-state {
        type alarm-state;
        default "enable";
        description
          "MAC flapping alarm status.";
      }
    }
  }
}
