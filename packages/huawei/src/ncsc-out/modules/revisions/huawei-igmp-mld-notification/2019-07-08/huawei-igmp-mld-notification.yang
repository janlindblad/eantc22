module huawei-igmp-mld-notification {
  // Generated by yanger -t ncs
  tailf:mount-id "huawei-nc-1.0:huawei-nc-1.0";
  tailf:ncs-device-type "netconf";

  yang-version 1;
  namespace "urn:huawei:yang:huawei-igmp-mld-notification";
  prefix igmp-mld-n;

  import huawei-pub-type {
    prefix pub-type;
  }
  import ietf-inet-types {
    prefix inet;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "The module defines notifications for IGMP and MLD.";

  revision 2019-07-08 {
    description
      "Initial revision.";
    reference "Huawei private.";
  }
  ext:task-name "igmp";

  typedef ncs_template_ip-addr-type {
    type string;
    description
      "Address family.";
  }

  typedef ncs_template_instance-name {
    type string;
    description
      "Instance name.";
  }

  typedef ncs_rpc_notif_ip-addr-type {
    type enumeration {
      enum "unknown" {
        value 0;
        description
          "Unknown type.";
      }
      enum "ipv4unicast" {
        value 1;
        description
          "IPv4 unicast.";
      }
      enum "ipv6unicast" {
        value 2;
        description
          "IPv6 unicast.";
      }
    }
    description
      "Address family.";
  }

  typedef ncs_rpc_notif_instance-name {
    type string {
      length "1..31";
    }
    description
      "Instance name.";
  }

  typedef live_ncs_ip-addr-type {
    type enumeration {
      enum "unknown" {
        value 0;
        description
          "Unknown type.";
      }
      enum "ipv4unicast" {
        value 1;
        description
          "IPv4 unicast.";
      }
      enum "ipv6unicast" {
        value 2;
        description
          "IPv6 unicast.";
      }
    }
    description
      "Address family.";
  }

  typedef live_ncs_instance-name {
    type string {
      length "1..31";
    }
    description
      "Instance name.";
  }

  typedef ip-addr-type {
    type enumeration {
      enum "unknown" {
        value 0;
        description
          "Unknown type.";
      }
      enum "ipv4unicast" {
        value 1;
        description
          "IPv4 unicast.";
      }
      enum "ipv6unicast" {
        value 2;
        description
          "IPv6 unicast.";
      }
    }
    description
      "Address family.";
  }

  typedef instance-name {
    type string {
      length "1..31";
    }
    description
      "Instance name.";
  }

  augment "/ncs:devices/ncs:device/ncs:notifications/ncs:received-notifications/ncs:notification/ncs:data" {
    container hw-igmp-mld-interface-threshold-exceed-clear {
      presence "";
      config false;
      description
        "The number of IGMP or MLD entries on the interface fell below the lower threshold.";
      leaf address-family {
        type igmp-mld-n:ncs_rpc_notif_ip-addr-type;
        description
          "Address family.";
      }
      leaf if-index {
        type uint32;
        description
          "Interface index.";
      }
      leaf current-count {
        type uint32;
        description
          "Number of created IGMP/MLD entries on the interface.";
      }
      leaf threshold-count {
        type uint32;
        description
          "Threshold at which the alarm is generated.";
      }
      leaf if-name {
        type pub-type:ncs_rpc_notif_if-name;
        description
          "Name of the interface.";
      }
      leaf instance-name {
        type igmp-mld-n:ncs_rpc_notif_instance-name;
        description
          "Instance of which the number of created (S, G) entries on the device reaches the specified limit.";
      }
    }
  }
  augment "/ncs:devices/ncs:device/ncs:notifications/ncs:received-notifications/ncs:notification/ncs:data" {
    container hw-igmp-mld-interface-threshold-exceed {
      presence "";
      config false;
      description
        "The number of IGMP or MLD entries on the interface reached the upper threshold.";
      leaf address-family {
        type igmp-mld-n:ncs_rpc_notif_ip-addr-type;
        description
          "Address family.";
      }
      leaf if-index {
        type uint32;
        description
          "Interface index.";
      }
      leaf current-count {
        type uint32;
        description
          "Number of created IGMP/MLD entries on the interface.";
      }
      leaf threshold-count {
        type uint32;
        description
          "Threshold at which the alarm is generated.";
      }
      leaf if-name {
        type pub-type:ncs_rpc_notif_if-name;
        description
          "Name of the interface.";
      }
      leaf instance-name {
        type igmp-mld-n:ncs_rpc_notif_instance-name;
        description
          "Instance of which the number of created (S, G) entries on the device reaches the specified limit.";
      }
    }
  }
  augment "/ncs:devices/ncs:device/ncs:notifications/ncs:received-notifications/ncs:notification/ncs:data" {
    container hw-igmp-mld-interface-limit-clear {
      presence "";
      config false;
      description
        "The new Report message can be processed because the number of IGMP or MLD group memberships on the interface falls below the upper limit.";
      leaf address-family {
        type igmp-mld-n:ncs_rpc_notif_ip-addr-type;
        description
          "Address family.";
      }
      leaf src-addr {
        type inet:ip-address-no-zone;
        description
          "Source address.";
      }
      leaf grp-addr {
        type inet:ip-address-no-zone;
        description
          "Group address.";
      }
      leaf if-index {
        type uint32;
        description
          "Interface index.";
      }
      leaf current-count {
        type uint32;
        description
          "Limit on the number of IGMP entries on the device.";
      }
      leaf if-name {
        type pub-type:ncs_rpc_notif_if-name;
        description
          "Name of the interface.";
      }
      leaf instance-name {
        type igmp-mld-n:ncs_rpc_notif_instance-name;
        description
          "Name of the instance where the number of IGMP entries on the interface exceeded the limit.";
      }
    }
  }
  augment "/ncs:devices/ncs:device/ncs:notifications/ncs:received-notifications/ncs:notification/ncs:data" {
    container hw-igmp-mld-interface-limit {
      presence "";
      config false;
      description
        "Membership report message is discarded because the interface-specific IGMP or MLD group membership limitation is exceeded.";
      leaf address-family {
        type igmp-mld-n:ncs_rpc_notif_ip-addr-type;
        description
          "Address family.";
      }
      leaf src-addr {
        type inet:ip-address-no-zone;
        description
          "Source address.";
      }
      leaf grp-addr {
        type inet:ip-address-no-zone;
        description
          "Group address.";
      }
      leaf if-index {
        type uint32;
        description
          "Interface index.";
      }
      leaf current-count {
        type uint32;
        description
          "Limit on the number of IGMP entries on the device.";
      }
      leaf if-name {
        type pub-type:ncs_rpc_notif_if-name;
        description
          "Name of the interface.";
      }
      leaf instance-name {
        type igmp-mld-n:ncs_rpc_notif_instance-name;
        description
          "Name of the instance where the number of IGMP entries on the interface exceeded the limit.";
      }
    }
  }
  augment "/ncs:devices/ncs:device/ncs:netconf-notifications/ncs:received-notifications/ncs:notification/ncs:data" {
    container hw-igmp-mld-interface-threshold-exceed-clear {
      presence "";
      config false;
      description
        "The number of IGMP or MLD entries on the interface fell below the lower threshold.";
      leaf address-family {
        type igmp-mld-n:ncs_rpc_notif_ip-addr-type;
        description
          "Address family.";
      }
      leaf if-index {
        type uint32;
        description
          "Interface index.";
      }
      leaf current-count {
        type uint32;
        description
          "Number of created IGMP/MLD entries on the interface.";
      }
      leaf threshold-count {
        type uint32;
        description
          "Threshold at which the alarm is generated.";
      }
      leaf if-name {
        type pub-type:ncs_rpc_notif_if-name;
        description
          "Name of the interface.";
      }
      leaf instance-name {
        type igmp-mld-n:ncs_rpc_notif_instance-name;
        description
          "Instance of which the number of created (S, G) entries on the device reaches the specified limit.";
      }
    }
  }
  augment "/ncs:devices/ncs:device/ncs:netconf-notifications/ncs:received-notifications/ncs:notification/ncs:data" {
    container hw-igmp-mld-interface-threshold-exceed {
      presence "";
      config false;
      description
        "The number of IGMP or MLD entries on the interface reached the upper threshold.";
      leaf address-family {
        type igmp-mld-n:ncs_rpc_notif_ip-addr-type;
        description
          "Address family.";
      }
      leaf if-index {
        type uint32;
        description
          "Interface index.";
      }
      leaf current-count {
        type uint32;
        description
          "Number of created IGMP/MLD entries on the interface.";
      }
      leaf threshold-count {
        type uint32;
        description
          "Threshold at which the alarm is generated.";
      }
      leaf if-name {
        type pub-type:ncs_rpc_notif_if-name;
        description
          "Name of the interface.";
      }
      leaf instance-name {
        type igmp-mld-n:ncs_rpc_notif_instance-name;
        description
          "Instance of which the number of created (S, G) entries on the device reaches the specified limit.";
      }
    }
  }
  augment "/ncs:devices/ncs:device/ncs:netconf-notifications/ncs:received-notifications/ncs:notification/ncs:data" {
    container hw-igmp-mld-interface-limit-clear {
      presence "";
      config false;
      description
        "The new Report message can be processed because the number of IGMP or MLD group memberships on the interface falls below the upper limit.";
      leaf address-family {
        type igmp-mld-n:ncs_rpc_notif_ip-addr-type;
        description
          "Address family.";
      }
      leaf src-addr {
        type inet:ip-address-no-zone;
        description
          "Source address.";
      }
      leaf grp-addr {
        type inet:ip-address-no-zone;
        description
          "Group address.";
      }
      leaf if-index {
        type uint32;
        description
          "Interface index.";
      }
      leaf current-count {
        type uint32;
        description
          "Limit on the number of IGMP entries on the device.";
      }
      leaf if-name {
        type pub-type:ncs_rpc_notif_if-name;
        description
          "Name of the interface.";
      }
      leaf instance-name {
        type igmp-mld-n:ncs_rpc_notif_instance-name;
        description
          "Name of the instance where the number of IGMP entries on the interface exceeded the limit.";
      }
    }
  }
  augment "/ncs:devices/ncs:device/ncs:netconf-notifications/ncs:received-notifications/ncs:notification/ncs:data" {
    container hw-igmp-mld-interface-limit {
      presence "";
      config false;
      description
        "Membership report message is discarded because the interface-specific IGMP or MLD group membership limitation is exceeded.";
      leaf address-family {
        type igmp-mld-n:ncs_rpc_notif_ip-addr-type;
        description
          "Address family.";
      }
      leaf src-addr {
        type inet:ip-address-no-zone;
        description
          "Source address.";
      }
      leaf grp-addr {
        type inet:ip-address-no-zone;
        description
          "Group address.";
      }
      leaf if-index {
        type uint32;
        description
          "Interface index.";
      }
      leaf current-count {
        type uint32;
        description
          "Limit on the number of IGMP entries on the device.";
      }
      leaf if-name {
        type pub-type:ncs_rpc_notif_if-name;
        description
          "Name of the interface.";
      }
      leaf instance-name {
        type igmp-mld-n:ncs_rpc_notif_instance-name;
        description
          "Name of the instance where the number of IGMP entries on the interface exceeded the limit.";
      }
    }
  }
}
