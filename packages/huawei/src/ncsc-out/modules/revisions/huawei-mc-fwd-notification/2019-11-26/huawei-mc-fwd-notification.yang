module huawei-mc-fwd-notification {
  // Generated by yanger -t ncs
  tailf:mount-id "huawei-nc-1.0:huawei-nc-1.0";
  tailf:ncs-device-type "netconf";

  yang-version 1;
  namespace "urn:huawei:yang:huawei-mc-fwd-notification";
  prefix multicast-forward-notification;

  import huawei-pub-type {
    prefix pub-type;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Notification of multicast-forward-notification.";

  revision 2019-11-26 {
    description
      "Init revision.";
    reference "Huawei private.";
  }
  ext:task-name "forwarding";

  augment "/ncs:devices/ncs:device/ncs:notifications/ncs:received-notifications/ncs:notification/ncs:data" {
    container nat-igmp-report-event {
      presence "";
      config false;
      description
        "Send IGMP package data.";
      leaf ifname {
        type pub-type:ncs_rpc_notif_if-name;
        description
          "Name of an interface.";
      }
      leaf igmp-package-data {
        type string {
          length "1..512";
        }
        description
          "Igmp package data.";
      }
    }
  }
  augment "/ncs:devices/ncs:device/ncs:netconf-notifications/ncs:received-notifications/ncs:notification/ncs:data" {
    container nat-igmp-report-event {
      presence "";
      config false;
      description
        "Send IGMP package data.";
      leaf ifname {
        type pub-type:ncs_rpc_notif_if-name;
        description
          "Name of an interface.";
      }
      leaf igmp-package-data {
        type string {
          length "1..512";
        }
        description
          "Igmp package data.";
      }
    }
  }
}
