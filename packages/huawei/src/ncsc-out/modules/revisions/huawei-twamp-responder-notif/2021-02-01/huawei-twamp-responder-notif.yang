module huawei-twamp-responder-notif {
  // Generated by yanger -t ncs
  tailf:mount-id "huawei-nc-1.0:huawei-nc-1.0";
  tailf:ncs-device-type "netconf";

  yang-version 1;
  namespace "urn:huawei:yang:huawei-twamp-responder-notif";
  prefix twamp-responder-notif;

  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Notification of twamp responder.";

  revision 2021-02-01 {
    description
      "Add standard TWAMP alarm.";
    reference "Huawei private.";
  }
  revision 2020-10-30 {
    description
      "Initial revision.";
    reference "Huawei private.";
  }
  ext:task-name "twamp";

  augment "/ncs:devices/ncs:device/ncs:notifications/ncs:received-notifications/ncs:notification/ncs:data" {
    container control-session-num-recovery {
      presence "";
      config false;
      description
        "The number of TWAMP control session is under device capability.";
    }
  }
  augment "/ncs:devices/ncs:device/ncs:notifications/ncs:received-notifications/ncs:notification/ncs:data" {
    container control-session-num-exceed {
      presence "";
      config false;
      description
        "The number of TWAMP control session is out of device capability.";
    }
  }
  augment "/ncs:devices/ncs:device/ncs:notifications/ncs:received-notifications/ncs:notification/ncs:data" {
    container responder-session-num-recovery {
      presence "";
      config false;
      description
        "The number of TWAMP responder session is under device capability.";
    }
  }
  augment "/ncs:devices/ncs:device/ncs:notifications/ncs:received-notifications/ncs:notification/ncs:data" {
    container responder-session-num-exceed {
      presence "";
      config false;
      description
        "The number of TWAMP responder session is out of device capability.";
    }
  }
  augment "/ncs:devices/ncs:device/ncs:netconf-notifications/ncs:received-notifications/ncs:notification/ncs:data" {
    container control-session-num-recovery {
      presence "";
      config false;
      description
        "The number of TWAMP control session is under device capability.";
    }
  }
  augment "/ncs:devices/ncs:device/ncs:netconf-notifications/ncs:received-notifications/ncs:notification/ncs:data" {
    container control-session-num-exceed {
      presence "";
      config false;
      description
        "The number of TWAMP control session is out of device capability.";
    }
  }
  augment "/ncs:devices/ncs:device/ncs:netconf-notifications/ncs:received-notifications/ncs:notification/ncs:data" {
    container responder-session-num-recovery {
      presence "";
      config false;
      description
        "The number of TWAMP responder session is under device capability.";
    }
  }
  augment "/ncs:devices/ncs:device/ncs:netconf-notifications/ncs:received-notifications/ncs:notification/ncs:data" {
    container responder-session-num-exceed {
      presence "";
      config false;
      description
        "The number of TWAMP responder session is out of device capability.";
    }
  }
}
