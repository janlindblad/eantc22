module huawei-said-frame {
  // Generated by yanger -t ncs
  tailf:mount-id "huawei-nc-1.0:huawei-nc-1.0";
  tailf:ncs-device-type "netconf";

  yang-version 1;
  namespace "urn:huawei:yang:huawei-said-frame";
  prefix sf;

  import huawei-extension {
    prefix ext;
  }
  import huawei-devm {
    prefix devm;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com
    ";
  description
    "SAID frame configurations.";

  revision 2020-03-10 {
    description
      "Init revision.";
    reference "Huawei private.";
  }
  ext:task-name "saidframe";

  typedef ncs_template_state-type {
    type string;
    description
      "SAID node running states.";
  }

  typedef ncs_template_operation-type {
    type string;
    description
      "SAID node operating types.";
  }

  typedef ncs_template_said-name-lpu {
    type string;
    description
      "SAID node name in LPU.";
  }

  typedef ncs_template_said-name-mpu {
    type string;
    description
      "SAID node name in MPU.";
  }

  typedef ncs_template_disable-flag {
    type string;
    description
      "SAID node disable flag.";
  }

  typedef ncs_template_enable-flag {
    type string;
    description
      "SAID node enable flag.";
  }

  typedef ncs_rpc_notif_state-type {
    type enumeration {
      enum "init" {
        value 0;
        description
          "Init state.";
      }
      enum "detecting" {
        value 1;
        description
          "Detecting state.";
      }
      enum "diagnosing" {
        value 2;
        description
          "Diagnosing state.";
      }
      enum "invalid-diagnose" {
        value 3;
        description
          "Invalid diagnose state.";
      }
      enum "recovering" {
        value 4;
        description
          "Recovering state.";
      }
      enum "judging" {
        value 5;
        description
          "Judging state.";
      }
      enum "exp-judging" {
        value 6;
        description
          "Exception judging state.";
      }
    }
    description
      "SAID node running states.";
  }

  typedef ncs_rpc_notif_operation-type {
    type enumeration {
      enum "common" {
        value 0;
        description
          "Common operation type.";
      }
      enum "prevention" {
        value 1;
        description
          "Prevented operation type.";
      }
    }
    description
      "SAID node operating types.";
  }

  typedef ncs_rpc_notif_said-name-lpu {
    type enumeration {
      enum "ping" {
        value 2;
        description
          "SAID ping node.";
      }
      enum "ping-trunk" {
        value 3;
        description
          "SAID ping trunk node.";
      }
      enum "traffic-fail" {
        value 4;
        description
          "SAID traffic fail node.";
      }
      enum "seu-igp" {
        value 5;
        description
          "SAID seuigp node.";
      }
      enum "aaa" {
        value 8;
        description
          "SAID aaa node.";
      }
      enum "seu-trunk" {
        value 20;
        description
          "SAID seutrunk node.";
      }
      enum "seuloop" {
        value 22;
        description
          "SAID seuloop node.";
      }
      enum "reset-board" {
        value 25;
        description
          "SAID reset board node.";
      }
      enum "cfc" {
        value 26;
        description
          "SAID cfc node.";
      }
      enum "ipnice" {
        value 28;
        description
          "SAID ipnice node.";
      }
    }
    description
      "SAID node name in LPU.";
  }

  typedef ncs_rpc_notif_said-name-mpu {
    type enumeration {
      enum "ping" {
        value 2;
        description
          "SAID ping node.";
      }
      enum "ping-trunk" {
        value 3;
        description
          "SAID ping trunk node.";
      }
      enum "traffic-fail" {
        value 4;
        description
          "SAID traffic fail node.";
      }
      enum "seu-igp" {
        value 5;
        description
          "SAID seuigp node.";
      }
      enum "aaa" {
        value 8;
        description
          "SAID aaa node.";
      }
      enum "seu-trunk" {
        value 20;
        description
          "SAID seutrunk node.";
      }
      enum "seuloop" {
        value 22;
        description
          "SAID seuloop node.";
      }
      enum "reset-board" {
        value 25;
        description
          "SAID reset board node.";
      }
      enum "cfc" {
        value 26;
        description
          "SAID cfc node.";
      }
      enum "ipnice" {
        value 28;
        description
          "SAID ipnice node.";
      }
    }
    description
      "SAID node name in MPU.";
  }

  typedef ncs_rpc_notif_disable-flag {
    type enumeration {
      enum "undodisable" {
        value 0;
        description
          "SAID node is enable.";
      }
      enum "disable" {
        value 1;
        description
          "SAID node is disable.";
      }
    }
    description
      "SAID node disable flag.";
  }

  typedef ncs_rpc_notif_enable-flag {
    type enumeration {
      enum "disable" {
        value 0;
        description
          "SAID node is disable.";
      }
      enum "enable" {
        value 1;
        description
          "SAID node is enable.";
      }
    }
    description
      "SAID node enable flag.";
  }

  typedef live_ncs_state-type {
    type enumeration {
      enum "init" {
        value 0;
        description
          "Init state.";
      }
      enum "detecting" {
        value 1;
        description
          "Detecting state.";
      }
      enum "diagnosing" {
        value 2;
        description
          "Diagnosing state.";
      }
      enum "invalid-diagnose" {
        value 3;
        description
          "Invalid diagnose state.";
      }
      enum "recovering" {
        value 4;
        description
          "Recovering state.";
      }
      enum "judging" {
        value 5;
        description
          "Judging state.";
      }
      enum "exp-judging" {
        value 6;
        description
          "Exception judging state.";
      }
    }
    description
      "SAID node running states.";
  }

  typedef live_ncs_operation-type {
    type enumeration {
      enum "common" {
        value 0;
        description
          "Common operation type.";
      }
      enum "prevention" {
        value 1;
        description
          "Prevented operation type.";
      }
    }
    description
      "SAID node operating types.";
  }

  typedef live_ncs_said-name-lpu {
    type enumeration {
      enum "ping" {
        value 2;
        description
          "SAID ping node.";
      }
      enum "ping-trunk" {
        value 3;
        description
          "SAID ping trunk node.";
      }
      enum "traffic-fail" {
        value 4;
        description
          "SAID traffic fail node.";
      }
      enum "seu-igp" {
        value 5;
        description
          "SAID seuigp node.";
      }
      enum "aaa" {
        value 8;
        description
          "SAID aaa node.";
      }
      enum "seu-trunk" {
        value 20;
        description
          "SAID seutrunk node.";
      }
      enum "seuloop" {
        value 22;
        description
          "SAID seuloop node.";
      }
      enum "reset-board" {
        value 25;
        description
          "SAID reset board node.";
      }
      enum "cfc" {
        value 26;
        description
          "SAID cfc node.";
      }
      enum "ipnice" {
        value 28;
        description
          "SAID ipnice node.";
      }
    }
    description
      "SAID node name in LPU.";
  }

  typedef live_ncs_said-name-mpu {
    type enumeration {
      enum "ping" {
        value 2;
        description
          "SAID ping node.";
      }
      enum "ping-trunk" {
        value 3;
        description
          "SAID ping trunk node.";
      }
      enum "traffic-fail" {
        value 4;
        description
          "SAID traffic fail node.";
      }
      enum "seu-igp" {
        value 5;
        description
          "SAID seuigp node.";
      }
      enum "aaa" {
        value 8;
        description
          "SAID aaa node.";
      }
      enum "seu-trunk" {
        value 20;
        description
          "SAID seutrunk node.";
      }
      enum "seuloop" {
        value 22;
        description
          "SAID seuloop node.";
      }
      enum "reset-board" {
        value 25;
        description
          "SAID reset board node.";
      }
      enum "cfc" {
        value 26;
        description
          "SAID cfc node.";
      }
      enum "ipnice" {
        value 28;
        description
          "SAID ipnice node.";
      }
    }
    description
      "SAID node name in MPU.";
  }

  typedef live_ncs_disable-flag {
    type enumeration {
      enum "undodisable" {
        value 0;
        description
          "SAID node is enable.";
      }
      enum "disable" {
        value 1;
        description
          "SAID node is disable.";
      }
    }
    description
      "SAID node disable flag.";
  }

  typedef live_ncs_enable-flag {
    type enumeration {
      enum "disable" {
        value 0;
        description
          "SAID node is disable.";
      }
      enum "enable" {
        value 1;
        description
          "SAID node is enable.";
      }
    }
    description
      "SAID node enable flag.";
  }

  typedef state-type {
    type enumeration {
      enum "init" {
        value 0;
        description
          "Init state.";
      }
      enum "detecting" {
        value 1;
        description
          "Detecting state.";
      }
      enum "diagnosing" {
        value 2;
        description
          "Diagnosing state.";
      }
      enum "invalid-diagnose" {
        value 3;
        description
          "Invalid diagnose state.";
      }
      enum "recovering" {
        value 4;
        description
          "Recovering state.";
      }
      enum "judging" {
        value 5;
        description
          "Judging state.";
      }
      enum "exp-judging" {
        value 6;
        description
          "Exception judging state.";
      }
    }
    description
      "SAID node running states.";
  }

  typedef operation-type {
    type enumeration {
      enum "common" {
        value 0;
        description
          "Common operation type.";
      }
      enum "prevention" {
        value 1;
        description
          "Prevented operation type.";
      }
    }
    description
      "SAID node operating types.";
  }

  typedef said-name-lpu {
    type enumeration {
      enum "ping" {
        value 2;
        description
          "SAID ping node.";
      }
      enum "ping-trunk" {
        value 3;
        description
          "SAID ping trunk node.";
      }
      enum "traffic-fail" {
        value 4;
        description
          "SAID traffic fail node.";
      }
      enum "seu-igp" {
        value 5;
        description
          "SAID seuigp node.";
      }
      enum "aaa" {
        value 8;
        description
          "SAID aaa node.";
      }
      enum "seu-trunk" {
        value 20;
        description
          "SAID seutrunk node.";
      }
      enum "seuloop" {
        value 22;
        description
          "SAID seuloop node.";
      }
      enum "reset-board" {
        value 25;
        description
          "SAID reset board node.";
      }
      enum "cfc" {
        value 26;
        description
          "SAID cfc node.";
      }
      enum "ipnice" {
        value 28;
        description
          "SAID ipnice node.";
      }
    }
    description
      "SAID node name in LPU.";
  }

  typedef said-name-mpu {
    type enumeration {
      enum "ping" {
        value 2;
        description
          "SAID ping node.";
      }
      enum "ping-trunk" {
        value 3;
        description
          "SAID ping trunk node.";
      }
      enum "traffic-fail" {
        value 4;
        description
          "SAID traffic fail node.";
      }
      enum "seu-igp" {
        value 5;
        description
          "SAID seuigp node.";
      }
      enum "aaa" {
        value 8;
        description
          "SAID aaa node.";
      }
      enum "seu-trunk" {
        value 20;
        description
          "SAID seutrunk node.";
      }
      enum "seuloop" {
        value 22;
        description
          "SAID seuloop node.";
      }
      enum "reset-board" {
        value 25;
        description
          "SAID reset board node.";
      }
      enum "cfc" {
        value 26;
        description
          "SAID cfc node.";
      }
      enum "ipnice" {
        value 28;
        description
          "SAID ipnice node.";
      }
    }
    description
      "SAID node name in MPU.";
  }

  typedef disable-flag {
    type enumeration {
      enum "undodisable" {
        value 0;
        description
          "SAID node is enable.";
      }
      enum "disable" {
        value 1;
        description
          "SAID node is disable.";
      }
    }
    description
      "SAID node disable flag.";
  }

  typedef enable-flag {
    type enumeration {
      enum "disable" {
        value 0;
        description
          "SAID node is disable.";
      }
      enum "enable" {
        value 1;
        description
          "SAID node is enable.";
      }
    }
    description
      "SAID node enable flag.";
  }

  augment "/ncs:devices/ncs:device/ncs:config" {
    container said-frame {
      tailf:ncs-device-type "netconf";
      tailf:display-when "not(../../ncs:module) or ../../ncs:module[ncs:name='huawei-said-frame']";
      description
        "SAID frame.";
      container global-switch {
        description
          "Configure SAID global switch.";
        leaf disable {
          type disable-flag;
          default "undodisable";
          description
            "SAID global disable flag.";
        }
      }
      // NCS drop config false container 'lpu-nodes'
      container lpunodecfgs {
        description
          "List of SAID node configurations in all LPUs.";
        list lpunodecfg {
          key "said-name slot-id";
          description
            "Configure SAID node configurations in a LPU.";
          leaf said-name {
            type said-name-lpu;
            description
              "SAID node name.";
          }
          leaf slot-id {
            type string {
              length "1..16";
            }
            description
              "Indicates the slot ID of a board.";
          }
          leaf disable {
            type disable-flag;
            mandatory true;
            description
              "Disable flag.";
          }
        }
      }
      // NCS drop config false container 'mpu-nodes'
      container mpunodecfgs {
        description
          "List of SAID node configurations in all MPUs.";
        list mpunodecfg {
          key "said-name";
          description
            "Configure SAID node configurations in a MPU.";
          leaf said-name {
            type said-name-mpu;
            description
              "SAID node name.";
          }
          leaf disable {
            type disable-flag;
            mandatory true;
            description
              "Disable flag.";
          }
        }
      }
    }
  }
  augment "/ncs:devices/ncs:device/ncs:live-status" {
    container said-frame {
      tailf:ncs-device-type "netconf";
      tailf:display-when "not(../../ncs:module) or ../../ncs:module[ncs:name='huawei-said-frame'] or (../../ncs:live-status-protocol[not(ncs:capability)]) or (../../ncs:live-status-protocol/ncs:capability/ncs:module[.='huawei-said-frame'])";
      description
        "SAID frame.";
      container global-switch {
        description
          "Configure SAID global switch.";
        leaf disable {
          type live_ncs_disable-flag;
          // NCS drop default statement
          description
            "SAID global disable flag.";
        }
      }
      container lpu-nodes {
        description
          "List of SAID node information in all LPUs.";
        list lpu-node {
          key "said-name slot-id";
          description
            "Statistics of SAID node information in a LPU.";
          leaf said-name {
            type live_ncs_said-name-lpu;
            description
              "SAID node name.";
          }
          leaf slot-id {
            type string {
              length "1..16";
            }
            description
              "Indicates the slot ID of a board.";
          }
          leaf operate {
            type live_ncs_operation-type;
            description
              "SAID node operating type.";
          }
          leaf state {
            type live_ncs_state-type;
            description
              "SAID node running state.";
          }
          leaf cycle {
            type uint32;
            description
              "Detecting cycle.";
          }
          leaf enable {
            type live_ncs_enable-flag;
            description
              "SAID node enable flag.";
          }
        }
      }
      container lpunodecfgs {
        description
          "List of SAID node configurations in all LPUs.";
        list lpunodecfg {
          key "said-name slot-id";
          description
            "Configure SAID node configurations in a LPU.";
          leaf said-name {
            type live_ncs_said-name-lpu;
            description
              "SAID node name.";
          }
          leaf slot-id {
            type string {
              length "1..16";
            }
            description
              "Indicates the slot ID of a board.";
          }
          leaf disable {
            type live_ncs_disable-flag;
            // NCS drop mandatory statement
            description
              "Disable flag.";
          }
        }
      }
      container mpu-nodes {
        description
          "List of SAID node information in all MPUs.";
        list mpu-node {
          key "said-name";
          description
            "Statistics of SAID node information in a MPU.";
          leaf said-name {
            type live_ncs_said-name-mpu;
            description
              "SAID node name.";
          }
          leaf slot-id {
            type leafref {
              path "/ncs:devices/ncs:device/ncs:live-status/devm:devm/devm:mpu-boards/devm:mpu-board/devm:position" {
                tailf:xpath-root 3;
              }
            }
            description
              "Slot ID.";
          }
          leaf operate {
            type live_ncs_operation-type;
            description
              "SAID node operating type.";
          }
          leaf state {
            type live_ncs_state-type;
            description
              "SAID node running state.";
          }
          leaf cycle {
            type uint32;
            description
              "Detecting cycle.";
          }
          leaf enable {
            type live_ncs_enable-flag;
            description
              "SAID node enable flag.";
          }
        }
      }
      container mpunodecfgs {
        description
          "List of SAID node configurations in all MPUs.";
        list mpunodecfg {
          key "said-name";
          description
            "Configure SAID node configurations in a MPU.";
          leaf said-name {
            type live_ncs_said-name-mpu;
            description
              "SAID node name.";
          }
          leaf disable {
            type live_ncs_disable-flag;
            // NCS drop mandatory statement
            description
              "Disable flag.";
          }
        }
      }
    }
  }
  augment "/ncs:devices/ncs:template/ncs:ned-id/ncs:config" {
    container said-frame {
      description
        "SAID frame.";
      container global-switch {
        description
          "Configure SAID global switch.";
        leaf disable {
          type ncs_template_disable-flag;
          // NCS drop default statement
          description
            "SAID global disable flag.";
        }
      }
      // NCS drop config false container 'lpu-nodes'
      container lpunodecfgs {
        description
          "List of SAID node configurations in all LPUs.";
        list lpunodecfg {
          // NCS patched for predictable order
          ordered-by user;
          key "said-name slot-id";
          description
            "Configure SAID node configurations in a LPU.";
          leaf said-name {
            type ncs_template_said-name-lpu;
            description
              "SAID node name.";
          }
          leaf slot-id {
            type string;
            description
              "Indicates the slot ID of a board.";
          }
          leaf disable {
            type ncs_template_disable-flag;
            // NCS drop mandatory statement
            description
              "Disable flag.";
          }
        }
      }
      // NCS drop config false container 'mpu-nodes'
      container mpunodecfgs {
        description
          "List of SAID node configurations in all MPUs.";
        list mpunodecfg {
          // NCS patched for predictable order
          ordered-by user;
          key "said-name";
          description
            "Configure SAID node configurations in a MPU.";
          leaf said-name {
            type ncs_template_said-name-mpu;
            description
              "SAID node name.";
          }
          leaf disable {
            type ncs_template_disable-flag;
            // NCS drop mandatory statement
            description
              "Disable flag.";
          }
        }
      }
    }
  }
}
