module huawei-rpki {
  // Generated by yanger -t ncs
  tailf:mount-id "huawei-nc-1.0:huawei-nc-1.0";
  tailf:ncs-device-type "netconf";

  yang-version 1;
  namespace "urn:huawei:yang:huawei-rpki";
  prefix rpki;

  import huawei-network-instance {
    prefix ni;
  }
  import huawei-extension {
    prefix ext;
  }
  import ietf-inet-types {
    prefix inet;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Resource Public Key Infrastructure.";

  revision 2020-12-09 {
    description
      "Initial revision.";
    reference "Huawei private.";
  }
  ext:task-name "rpki";

  augment "/ncs:devices/ncs:device/ncs:config" {
    container rpki {
      tailf:ncs-device-type "netconf";
      tailf:display-when "not(../../ncs:module) or ../../ncs:module[ncs:name='huawei-rpki']";
      description
        "Configure RPKI.";
      container rpki {
        presence "Enable RPKI.";
        description
          "Enable/disable RPKI globally.";
      }
    }
  }
  augment "/ncs:devices/ncs:device/ncs:live-status" {
    container rpki {
      tailf:ncs-device-type "netconf";
      tailf:display-when "not(../../ncs:module) or ../../ncs:module[ncs:name='huawei-rpki'] or (../../ncs:live-status-protocol[not(ncs:capability)]) or (../../ncs:live-status-protocol/ncs:capability/ncs:module[.='huawei-rpki'])";
      description
        "Configure RPKI.";
      container rpki {
        presence "Enable RPKI.";
        description
          "Enable/disable RPKI globally.";
      }
    }
  }
  augment "/ncs:devices/ncs:template/ncs:ned-id/ncs:config" {
    container rpki {
      description
        "Configure RPKI.";
      container rpki {
        presence "Enable RPKI.";
        description
          "Enable/disable RPKI globally.";
      }
    }
  }
  augment "/ncs:devices/ncs:template/ncs:ned-id/ncs:config/ni:network-instance/ni:instances/ni:instance" {
    description
      "Rpki session configuration.";
    container rpki {
      // NCS drop when statement
      description
        "Configure RPKI.";
      container sessions {
        description
          "List of rpki session.";
        list session {
          // NCS patched for predictable order
          ordered-by user;
          // NCS drop must statement
          key "remote-address";
          // NCS drop max-elements statement
          description
            "Configure rpki session.";
          leaf remote-address {
            type string;
            description
              "Specifies the address of a Resource Public Key Infrastructure (RPKI) server to establish a TCP connection between the router and the RPKI server.";
          }
          leaf tcp-port {
            type string;
            description
              "TCP connection port.";
          }
          leaf aging-time {
            type string;
            units "s";
            // NCS drop default statement
            description
              "Aging time.";
          }
          leaf refresh-time {
            type string;
            units "s";
            // NCS drop default statement
            description
              "Refresh time.";
          }
        }
      }
    }
  }
  augment "/ncs:devices/ncs:device/ncs:live-status/ni:network-instance/ni:instances/ni:instance" {
    description
      "Rpki session configuration.";
    container rpki {
      tailf:ncs-device-type "netconf";
      tailf:display-when "not(../../../../../ncs:module) or ../../../../../ncs:module[ncs:name='huawei-rpki'] or (../../../../../ncs:live-status-protocol[not(ncs:capability)]) or (../../../../../ncs:live-status-protocol/ncs:capability/ncs:module[.='huawei-rpki'])";
      // NCS drop when statement
      description
        "Configure RPKI.";
      container sessions {
        description
          "List of rpki session.";
        list session {
          // NCS drop must statement
          key "remote-address";
          // NCS drop max-elements statement
          description
            "Configure rpki session.";
          leaf remote-address {
            type inet:ip-address-no-zone;
            description
              "Specifies the address of a Resource Public Key Infrastructure (RPKI) server to establish a TCP connection between the router and the RPKI server.";
          }
          leaf tcp-port {
            type uint16 {
              range "1..65535";
            }
            description
              "TCP connection port.";
          }
          leaf aging-time {
            type uint32 {
              range "60..604800";
            }
            units "s";
            // NCS drop default statement
            description
              "Aging time.";
          }
          leaf refresh-time {
            type uint32 {
              range "10..3600";
            }
            units "s";
            // NCS drop default statement
            description
              "Refresh time.";
          }
        }
      }
    }
  }
  augment "/ncs:devices/ncs:device/ncs:config/ni:network-instance/ni:instances/ni:instance" {
    description
      "Rpki session configuration.";
    container rpki {
      tailf:ncs-device-type "netconf";
      tailf:display-when "not(../../../../../ncs:module) or ../../../../../ncs:module[ncs:name='huawei-rpki']";
      when '/rpki:rpki/rpki:rpki' {
        tailf:xpath-root 3;
      }
      description
        "Configure RPKI.";
      container sessions {
        description
          "List of rpki session.";
        list session {
          must 'aging-time>=2*(refresh-time)' {
            tailf:xpath-root 3;
          }
          key "remote-address";
          max-elements 2;
          description
            "Configure rpki session.";
          leaf remote-address {
            type inet:ip-address-no-zone;
            description
              "Specifies the address of a Resource Public Key Infrastructure (RPKI) server to establish a TCP connection between the router and the RPKI server.";
          }
          leaf tcp-port {
            type uint16 {
              range "1..65535";
            }
            description
              "TCP connection port.";
          }
          leaf aging-time {
            type uint32 {
              range "60..604800";
            }
            units "s";
            default "3600";
            description
              "Aging time.";
          }
          leaf refresh-time {
            type uint32 {
              range "10..3600";
            }
            units "s";
            default "1800";
            description
              "Refresh time.";
          }
        }
      }
    }
  }
}
