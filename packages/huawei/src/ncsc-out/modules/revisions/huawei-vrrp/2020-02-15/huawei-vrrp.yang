module huawei-vrrp {
  // Generated by yanger -t ncs
  tailf:mount-id "huawei-nc-1.0:huawei-nc-1.0";
  tailf:ncs-device-type "netconf";

  namespace "urn:huawei:yang:huawei-vrrp";
  prefix vrrp;

  import huawei-ifm {
    prefix ifm;
  }
  import ietf-inet-types {
    prefix inet;
  }
  import huawei-pub-type {
    prefix pub-type;
  }
  import huawei-extension {
    prefix ext;
  }
  import huawei-network-instance {
    prefix ni;
  }
  import huawei-bfd {
    prefix bfd;
  }
  import ietf-yang-types {
    prefix yang;
  }
  import huawei-monitor-group {
    prefix monitor-group;
  }
  import huawei-ip {
    prefix ip;
  }
  import huawei-nqa {
    prefix nqa;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Global VRRP configuration.";

  revision 2020-02-15 {
    description
      "Modify description.";
    reference "Huawei private.";
  }
  revision 2019-10-27 {
    description
      "Initial revision.";
    reference "Huawei private.";
  }
  ext:task-name "vrrp";

  typedef ncs_template_vrrp-type {
    type string;
    description
      "VRRP group type.";
  }

  typedef ncs_template_vrrp-bfd-type {
    type string;
    description
      "The type of VRRP track BFD.";
  }

  typedef ncs_template_vrrp-track-mode {
    type string;
    description
      "VRRP track mode is like increase/reduce.";
  }

  typedef ncs_template_vrrp-track-bfd-state {
    type string;
    description
      "VRRP track bfd state is like down/up/admin-down/unknow.";
  }

  typedef ncs_template_vrrp-oper-state {
    type string;
    description
      "VRRP operation state is like initialize/backup/master.";
  }

  typedef ncs_template_vrrp6cksm-mode {
    type string;
    description
      "VRRP6 cksm-mode is like include-pseudo-header/exclude-pseudo-header.";
  }

  typedef ncs_template_vrrpauthen-mode {
    type string;
    description
      "VRRP authen-mode is like none/simple/md5.";
  }

  typedef ncs_template_vrrp-v3-sendmode {
    type string;
    description
      "VRRP V3 send mode is like v2-only/v2v3-both/v3-only.";
  }

  typedef ncs_template_vrrp-version {
    type string;
    description
      "VRRP version is like v2/v3.";
  }

  typedef ncs_template_vrrptrack-mode {
    type string;
    description
      "VRRP track mode is like increase/reduce.";
  }

  typedef ncs_template_mtgrptrack-mode {
    type string;
    description
      "Monitor-group track mode is like normal/link.";
  }

  typedef ncs_template_vgmp-type {
    type string;
    description
      "The configuration of VRRP.";
  }

  typedef ncs_rpc_notif_vrrp-type {
    type enumeration {
      enum "normal" {
        value 0;
        description
          "Normal VRRP.";
      }
      enum "admin" {
        value 1;
        description
          "Admin VRRP.";
      }
      enum "member" {
        value 2;
        description
          "Member VRRP.";
      }
      enum "lbrg" {
        value 3;
        description
          "Load-balance redundancy group VRRP.";
      }
      enum "lbrg-mem" {
        value 4;
        description
          "Load-balance redundancy group member VRRP.";
      }
      enum "mem-lbrg" {
        value 5;
        description
          "Member of load-balance redundancy group VRRP.";
      }
      enum "mem-lbrg-mem" {
        value 6;
        description
          "Member of load-balance redundancy group Member VRRP.";
      }
      enum "unicast" {
        value 7;
        description
          "Unicast VRRP.";
      }
    }
    description
      "VRRP group type.";
  }

  typedef ncs_rpc_notif_vrrp-bfd-type {
    type enumeration {
      enum "normal" {
        value 0;
        description
          "Normal BFD session.";
      }
      enum "link" {
        value 1;
        description
          "Link BFD session.";
      }
      enum "peer" {
        value 2;
        description
          "Peer BFD session.";
      }
    }
    description
      "The type of VRRP track BFD.";
  }

  typedef ncs_rpc_notif_vrrp-track-mode {
    type enumeration {
      enum "increase" {
        value 0;
        description
          "Increase priority.";
      }
      enum "reduce" {
        value 1;
        description
          "Reduce priority.";
      }
    }
    description
      "VRRP track mode is like increase/reduce.";
  }

  typedef ncs_rpc_notif_vrrp-track-bfd-state {
    type enumeration {
      enum "down" {
        value 0;
        description
          "BFD state down.";
      }
      enum "up" {
        value 1;
        description
          "BFD state up.";
      }
      enum "admin-down" {
        value 2;
        description
          "BFD state admindown.";
      }
      enum "unknow" {
        value 3;
        description
          "BFD state unknow.";
      }
    }
    description
      "VRRP track bfd state is like down/up/admin-down/unknow.";
  }

  typedef ncs_rpc_notif_vrrp-oper-state {
    type enumeration {
      enum "initialize" {
        value 0;
        description
          "Initialize state.";
      }
      enum "backup" {
        value 1;
        description
          "Backup state.";
      }
      enum "master" {
        value 2;
        description
          "Master state.";
      }
    }
    description
      "VRRP operation state is like initialize/backup/master.";
  }

  typedef ncs_rpc_notif_vrrp6cksm-mode {
    type enumeration {
      enum "include-pseudo-header" {
        value 0;
        description
          "Include a pseudo header.";
      }
      enum "exclude-pseudo-header" {
        value 1;
        description
          "Exclude a pseudo header.";
      }
    }
    description
      "VRRP6 cksm-mode is like include-pseudo-header/exclude-pseudo-header.";
  }

  typedef ncs_rpc_notif_vrrpauthen-mode {
    type enumeration {
      enum "none" {
        value 0;
        description
          "No authentication mode.";
      }
      enum "simple" {
        value 1;
        description
          "Simple authentication mode.";
      }
      enum "md5" {
        value 2;
        description
          "MD5 authentication mode.";
      }
      enum "hmac-sha256" {
        value 3;
        description
          "SHA256 authentication mode.";
      }
    }
    description
      "VRRP authen-mode is like none/simple/md5.";
  }

  typedef ncs_rpc_notif_vrrp-v3-sendmode {
    type enumeration {
      enum "v3-only" {
        value 0;
        description
          "Only VRRPv3 advertisement packets are sent.";
      }
      enum "v2v3-both" {
        value 1;
        description
          "Both VRRPv2 and VRRPv3 advertisement packets are sent.";
      }
      enum "v2-only" {
        value 2;
        description
          "Only VRRPv2 advertisement packets are sent.";
      }
    }
    description
      "VRRP V3 send mode is like v2-only/v2v3-both/v3-only.";
  }

  typedef ncs_rpc_notif_vrrp-version {
    type enumeration {
      enum "v2" {
        value 0;
        description
          "VRRPv2 version.";
      }
      enum "v3" {
        value 1;
        description
          "VRRPv3 version.";
      }
    }
    description
      "VRRP version is like v2/v3.";
  }

  typedef ncs_rpc_notif_vrrptrack-mode {
    type enumeration {
      enum "increase" {
        value 0;
        description
          "Increase priority.";
      }
      enum "reduce" {
        value 1;
        description
          "Reduce priority.";
      }
    }
    description
      "VRRP track mode is like increase/reduce.";
  }

  typedef ncs_rpc_notif_mtgrptrack-mode {
    type enumeration {
      enum "link" {
        value 0;
        description
          "Link mode.";
      }
      enum "reduce" {
        value 1;
        description
          "Mode in which the priority is reduced.";
      }
    }
    description
      "Monitor-group track mode is like normal/link.";
  }

  typedef ncs_rpc_notif_vgmp-type {
    type enumeration {
      enum "none" {
        value 0;
        description
          "Status of none.";
      }
      enum "active" {
        value 1;
        description
          "Status of active.";
      }
      enum "standby" {
        value 2;
        description
          "Status of standby.";
      }
    }
    description
      "The configuration of VRRP.";
  }

  typedef live_ncs_vrrp-type {
    type enumeration {
      enum "normal" {
        value 0;
        description
          "Normal VRRP.";
      }
      enum "admin" {
        value 1;
        description
          "Admin VRRP.";
      }
      enum "member" {
        value 2;
        description
          "Member VRRP.";
      }
      enum "lbrg" {
        value 3;
        description
          "Load-balance redundancy group VRRP.";
      }
      enum "lbrg-mem" {
        value 4;
        description
          "Load-balance redundancy group member VRRP.";
      }
      enum "mem-lbrg" {
        value 5;
        description
          "Member of load-balance redundancy group VRRP.";
      }
      enum "mem-lbrg-mem" {
        value 6;
        description
          "Member of load-balance redundancy group Member VRRP.";
      }
      enum "unicast" {
        value 7;
        description
          "Unicast VRRP.";
      }
    }
    description
      "VRRP group type.";
  }

  typedef live_ncs_vrrp-bfd-type {
    type enumeration {
      enum "normal" {
        value 0;
        description
          "Normal BFD session.";
      }
      enum "link" {
        value 1;
        description
          "Link BFD session.";
      }
      enum "peer" {
        value 2;
        description
          "Peer BFD session.";
      }
    }
    description
      "The type of VRRP track BFD.";
  }

  typedef live_ncs_vrrp-track-mode {
    type enumeration {
      enum "increase" {
        value 0;
        description
          "Increase priority.";
      }
      enum "reduce" {
        value 1;
        description
          "Reduce priority.";
      }
    }
    description
      "VRRP track mode is like increase/reduce.";
  }

  typedef live_ncs_vrrp-track-bfd-state {
    type enumeration {
      enum "down" {
        value 0;
        description
          "BFD state down.";
      }
      enum "up" {
        value 1;
        description
          "BFD state up.";
      }
      enum "admin-down" {
        value 2;
        description
          "BFD state admindown.";
      }
      enum "unknow" {
        value 3;
        description
          "BFD state unknow.";
      }
    }
    description
      "VRRP track bfd state is like down/up/admin-down/unknow.";
  }

  typedef live_ncs_vrrp-oper-state {
    type enumeration {
      enum "initialize" {
        value 0;
        description
          "Initialize state.";
      }
      enum "backup" {
        value 1;
        description
          "Backup state.";
      }
      enum "master" {
        value 2;
        description
          "Master state.";
      }
    }
    description
      "VRRP operation state is like initialize/backup/master.";
  }

  typedef live_ncs_vrrp6cksm-mode {
    type enumeration {
      enum "include-pseudo-header" {
        value 0;
        description
          "Include a pseudo header.";
      }
      enum "exclude-pseudo-header" {
        value 1;
        description
          "Exclude a pseudo header.";
      }
    }
    description
      "VRRP6 cksm-mode is like include-pseudo-header/exclude-pseudo-header.";
  }

  typedef live_ncs_vrrpauthen-mode {
    type enumeration {
      enum "none" {
        value 0;
        description
          "No authentication mode.";
      }
      enum "simple" {
        value 1;
        description
          "Simple authentication mode.";
      }
      enum "md5" {
        value 2;
        description
          "MD5 authentication mode.";
      }
      enum "hmac-sha256" {
        value 3;
        description
          "SHA256 authentication mode.";
      }
    }
    description
      "VRRP authen-mode is like none/simple/md5.";
  }

  typedef live_ncs_vrrp-v3-sendmode {
    type enumeration {
      enum "v3-only" {
        value 0;
        description
          "Only VRRPv3 advertisement packets are sent.";
      }
      enum "v2v3-both" {
        value 1;
        description
          "Both VRRPv2 and VRRPv3 advertisement packets are sent.";
      }
      enum "v2-only" {
        value 2;
        description
          "Only VRRPv2 advertisement packets are sent.";
      }
    }
    description
      "VRRP V3 send mode is like v2-only/v2v3-both/v3-only.";
  }

  typedef live_ncs_vrrp-version {
    type enumeration {
      enum "v2" {
        value 0;
        description
          "VRRPv2 version.";
      }
      enum "v3" {
        value 1;
        description
          "VRRPv3 version.";
      }
    }
    description
      "VRRP version is like v2/v3.";
  }

  typedef live_ncs_vrrptrack-mode {
    type enumeration {
      enum "increase" {
        value 0;
        description
          "Increase priority.";
      }
      enum "reduce" {
        value 1;
        description
          "Reduce priority.";
      }
    }
    description
      "VRRP track mode is like increase/reduce.";
  }

  typedef live_ncs_mtgrptrack-mode {
    type enumeration {
      enum "link" {
        value 0;
        description
          "Link mode.";
      }
      enum "reduce" {
        value 1;
        description
          "Mode in which the priority is reduced.";
      }
    }
    description
      "Monitor-group track mode is like normal/link.";
  }

  typedef live_ncs_vgmp-type {
    type enumeration {
      enum "none" {
        value 0;
        description
          "Status of none.";
      }
      enum "active" {
        value 1;
        description
          "Status of active.";
      }
      enum "standby" {
        value 2;
        description
          "Status of standby.";
      }
    }
    description
      "The configuration of VRRP.";
  }

  typedef vrrp-type {
    type enumeration {
      enum "normal" {
        value 0;
        description
          "Normal VRRP.";
      }
      enum "admin" {
        value 1;
        description
          "Admin VRRP.";
      }
      enum "member" {
        value 2;
        description
          "Member VRRP.";
      }
      enum "lbrg" {
        value 3;
        description
          "Load-balance redundancy group VRRP.";
      }
      enum "lbrg-mem" {
        value 4;
        description
          "Load-balance redundancy group member VRRP.";
      }
      enum "mem-lbrg" {
        value 5;
        description
          "Member of load-balance redundancy group VRRP.";
      }
      enum "mem-lbrg-mem" {
        value 6;
        description
          "Member of load-balance redundancy group Member VRRP.";
      }
      enum "unicast" {
        value 7;
        description
          "Unicast VRRP.";
      }
    }
    description
      "VRRP group type.";
  }

  typedef vrrp-bfd-type {
    type enumeration {
      enum "normal" {
        value 0;
        description
          "Normal BFD session.";
      }
      enum "link" {
        value 1;
        description
          "Link BFD session.";
      }
      enum "peer" {
        value 2;
        description
          "Peer BFD session.";
      }
    }
    description
      "The type of VRRP track BFD.";
  }

  typedef vrrp-track-mode {
    type enumeration {
      enum "increase" {
        value 0;
        description
          "Increase priority.";
      }
      enum "reduce" {
        value 1;
        description
          "Reduce priority.";
      }
    }
    description
      "VRRP track mode is like increase/reduce.";
  }

  typedef vrrp-track-bfd-state {
    type enumeration {
      enum "down" {
        value 0;
        description
          "BFD state down.";
      }
      enum "up" {
        value 1;
        description
          "BFD state up.";
      }
      enum "admin-down" {
        value 2;
        description
          "BFD state admindown.";
      }
      enum "unknow" {
        value 3;
        description
          "BFD state unknow.";
      }
    }
    description
      "VRRP track bfd state is like down/up/admin-down/unknow.";
  }

  typedef vrrp-oper-state {
    type enumeration {
      enum "initialize" {
        value 0;
        description
          "Initialize state.";
      }
      enum "backup" {
        value 1;
        description
          "Backup state.";
      }
      enum "master" {
        value 2;
        description
          "Master state.";
      }
    }
    description
      "VRRP operation state is like initialize/backup/master.";
  }

  typedef vrrp6cksm-mode {
    type enumeration {
      enum "include-pseudo-header" {
        value 0;
        description
          "Include a pseudo header.";
      }
      enum "exclude-pseudo-header" {
        value 1;
        description
          "Exclude a pseudo header.";
      }
    }
    description
      "VRRP6 cksm-mode is like include-pseudo-header/exclude-pseudo-header.";
  }

  typedef vrrpauthen-mode {
    type enumeration {
      enum "none" {
        value 0;
        description
          "No authentication mode.";
      }
      enum "simple" {
        value 1;
        description
          "Simple authentication mode.";
      }
      enum "md5" {
        value 2;
        description
          "MD5 authentication mode.";
      }
      enum "hmac-sha256" {
        value 3;
        description
          "SHA256 authentication mode.";
      }
    }
    description
      "VRRP authen-mode is like none/simple/md5.";
  }

  typedef vrrp-v3-sendmode {
    type enumeration {
      enum "v3-only" {
        value 0;
        description
          "Only VRRPv3 advertisement packets are sent.";
      }
      enum "v2v3-both" {
        value 1;
        description
          "Both VRRPv2 and VRRPv3 advertisement packets are sent.";
      }
      enum "v2-only" {
        value 2;
        description
          "Only VRRPv2 advertisement packets are sent.";
      }
    }
    description
      "VRRP V3 send mode is like v2-only/v2v3-both/v3-only.";
  }

  typedef vrrp-version {
    type enumeration {
      enum "v2" {
        value 0;
        description
          "VRRPv2 version.";
      }
      enum "v3" {
        value 1;
        description
          "VRRPv3 version.";
      }
    }
    description
      "VRRP version is like v2/v3.";
  }

  typedef vrrptrack-mode {
    type enumeration {
      enum "increase" {
        value 0;
        description
          "Increase priority.";
      }
      enum "reduce" {
        value 1;
        description
          "Reduce priority.";
      }
    }
    description
      "VRRP track mode is like increase/reduce.";
  }

  typedef mtgrptrack-mode {
    type enumeration {
      enum "link" {
        value 0;
        description
          "Link mode.";
      }
      enum "reduce" {
        value 1;
        description
          "Mode in which the priority is reduced.";
      }
    }
    description
      "Monitor-group track mode is like normal/link.";
  }

  typedef vgmp-type {
    type enumeration {
      enum "none" {
        value 0;
        description
          "Status of none.";
      }
      enum "active" {
        value 1;
        description
          "Status of active.";
      }
      enum "standby" {
        value 2;
        description
          "Status of standby.";
      }
    }
    description
      "The configuration of VRRP.";
  }

  augment "/ncs:devices/ncs:device/ncs:config" {
    container vrrp {
      tailf:ncs-device-type "netconf";
      tailf:display-when "not(../../ncs:module) or ../../ncs:module[ncs:name='huawei-vrrp']";
      description
        "Virtual router redundancy protocol.";
      container global {
        description
          "Configure global VRRP configuration.";
        leaf gratuitous-arp-enable {
          type boolean;
          default "true";
          description
            "Enable/disable a device to periodically send gratuitous ARP packets.";
        }
        leaf gratuitous-timeout {
          when "../gratuitous-arp-enable='true'" {
            tailf:xpath-root 3;
          }
          type uint16 {
            range "30..1200";
          }
          units "s";
          default "30";
          description
            "Interval at which gratuitous ARP packets are sent.";
        }
        leaf adv-time-learn {
          type boolean;
          default "true";
          description
            "Enable/disable learning the interval at which VRRP packets are sent.";
        }
        leaf ping-enable {
          type boolean;
          default "true";
          description
            "Enable/disable ping virtual IP address.";
        }
        leaf recover-delay {
          type uint16 {
            range "0..3600";
          }
          units "s";
          default "0";
          description
            "Delay in recovering after an interface goes up. The delay is used for interface flapping suppression.";
        }
        leaf version {
          type vrrp-version;
          default "v2";
          description
            "Global VRRP version.";
        }
        leaf virtual-iproute-enable {
          type boolean;
          default "true";
          description
            "Enable/disable virtual IP routing function.";
        }
        leaf virtual-ospf-enable {
          when "not(../virtual-iproute-enable='false')" {
            tailf:xpath-root 3;
          }
          type boolean;
          default "true";
          description
            "Enable/disable advertising the virtual IP route by OSPF.";
        }
        leaf virtual-isis-enable {
          when "not(../virtual-iproute-enable='false')" {
            tailf:xpath-root 3;
          }
          type boolean;
          default "true";
          description
            "Enable/disable advertising the virtual IP route by ISIS.";
        }
        leaf virtual-rip-enable {
          when "not(../virtual-iproute-enable='false')" {
            tailf:xpath-root 3;
          }
          type boolean;
          default "true";
          description
            "Enable/disable advertising the virtual IP route by RIP.";
        }
        leaf v6-cks-mode {
          type vrrp6cksm-mode;
          default "include-pseudo-header";
          description
            "VRRP6 checksum mode.";
        }
        leaf smooth-switch-time {
          when "not(../adv-time-learn='false')" {
            tailf:xpath-root 3;
          }
          type uint8 {
            range "1..255";
          }
          units "s";
          default "100";
          description
            "Interval carried in smooth VRRP switching packets.";
        }
        leaf unicast-port {
          type uint32 {
            range "1025..65535";
          }
          default "3077";
          description
            "Number of a UDP interface for sending and receiving unicast VRRP packets.";
        }
        leaf gratuitous-enhance-enable {
          type boolean;
          default "false";
          description
            "Enable/disable gratuitous ARP enhance.";
        }
        container vrrp-session-car {
          must 'pir >= cir and pbs >= cbs' {
            tailf:xpath-root 3;
          }
          description
            "Configure session CAR.";
          leaf enable {
            type boolean;
            default "true";
            description
              "Enable/disable session CAR.";
          }
          leaf cir {
            type uint32 {
              range "0..325";
            }
            units "kbit/s";
            default "4";
            description
              "Specify the session CAR CIR value.";
          }
          leaf cbs {
            type uint32 {
              range "0..30000";
            }
            units "Byte";
            default "9000";
            description
              "Specify the session CAR CBS value.";
          }
          leaf pir {
            type uint32 {
              range "0..325";
            }
            units "kbit/s";
            default "5";
            description
              "Specify the session CAR PIR value.";
          }
          leaf pbs {
            type uint32 {
              range "0..30000";
            }
            units "Byte";
            default "9000";
            description
              "Specify the session CAR PBS value.";
          }
        }
        container vrrp6-session-car {
          must 'pir >= cir and pbs >= cbs' {
            tailf:xpath-root 3;
          }
          description
            "Configure session CAR.";
          leaf enable {
            type boolean;
            default "true";
            description
              "Enable/disable session CAR.";
          }
          leaf cir {
            type uint32 {
              range "0..2600";
            }
            units "kbit/s";
            default "32";
            description
              "Specify the session CAR CIR value.";
          }
          leaf cbs {
            type uint32 {
              range "0..1600000";
            }
            units "Byte";
            default "72000";
            description
              "Specify the session CAR CBS value.";
          }
          leaf pir {
            type uint32 {
              range "0..2600";
            }
            units "kbit/s";
            default "40";
            description
              "Specify the session CAR PIR value.";
          }
          leaf pbs {
            type uint32 {
              range "0..1600000";
            }
            units "Byte";
            default "72000";
            description
              "Specify the session CAR PBS value.";
          }
        }
      }
    }
  }
  augment "/ncs:devices/ncs:device/ncs:live-status" {
    container vrrp {
      tailf:ncs-device-type "netconf";
      tailf:display-when "not(../../ncs:module) or ../../ncs:module[ncs:name='huawei-vrrp'] or (../../ncs:live-status-protocol[not(ncs:capability)]) or (../../ncs:live-status-protocol/ncs:capability/ncs:module[.='huawei-vrrp'])";
      description
        "Virtual router redundancy protocol.";
      container global {
        description
          "Configure global VRRP configuration.";
        leaf gratuitous-arp-enable {
          type boolean;
          // NCS drop default statement
          description
            "Enable/disable a device to periodically send gratuitous ARP packets.";
        }
        leaf gratuitous-timeout {
          // NCS drop when statement
          type uint16 {
            range "30..1200";
          }
          units "s";
          // NCS drop default statement
          description
            "Interval at which gratuitous ARP packets are sent.";
        }
        leaf adv-time-learn {
          type boolean;
          // NCS drop default statement
          description
            "Enable/disable learning the interval at which VRRP packets are sent.";
        }
        leaf ping-enable {
          type boolean;
          // NCS drop default statement
          description
            "Enable/disable ping virtual IP address.";
        }
        leaf recover-delay {
          type uint16 {
            range "0..3600";
          }
          units "s";
          // NCS drop default statement
          description
            "Delay in recovering after an interface goes up. The delay is used for interface flapping suppression.";
        }
        leaf version {
          type live_ncs_vrrp-version;
          // NCS drop default statement
          description
            "Global VRRP version.";
        }
        leaf virtual-iproute-enable {
          type boolean;
          // NCS drop default statement
          description
            "Enable/disable virtual IP routing function.";
        }
        leaf virtual-ospf-enable {
          // NCS drop when statement
          type boolean;
          // NCS drop default statement
          description
            "Enable/disable advertising the virtual IP route by OSPF.";
        }
        leaf virtual-isis-enable {
          // NCS drop when statement
          type boolean;
          // NCS drop default statement
          description
            "Enable/disable advertising the virtual IP route by ISIS.";
        }
        leaf virtual-rip-enable {
          // NCS drop when statement
          type boolean;
          // NCS drop default statement
          description
            "Enable/disable advertising the virtual IP route by RIP.";
        }
        leaf v6-cks-mode {
          type live_ncs_vrrp6cksm-mode;
          // NCS drop default statement
          description
            "VRRP6 checksum mode.";
        }
        leaf smooth-switch-time {
          // NCS drop when statement
          type uint8 {
            range "1..255";
          }
          units "s";
          // NCS drop default statement
          description
            "Interval carried in smooth VRRP switching packets.";
        }
        leaf unicast-port {
          type uint32 {
            range "1025..65535";
          }
          // NCS drop default statement
          description
            "Number of a UDP interface for sending and receiving unicast VRRP packets.";
        }
        leaf gratuitous-enhance-enable {
          type boolean;
          // NCS drop default statement
          description
            "Enable/disable gratuitous ARP enhance.";
        }
        container vrrp-session-car {
          // NCS drop must statement
          description
            "Configure session CAR.";
          leaf enable {
            type boolean;
            // NCS drop default statement
            description
              "Enable/disable session CAR.";
          }
          leaf cir {
            type uint32 {
              range "0..325";
            }
            units "kbit/s";
            // NCS drop default statement
            description
              "Specify the session CAR CIR value.";
          }
          leaf cbs {
            type uint32 {
              range "0..30000";
            }
            units "Byte";
            // NCS drop default statement
            description
              "Specify the session CAR CBS value.";
          }
          leaf pir {
            type uint32 {
              range "0..325";
            }
            units "kbit/s";
            // NCS drop default statement
            description
              "Specify the session CAR PIR value.";
          }
          leaf pbs {
            type uint32 {
              range "0..30000";
            }
            units "Byte";
            // NCS drop default statement
            description
              "Specify the session CAR PBS value.";
          }
        }
        container vrrp6-session-car {
          // NCS drop must statement
          description
            "Configure session CAR.";
          leaf enable {
            type boolean;
            // NCS drop default statement
            description
              "Enable/disable session CAR.";
          }
          leaf cir {
            type uint32 {
              range "0..2600";
            }
            units "kbit/s";
            // NCS drop default statement
            description
              "Specify the session CAR CIR value.";
          }
          leaf cbs {
            type uint32 {
              range "0..1600000";
            }
            units "Byte";
            // NCS drop default statement
            description
              "Specify the session CAR CBS value.";
          }
          leaf pir {
            type uint32 {
              range "0..2600";
            }
            units "kbit/s";
            // NCS drop default statement
            description
              "Specify the session CAR PIR value.";
          }
          leaf pbs {
            type uint32 {
              range "0..1600000";
            }
            units "Byte";
            // NCS drop default statement
            description
              "Specify the session CAR PBS value.";
          }
        }
      }
    }
  }
  augment "/ncs:devices/ncs:template/ncs:ned-id/ncs:config" {
    container vrrp {
      description
        "Virtual router redundancy protocol.";
      container global {
        description
          "Configure global VRRP configuration.";
        leaf gratuitous-arp-enable {
          type string;
          // NCS drop default statement
          description
            "Enable/disable a device to periodically send gratuitous ARP packets.";
        }
        leaf gratuitous-timeout {
          // NCS drop when statement
          type string;
          units "s";
          // NCS drop default statement
          description
            "Interval at which gratuitous ARP packets are sent.";
        }
        leaf adv-time-learn {
          type string;
          // NCS drop default statement
          description
            "Enable/disable learning the interval at which VRRP packets are sent.";
        }
        leaf ping-enable {
          type string;
          // NCS drop default statement
          description
            "Enable/disable ping virtual IP address.";
        }
        leaf recover-delay {
          type string;
          units "s";
          // NCS drop default statement
          description
            "Delay in recovering after an interface goes up. The delay is used for interface flapping suppression.";
        }
        leaf version {
          type ncs_template_vrrp-version;
          // NCS drop default statement
          description
            "Global VRRP version.";
        }
        leaf virtual-iproute-enable {
          type string;
          // NCS drop default statement
          description
            "Enable/disable virtual IP routing function.";
        }
        leaf virtual-ospf-enable {
          // NCS drop when statement
          type string;
          // NCS drop default statement
          description
            "Enable/disable advertising the virtual IP route by OSPF.";
        }
        leaf virtual-isis-enable {
          // NCS drop when statement
          type string;
          // NCS drop default statement
          description
            "Enable/disable advertising the virtual IP route by ISIS.";
        }
        leaf virtual-rip-enable {
          // NCS drop when statement
          type string;
          // NCS drop default statement
          description
            "Enable/disable advertising the virtual IP route by RIP.";
        }
        leaf v6-cks-mode {
          type ncs_template_vrrp6cksm-mode;
          // NCS drop default statement
          description
            "VRRP6 checksum mode.";
        }
        leaf smooth-switch-time {
          // NCS drop when statement
          type string;
          units "s";
          // NCS drop default statement
          description
            "Interval carried in smooth VRRP switching packets.";
        }
        leaf unicast-port {
          type string;
          // NCS drop default statement
          description
            "Number of a UDP interface for sending and receiving unicast VRRP packets.";
        }
        leaf gratuitous-enhance-enable {
          type string;
          // NCS drop default statement
          description
            "Enable/disable gratuitous ARP enhance.";
        }
        container vrrp-session-car {
          // NCS drop must statement
          description
            "Configure session CAR.";
          leaf enable {
            type string;
            // NCS drop default statement
            description
              "Enable/disable session CAR.";
          }
          leaf cir {
            type string;
            units "kbit/s";
            // NCS drop default statement
            description
              "Specify the session CAR CIR value.";
          }
          leaf cbs {
            type string;
            units "Byte";
            // NCS drop default statement
            description
              "Specify the session CAR CBS value.";
          }
          leaf pir {
            type string;
            units "kbit/s";
            // NCS drop default statement
            description
              "Specify the session CAR PIR value.";
          }
          leaf pbs {
            type string;
            units "Byte";
            // NCS drop default statement
            description
              "Specify the session CAR PBS value.";
          }
        }
        container vrrp6-session-car {
          // NCS drop must statement
          description
            "Configure session CAR.";
          leaf enable {
            type string;
            // NCS drop default statement
            description
              "Enable/disable session CAR.";
          }
          leaf cir {
            type string;
            units "kbit/s";
            // NCS drop default statement
            description
              "Specify the session CAR CIR value.";
          }
          leaf cbs {
            type string;
            units "Byte";
            // NCS drop default statement
            description
              "Specify the session CAR CBS value.";
          }
          leaf pir {
            type string;
            units "kbit/s";
            // NCS drop default statement
            description
              "Specify the session CAR PIR value.";
          }
          leaf pbs {
            type string;
            units "Byte";
            // NCS drop default statement
            description
              "Specify the session CAR PBS value.";
          }
        }
      }
    }
  }
  augment "/ncs:devices/ncs:template/ncs:ned-id/ncs:config/ni:network-instance/ni:instances/ni:instance" {
    description
      "VRRP configurations on L3VPN.";
    container vrrp {
      status deprecated;
      description
        "Configure VRRP backup groups under network-instance.";
      container groups {
        status deprecated;
        description
          "List of all VRRP backup groups.";
        list group {
          // NCS patched for predictable order
          ordered-by user;
          key "id if-name";
          status deprecated;
          description
            "Configure VRRP operations on a device. It lists a series of VRRP operation entries. You can use this table to query the VRRP configuration on the device. In addition, you can create virtual router instances and modify the configuration.";
          leaf id {
            type string;
            status deprecated;
            description
              "VRRP backup group ID.";
          }
          leaf if-name {
            type string;
            // NCS drop must statement
            status deprecated;
            description
              "Name of the outbound interface of a BFD session. This parameter is available only when the type of the detected link is IP or LDP LSP. If only the destination IP address is specified, multi-hop routes are detected. If both the destination IP address and outbound interface name are specified, single-hop links are detected. That is, a fixed route is detected, with the interface where the BFD session resides as the outbound interface and the destination IP address as the next hop address.";
          }
          leaf priority {
            type string;
            // NCS drop default statement
            status deprecated;
            description
              "Configured VRRP priority. A larger value indicates a higher priority.";
          }
          leaf preempt-mode {
            type string;
            // NCS drop default statement
            status deprecated;
            description
              "Enable/disable whether a high-priority router can preempt the master state.";
          }
          leaf delay-time {
            // NCS drop when statement
            type string;
            units "s";
            // NCS drop default statement
            status deprecated;
            description
              "Preemption delay.";
          }
          leaf adver-interval {
            type string;
            units "ms";
            // NCS drop default statement
            status deprecated;
            description
              "Configure an interval (in milliseconds) at which the master sends VRRP advertisement packets. This interval must be a multiple of 1000. If the device supports fast advertisement sending, this interval can be set to 100ms 200ms or 500ms.";
          }
          leaf isplain {
            // NCS drop when statement
            type string;
            // NCS drop must statement
            // NCS drop default statement
            status deprecated;
            description
              "Enable/disable selecting the display mode of an authentication key.";
          }
          leaf authentication-key {
            // NCS drop when statement
            type pub-type:ncs_template_password;
            // NCS drop must statement
            status deprecated;
            description
              "Authentication key, which is set based on the authentication type. Value description: If non-authentication is specified, the value is empty. If simple authentication, MD5 authentication, or HMAC-SHA256 authentication is specified, the value is a string with the length ranging from 1 to 8 bytes or a ciphertext password with the corresponding length.";
          }
          leaf authentication-mode {
            type ncs_template_vrrpauthen-mode;
            // NCS drop must statement
            // NCS drop default statement
            status deprecated;
            description
              "Authentication type used for VRRP packet exchanges between virtual routers. The values are as follows: noAuthentication, simpleTextPassword, md5Authentication. The default value is noAuthentication.";
          }
          leaf hold-multi {
            type string;
            // NCS drop default statement
            status deprecated;
            description
              "Set the hello packet sending interval multiplier.";
          }
          leaf backup-forward {
            type string;
            // NCS drop default statement
            status deprecated;
            description
              "Enable/disable VRRP backup forward mode.";
          }
          leaf fast-resume {
            // NCS drop when statement
            type string;
            // NCS drop default statement
            status deprecated;
            description
              "Enable/disable VRRP fast resume mode.";
          }
          leaf v3-sendmode {
            // NCS drop when statement
            type ncs_template_vrrp-v3-sendmode;
            // NCS drop default statement
            status deprecated;
            description
              "VRRP advertisement packet mode on the interface.";
          }
          choice vrrp-type {
            status deprecated;
            description
              "Type of VRRP.";
            case member-vrrp {
              status deprecated;
              description
                "Member VRRP.";
              leaf admin-id {
                type string;
                // NCS drop must statement
                status deprecated;
                description
                  "Tracked MVRRP ID.";
              }
              leaf admin-if-name {
                type string;
                // NCS drop must statement
                status deprecated;
                description
                  "Tracked MVRRP interface name.";
              }
            }
            case admin-vrrp {
              status deprecated;
              description
                "Admin VRRP.";
              leaf admin-flag {
                type empty;
                status deprecated;
                description
                  "Management VRRP.";
              }
              leaf admin-ignore-ifdown {
                // NCS drop when statement
                type string;
                // NCS drop default statement
                status deprecated;
                description
                  "Enable/disable ignoring an interface down event.";
              }
            }
          }
          // NCS drop config false leaf type
          // NCS drop config false leaf state
          // NCS drop config false leaf 'create-time'
          // NCS drop config false leaf 'last-change-time'
          container virtual-ips {
            status deprecated;
            description
              "List of IP address table related to virtual routers. A VRRP backup group can have 0 to 16 extended virtual IP addresses.";
            list virtual-ip {
              // NCS patched for predictable order
              ordered-by user;
              key "address";
              // NCS drop max-elements statement
              status deprecated;
              description
                "Configure virtual IP address configuration. A VRRP backup group can have 0 to 16 extended virtual IP addresses.";
              leaf address {
                type string;
                status deprecated;
                description
                  "Virtual IP address.";
              }
            }
          }
          container track-interfaces {
            // NCS drop when statement
            status deprecated;
            description
              "List of interfaces tracked by a VRRP backup group. A VRRP backup group can track a maximum of 16 interfaces.";
            list track-interface {
              // NCS patched for predictable order
              ordered-by user;
              key "ifname";
              // NCS drop max-elements statement
              status deprecated;
              description
                "Configure VRRP backup group tracking interface.";
              leaf ifname {
                type string;
                status deprecated;
                description
                  "Name of the interface tracked by the VRRP backup group.";
              }
              leaf track-mode {
                type ncs_template_vrrptrack-mode;
                // NCS drop default statement
                status deprecated;
                description
                  "Mode in which the VRRP backup group tracks the interface.";
              }
              leaf priority-change {
                type string;
                // NCS drop default statement
                status deprecated;
                description
                  "Value by which the priority increases or reduces when the VRRP backup group tracks the interface.";
              }
            }
          }
          container track-bfds {
            // NCS drop when statement
            status deprecated;
            description
              "List of BFD sessions tracked by the VRRP backup group.";
            list track-bfd {
              // NCS patched for predictable order
              ordered-by user;
              key "session-name session-type";
              // NCS drop max-elements statement
              status deprecated;
              description
                "Configure VRRP backup group tracking BFD session.";
              leaf session-name {
                type string;
                status deprecated;
                description
                  "Name of the BFD session tracked by the VRRP backup group.";
              }
              leaf session-type {
                type ncs_template_vrrp-bfd-type;
                status deprecated;
                description
                  "Type of the BFD session tracked by the VRRP backup group.";
              }
              leaf track-mode {
                // NCS drop when statement
                type ncs_template_vrrp-track-mode;
                // NCS drop default statement
                status deprecated;
                description
                  "Mode in which the VRRP backup group tracks the BFD session.";
              }
              leaf priority-change {
                // NCS drop when statement
                type string;
                // NCS drop default statement
                status deprecated;
                description
                  "Value by which the priority increases or reduces when the VRRP backup group tracks the common BFD session.";
              }
              // NCS drop config false leaf 'session-id'
              // NCS drop config false leaf 'session-state'
            }
          }
        }
      }
    }
  }
  augment "/ncs:devices/ncs:device/ncs:live-status/ni:network-instance/ni:instances/ni:instance" {
    description
      "VRRP configurations on L3VPN.";
    container vrrp {
      tailf:ncs-device-type "netconf";
      tailf:display-when "not(../../../../../ncs:module) or ../../../../../ncs:module[ncs:name='huawei-vrrp'] or (../../../../../ncs:live-status-protocol[not(ncs:capability)]) or (../../../../../ncs:live-status-protocol/ncs:capability/ncs:module[.='huawei-vrrp'])";
      status deprecated;
      description
        "Configure VRRP backup groups under network-instance.";
      container groups {
        status deprecated;
        description
          "List of all VRRP backup groups.";
        list group {
          key "id if-name";
          status deprecated;
          description
            "Configure VRRP operations on a device. It lists a series of VRRP operation entries. You can use this table to query the VRRP configuration on the device. In addition, you can create virtual router instances and modify the configuration.";
          leaf id {
            type uint8 {
              range "1..255";
            }
            status deprecated;
            description
              "VRRP backup group ID.";
          }
          leaf if-name {
            type leafref {
              path "/ncs:devices/ncs:device/ncs:live-status/ifm:ifm/ifm:interfaces/ifm:interface/ifm:name" {
                tailf:xpath-root 3;
              }
            }
            // NCS drop must statement
            status deprecated;
            description
              "Name of the outbound interface of a BFD session. This parameter is available only when the type of the detected link is IP or LDP LSP. If only the destination IP address is specified, multi-hop routes are detected. If both the destination IP address and outbound interface name are specified, single-hop links are detected. That is, a fixed route is detected, with the interface where the BFD session resides as the outbound interface and the destination IP address as the next hop address.";
          }
          leaf priority {
            type uint8 {
              range "1..254";
            }
            // NCS drop default statement
            status deprecated;
            description
              "Configured VRRP priority. A larger value indicates a higher priority.";
          }
          leaf preempt-mode {
            type boolean;
            // NCS drop default statement
            status deprecated;
            description
              "Enable/disable whether a high-priority router can preempt the master state.";
          }
          leaf delay-time {
            // NCS drop when statement
            type uint16 {
              range "0..10800";
            }
            units "s";
            // NCS drop default statement
            status deprecated;
            description
              "Preemption delay.";
          }
          leaf adver-interval {
            type uint32 {
              range "100..255000";
            }
            units "ms";
            // NCS drop default statement
            status deprecated;
            description
              "Configure an interval (in milliseconds) at which the master sends VRRP advertisement packets. This interval must be a multiple of 1000. If the device supports fast advertisement sending, this interval can be set to 100ms 200ms or 500ms.";
          }
          leaf isplain {
            // NCS drop when statement
            type boolean;
            // NCS drop must statement
            // NCS drop default statement
            status deprecated;
            description
              "Enable/disable selecting the display mode of an authentication key.";
          }
          leaf authentication-key {
            // NCS drop when statement
            type pub-type:live_ncs_password;
            // NCS drop must statement
            status deprecated;
            description
              "Authentication key, which is set based on the authentication type. Value description: If non-authentication is specified, the value is empty. If simple authentication, MD5 authentication, or HMAC-SHA256 authentication is specified, the value is a string with the length ranging from 1 to 8 bytes or a ciphertext password with the corresponding length.";
          }
          leaf authentication-mode {
            type live_ncs_vrrpauthen-mode;
            // NCS drop must statement
            // NCS drop default statement
            status deprecated;
            description
              "Authentication type used for VRRP packet exchanges between virtual routers. The values are as follows: noAuthentication, simpleTextPassword, md5Authentication. The default value is noAuthentication.";
          }
          leaf hold-multi {
            type uint8 {
              range "3..10";
            }
            // NCS drop default statement
            status deprecated;
            description
              "Set the hello packet sending interval multiplier.";
          }
          leaf backup-forward {
            type boolean;
            // NCS drop default statement
            status deprecated;
            description
              "Enable/disable VRRP backup forward mode.";
          }
          leaf fast-resume {
            // NCS drop when statement
            type boolean;
            // NCS drop default statement
            status deprecated;
            description
              "Enable/disable VRRP fast resume mode.";
          }
          leaf v3-sendmode {
            // NCS drop when statement
            type live_ncs_vrrp-v3-sendmode;
            // NCS drop default statement
            status deprecated;
            description
              "VRRP advertisement packet mode on the interface.";
          }
          choice vrrp-type {
            status deprecated;
            description
              "Type of VRRP.";
            case member-vrrp {
              status deprecated;
              description
                "Member VRRP.";
              leaf admin-id {
                type uint8 {
                  range "1..255";
                }
                // NCS drop must statement
                status deprecated;
                description
                  "Tracked MVRRP ID.";
              }
              leaf admin-if-name {
                type leafref {
                  path "/ncs:devices/ncs:device/ncs:live-status/ifm:ifm/ifm:interfaces/ifm:interface/ifm:name" {
                    tailf:xpath-root 3;
                  }
                }
                // NCS drop must statement
                status deprecated;
                description
                  "Tracked MVRRP interface name.";
              }
            }
            case admin-vrrp {
              status deprecated;
              description
                "Admin VRRP.";
              leaf admin-flag {
                type empty;
                status deprecated;
                description
                  "Management VRRP.";
              }
              leaf admin-ignore-ifdown {
                // NCS drop when statement
                type boolean;
                // NCS drop default statement
                status deprecated;
                description
                  "Enable/disable ignoring an interface down event.";
              }
            }
          }
          leaf type {
            type live_ncs_vrrp-type;
            // NCS drop default statement
            status deprecated;
            description
              "Type of a VRRP backup group.";
          }
          leaf state {
            type live_ncs_vrrp-oper-state;
            status deprecated;
            description
              "Running status of the virtual router. This object has three defined values.
               Initialize: The virtual router is waiting for a startup event.
               Backup: The virtual router is monitoring the availability of the master router.
               Master: The virtual router is forwarding packets for IP addresses that are associated with this router.";
          }
          leaf create-time {
            type yang:date-and-time;
            status deprecated;
            description
              "Time when the VRRP backup group was created.";
          }
          leaf last-change-time {
            type yang:date-and-time;
            status deprecated;
            description
              "Time when the status of the VRRP backup group last changed.";
          }
          container virtual-ips {
            status deprecated;
            description
              "List of IP address table related to virtual routers. A VRRP backup group can have 0 to 16 extended virtual IP addresses.";
            list virtual-ip {
              key "address";
              // NCS drop max-elements statement
              status deprecated;
              description
                "Configure virtual IP address configuration. A VRRP backup group can have 0 to 16 extended virtual IP addresses.";
              leaf address {
                type inet:ipv4-address-no-zone;
                status deprecated;
                description
                  "Virtual IP address.";
              }
            }
          }
          container track-interfaces {
            // NCS drop when statement
            status deprecated;
            description
              "List of interfaces tracked by a VRRP backup group. A VRRP backup group can track a maximum of 16 interfaces.";
            list track-interface {
              key "ifname";
              // NCS drop max-elements statement
              status deprecated;
              description
                "Configure VRRP backup group tracking interface.";
              leaf ifname {
                type leafref {
                  path "/ncs:devices/ncs:device/ncs:live-status/ifm:ifm/ifm:interfaces/ifm:interface/ifm:name" {
                    tailf:xpath-root 3;
                  }
                }
                status deprecated;
                description
                  "Name of the interface tracked by the VRRP backup group.";
              }
              leaf track-mode {
                type live_ncs_vrrptrack-mode;
                // NCS drop default statement
                status deprecated;
                description
                  "Mode in which the VRRP backup group tracks the interface.";
              }
              leaf priority-change {
                type uint8 {
                  range "1..255";
                }
                // NCS drop default statement
                status deprecated;
                description
                  "Value by which the priority increases or reduces when the VRRP backup group tracks the interface.";
              }
            }
          }
          container track-bfds {
            // NCS drop when statement
            status deprecated;
            description
              "List of BFD sessions tracked by the VRRP backup group.";
            list track-bfd {
              key "session-name session-type";
              // NCS drop max-elements statement
              status deprecated;
              description
                "Configure VRRP backup group tracking BFD session.";
              leaf session-name {
                type leafref {
                  path "/ncs:devices/ncs:device/ncs:live-status/bfd:bfd/bfd:sessions/bfd:session/bfd:name" {
                    tailf:xpath-root 3;
                  }
                }
                status deprecated;
                description
                  "Name of the BFD session tracked by the VRRP backup group.";
              }
              leaf session-type {
                type live_ncs_vrrp-bfd-type;
                status deprecated;
                description
                  "Type of the BFD session tracked by the VRRP backup group.";
              }
              leaf track-mode {
                // NCS drop when statement
                type live_ncs_vrrp-track-mode;
                // NCS drop default statement
                status deprecated;
                description
                  "Mode in which the VRRP backup group tracks the BFD session.";
              }
              leaf priority-change {
                // NCS drop when statement
                type uint8 {
                  range "1..255";
                }
                // NCS drop default statement
                status deprecated;
                description
                  "Value by which the priority increases or reduces when the VRRP backup group tracks the common BFD session.";
              }
              leaf session-id {
                type uint32 {
                  range "1..32768";
                }
                status deprecated;
                description
                  "ID of the BFD session tracked by the VRRP backup group.";
              }
              leaf session-state {
                type live_ncs_vrrp-track-bfd-state;
                status deprecated;
                description
                  "State of the BFD session tracked by the VRRP backup group.";
              }
            }
          }
        }
      }
    }
  }
  augment "/ncs:devices/ncs:device/ncs:config/ni:network-instance/ni:instances/ni:instance" {
    description
      "VRRP configurations on L3VPN.";
    container vrrp {
      tailf:ncs-device-type "netconf";
      tailf:display-when "not(../../../../../ncs:module) or ../../../../../ncs:module[ncs:name='huawei-vrrp']";
      status deprecated;
      description
        "Configure VRRP backup groups under network-instance.";
      container groups {
        status deprecated;
        description
          "List of all VRRP backup groups.";
        list group {
          key "id if-name";
          status deprecated;
          description
            "Configure VRRP operations on a device. It lists a series of VRRP operation entries. You can use this table to query the VRRP configuration on the device. In addition, you can create virtual router instances and modify the configuration.";
          leaf id {
            type uint8 {
              range "1..255";
            }
            status deprecated;
            description
              "VRRP backup group ID.";
          }
          leaf if-name {
            type leafref {
              path "/ncs:devices/ncs:device/ncs:config/ifm:ifm/ifm:interfaces/ifm:interface/ifm:name" {
                tailf:xpath-root 3;
              }
            }
            must '../../../../ni:name=/ifm:ifm/ifm:interfaces/ifm:interface[ifm:name=current()]/ifm:vrf-name' {
              tailf:xpath-root 3;
            }
            status deprecated;
            description
              "Name of the outbound interface of a BFD session. This parameter is available only when the type of the detected link is IP or LDP LSP. If only the destination IP address is specified, multi-hop routes are detected. If both the destination IP address and outbound interface name are specified, single-hop links are detected. That is, a fixed route is detected, with the interface where the BFD session resides as the outbound interface and the destination IP address as the next hop address.";
          }
          leaf priority {
            type uint8 {
              range "1..254";
            }
            default "100";
            status deprecated;
            description
              "Configured VRRP priority. A larger value indicates a higher priority.";
          }
          leaf preempt-mode {
            type boolean;
            default "true";
            status deprecated;
            description
              "Enable/disable whether a high-priority router can preempt the master state.";
          }
          leaf delay-time {
            when "../preempt-mode='true'" {
              tailf:xpath-root 3;
            }
            type uint16 {
              range "0..10800";
            }
            units "s";
            default "0";
            status deprecated;
            description
              "Preemption delay.";
          }
          leaf adver-interval {
            type uint32 {
              range "100..255000";
            }
            units "ms";
            default "1000";
            status deprecated;
            description
              "Configure an interval (in milliseconds) at which the master sends VRRP advertisement packets. This interval must be a multiple of 1000. If the device supports fast advertisement sending, this interval can be set to 100ms 200ms or 500ms.";
          }
          leaf isplain {
            when "../authentication-mode='simple'" {
              tailf:xpath-root 3;
            }
            type boolean;
            must "../authentication-mode='simple' and ../authentication-key" {
              tailf:xpath-root 3;
            }
            default "false";
            status deprecated;
            description
              "Enable/disable selecting the display mode of an authentication key.";
          }
          leaf authentication-key {
            when "not(../authentication-mode='none')" {
              tailf:xpath-root 3;
            }
            type pub-type:password {
              length "1..128";
              pattern '(\S+.*\S+|\S*)';
            }
            must "(../authentication-mode='none' and not(../authentication-key)) or (not(../authentication-mode='none') and ../authentication-key)" {
              tailf:xpath-root 3;
            }
            status deprecated;
            description
              "Authentication key, which is set based on the authentication type. Value description: If non-authentication is specified, the value is empty. If simple authentication, MD5 authentication, or HMAC-SHA256 authentication is specified, the value is a string with the length ranging from 1 to 8 bytes or a ciphertext password with the corresponding length.";
          }
          leaf authentication-mode {
            type vrrpauthen-mode;
            must "((not(/ifm:ifm/ifm:interfaces/ifm:interface[ifm:name = current()/../if-name]/ifm:type='LoopBack') and not(../authentication-mode='hmac-sha256')) or ((/ifm:ifm/ifm:interfaces/ifm:interface[ifm:name = current()/../if-name]/ifm:type='LoopBack') and not(../authentication-mode='simple'))) and ((../authentication-mode='none' and not(../authentication-key)) or (not(../authentication-mode='none') and ../authentication-key))" {
              tailf:xpath-root 3;
            }
            default "none";
            status deprecated;
            description
              "Authentication type used for VRRP packet exchanges between virtual routers. The values are as follows: noAuthentication, simpleTextPassword, md5Authentication. The default value is noAuthentication.";
          }
          leaf hold-multi {
            type uint8 {
              range "3..10";
            }
            default "3";
            status deprecated;
            description
              "Set the hello packet sending interval multiplier.";
          }
          leaf backup-forward {
            type boolean;
            default "false";
            status deprecated;
            description
              "Enable/disable VRRP backup forward mode.";
          }
          leaf fast-resume {
            when '../admin-flag' {
              tailf:xpath-root 3;
            }
            type boolean;
            default "false";
            status deprecated;
            description
              "Enable/disable VRRP fast resume mode.";
          }
          leaf v3-sendmode {
            when "not(/vrrp:vrrp/vrrp:global/vrrp:version='v2')" {
              tailf:xpath-root 3;
            }
            type vrrp-v3-sendmode;
            default "v3-only";
            status deprecated;
            description
              "VRRP advertisement packet mode on the interface.";
          }
          choice vrrp-type {
            status deprecated;
            description
              "Type of VRRP.";
            case member-vrrp {
              status deprecated;
              description
                "Member VRRP.";
              leaf admin-id {
                type uint8 {
                  range "1..255";
                }
                must '../admin-if-name' {
                  tailf:xpath-root 3;
                }
                status deprecated;
                description
                  "Tracked MVRRP ID.";
              }
              leaf admin-if-name {
                type leafref {
                  path "/ncs:devices/ncs:device/ncs:config/ifm:ifm/ifm:interfaces/ifm:interface/ifm:name" {
                    tailf:xpath-root 3;
                  }
                }
                must '../admin-id' {
                  tailf:xpath-root 3;
                }
                status deprecated;
                description
                  "Tracked MVRRP interface name.";
              }
            }
            case admin-vrrp {
              status deprecated;
              description
                "Admin VRRP.";
              leaf admin-flag {
                type empty;
                status deprecated;
                description
                  "Management VRRP.";
              }
              leaf admin-ignore-ifdown {
                when '../admin-flag' {
                  tailf:xpath-root 3;
                }
                type boolean;
                default "false";
                status deprecated;
                description
                  "Enable/disable ignoring an interface down event.";
              }
            }
          }
          // NCS drop config false leaf type
          // NCS drop config false leaf state
          // NCS drop config false leaf 'create-time'
          // NCS drop config false leaf 'last-change-time'
          container virtual-ips {
            status deprecated;
            description
              "List of IP address table related to virtual routers. A VRRP backup group can have 0 to 16 extended virtual IP addresses.";
            list virtual-ip {
              key "address";
              max-elements 16;
              status deprecated;
              description
                "Configure virtual IP address configuration. A VRRP backup group can have 0 to 16 extended virtual IP addresses.";
              leaf address {
                type inet:ipv4-address-no-zone;
                status deprecated;
                description
                  "Virtual IP address.";
              }
            }
          }
          container track-interfaces {
            when 'not(../admin-id)' {
              tailf:xpath-root 3;
            }
            status deprecated;
            description
              "List of interfaces tracked by a VRRP backup group. A VRRP backup group can track a maximum of 16 interfaces.";
            list track-interface {
              key "ifname";
              max-elements 16;
              status deprecated;
              description
                "Configure VRRP backup group tracking interface.";
              leaf ifname {
                type leafref {
                  path "/ncs:devices/ncs:device/ncs:config/ifm:ifm/ifm:interfaces/ifm:interface/ifm:name" {
                    tailf:xpath-root 3;
                  }
                }
                status deprecated;
                description
                  "Name of the interface tracked by the VRRP backup group.";
              }
              leaf track-mode {
                type vrrptrack-mode;
                default "reduce";
                status deprecated;
                description
                  "Mode in which the VRRP backup group tracks the interface.";
              }
              leaf priority-change {
                type uint8 {
                  range "1..255";
                }
                default "10";
                status deprecated;
                description
                  "Value by which the priority increases or reduces when the VRRP backup group tracks the interface.";
              }
            }
          }
          container track-bfds {
            when 'not(../admin-id)' {
              tailf:xpath-root 3;
            }
            status deprecated;
            description
              "List of BFD sessions tracked by the VRRP backup group.";
            list track-bfd {
              key "session-name session-type";
              max-elements 17;
              status deprecated;
              description
                "Configure VRRP backup group tracking BFD session.";
              leaf session-name {
                type leafref {
                  path "/ncs:devices/ncs:device/ncs:config/bfd:bfd/bfd:sessions/bfd:session/bfd:name" {
                    tailf:xpath-root 3;
                  }
                }
                status deprecated;
                description
                  "Name of the BFD session tracked by the VRRP backup group.";
              }
              leaf session-type {
                type vrrp-bfd-type;
                status deprecated;
                description
                  "Type of the BFD session tracked by the VRRP backup group.";
              }
              leaf track-mode {
                when "../session-type='normal'" {
                  tailf:xpath-root 3;
                }
                type vrrp-track-mode;
                default "reduce";
                status deprecated;
                description
                  "Mode in which the VRRP backup group tracks the BFD session.";
              }
              leaf priority-change {
                when "../session-type='normal'" {
                  tailf:xpath-root 3;
                }
                type uint8 {
                  range "1..255";
                }
                default "10";
                status deprecated;
                description
                  "Value by which the priority increases or reduces when the VRRP backup group tracks the common BFD session.";
              }
              // NCS drop config false leaf 'session-id'
              // NCS drop config false leaf 'session-state'
            }
          }
        }
      }
    }
  }
  augment "/ncs:devices/ncs:template/ncs:ned-id/ncs:config/ifm:ifm/ifm:interfaces/ifm:interface" {
    description
      "VRRP configurations on interface.";
    container vrrp {
      description
        "Configure virtual router redundancy protocol.";
      container backup-groups {
        // NCS drop when statement
        description
          "Configure VRRP backup groups under interface. The configured attributes apply to all backup groups on the interface.";
        leaf ttlcheck-flag {
          type string;
          // NCS drop default statement
          description
            "Enable/disable TTL check which is performed for a received VRRP advertisement packet. The check is successful only when the TTL value is 255. By default, a TTL check is performed.";
        }
        leaf recover-delay {
          type string;
          units "s";
          // NCS drop default statement
          description
            "Delay in recovering after an interface goes Up. The delay is used for interface flapping suppression.";
        }
        leaf arpsend-simple {
          type string;
          // NCS drop default statement
          description
            "Enable/disable simple send mode for gratuitous ARP packets.";
        }
        choice advertise-send-mode {
          // NCS drop when statement
          description
            "VRRP backup groups send packets mode.";
          case all-subvlans {
            description
              "Packets are sent in all sub-VLANs of the super VLAN.";
            leaf sendmode-all {
              type empty;
              description
                "Packets are sent in all sub-VLANs of the super VLAN.";
            }
          }
          case one-subvlan {
            description
              "Packets are sent in one sub-VLAN of the super VLAN.";
            leaf send-subvlanid {
              type string;
              description
                "Specifies the ID of a sub-VLAN in which packets are sent. By default, packets are sent from the active VLAN with the minimum ID. This configuration is valid only for a super VLAN.";
            }
          }
        }
      }
      container track-admins {
        description
          "List of service interfaces.";
        list track-admin {
          // NCS patched for predictable order
          ordered-by user;
          key "id if-name";
          // NCS drop max-elements statement
          description
            "Configure service interface.";
          leaf id {
            type string;
            description
              "Tracked MVRRP ID.";
          }
          leaf if-name {
            type string;
            description
              "Tracked MVRRP interface name.";
          }
        }
      }
    }
  }
  augment "/ncs:devices/ncs:device/ncs:live-status/ifm:ifm/ifm:interfaces/ifm:interface" {
    description
      "VRRP configurations on interface.";
    container vrrp {
      tailf:ncs-device-type "netconf";
      tailf:display-when "not(../../../../../ncs:module) or ../../../../../ncs:module[ncs:name='huawei-vrrp'] or (../../../../../ncs:live-status-protocol[not(ncs:capability)]) or (../../../../../ncs:live-status-protocol/ncs:capability/ncs:module[.='huawei-vrrp'])";
      description
        "Configure virtual router redundancy protocol.";
      container backup-groups {
        // NCS drop when statement
        description
          "Configure VRRP backup groups under interface. The configured attributes apply to all backup groups on the interface.";
        leaf ttlcheck-flag {
          type boolean;
          // NCS drop default statement
          description
            "Enable/disable TTL check which is performed for a received VRRP advertisement packet. The check is successful only when the TTL value is 255. By default, a TTL check is performed.";
        }
        leaf recover-delay {
          type uint16 {
            range "0..3600";
          }
          units "s";
          // NCS drop default statement
          description
            "Delay in recovering after an interface goes Up. The delay is used for interface flapping suppression.";
        }
        leaf arpsend-simple {
          type boolean;
          // NCS drop default statement
          description
            "Enable/disable simple send mode for gratuitous ARP packets.";
        }
        choice advertise-send-mode {
          // NCS drop when statement
          description
            "VRRP backup groups send packets mode.";
          case all-subvlans {
            description
              "Packets are sent in all sub-VLANs of the super VLAN.";
            leaf sendmode-all {
              type empty;
              description
                "Packets are sent in all sub-VLANs of the super VLAN.";
            }
          }
          case one-subvlan {
            description
              "Packets are sent in one sub-VLAN of the super VLAN.";
            leaf send-subvlanid {
              type uint16 {
                range "1..4094";
              }
              description
                "Specifies the ID of a sub-VLAN in which packets are sent. By default, packets are sent from the active VLAN with the minimum ID. This configuration is valid only for a super VLAN.";
            }
          }
        }
      }
      container track-admins {
        description
          "List of service interfaces.";
        list track-admin {
          key "id if-name";
          // NCS drop max-elements statement
          description
            "Configure service interface.";
          leaf id {
            type uint8 {
              range "1..255";
            }
            description
              "Tracked MVRRP ID.";
          }
          leaf if-name {
            type leafref {
              path "/ncs:devices/ncs:device/ncs:live-status/ifm:ifm/ifm:interfaces/ifm:interface/ifm:name" {
                tailf:xpath-root 3;
              }
            }
            description
              "Tracked MVRRP interface name.";
          }
        }
      }
    }
  }
  augment "/ncs:devices/ncs:device/ncs:config/ifm:ifm/ifm:interfaces/ifm:interface" {
    description
      "VRRP configurations on interface.";
    container vrrp {
      tailf:ncs-device-type "netconf";
      tailf:display-when "not(../../../../../ncs:module) or ../../../../../ncs:module[ncs:name='huawei-vrrp']";
      description
        "Configure virtual router redundancy protocol.";
      container backup-groups {
        when '../../ip:ipv4/vrrp:vrrp/vrrp:groups/vrrp:group/vrrp:id' {
          tailf:xpath-root 3;
        }
        description
          "Configure VRRP backup groups under interface. The configured attributes apply to all backup groups on the interface.";
        leaf ttlcheck-flag {
          type boolean;
          default "true";
          description
            "Enable/disable TTL check which is performed for a received VRRP advertisement packet. The check is successful only when the TTL value is 255. By default, a TTL check is performed.";
        }
        leaf recover-delay {
          type uint16 {
            range "0..3600";
          }
          units "s";
          default "0";
          description
            "Delay in recovering after an interface goes Up. The delay is used for interface flapping suppression.";
        }
        leaf arpsend-simple {
          type boolean;
          default "false";
          description
            "Enable/disable simple send mode for gratuitous ARP packets.";
        }
        choice advertise-send-mode {
          when "../../ifm:type='Vlanif'" {
            tailf:xpath-root 3;
          }
          description
            "VRRP backup groups send packets mode.";
          case all-subvlans {
            description
              "Packets are sent in all sub-VLANs of the super VLAN.";
            leaf sendmode-all {
              type empty;
              description
                "Packets are sent in all sub-VLANs of the super VLAN.";
            }
          }
          case one-subvlan {
            description
              "Packets are sent in one sub-VLAN of the super VLAN.";
            leaf send-subvlanid {
              type uint16 {
                range "1..4094";
              }
              description
                "Specifies the ID of a sub-VLAN in which packets are sent. By default, packets are sent from the active VLAN with the minimum ID. This configuration is valid only for a super VLAN.";
            }
          }
        }
      }
      container track-admins {
        description
          "List of service interfaces.";
        list track-admin {
          key "id if-name";
          max-elements 1;
          description
            "Configure service interface.";
          leaf id {
            type uint8 {
              range "1..255";
            }
            description
              "Tracked MVRRP ID.";
          }
          leaf if-name {
            type leafref {
              path "/ncs:devices/ncs:device/ncs:config/ifm:ifm/ifm:interfaces/ifm:interface/ifm:name" {
                tailf:xpath-root 3;
              }
            }
            description
              "Tracked MVRRP interface name.";
          }
        }
      }
    }
  }
  augment "/ncs:devices/ncs:template/ncs:ned-id/ncs:config/ifm:ifm/ifm:interfaces/ifm:interface/ip:ipv4" {
    description
      "VRRP configurations on interface.";
    container vrrp {
      description
        "Configure all VRRP backup groups.";
      container groups {
        description
          "List of all VRRP backup groups.";
        list group {
          // NCS patched for predictable order
          ordered-by user;
          key "id";
          description
            "Configure VRRP operations on a device. It lists a series of VRRP operation entries. You can use this table to query the VRRP configuration on the device. In addition, you can create virtual router instances and modify the configuration.";
          leaf id {
            type string;
            description
              "VRRP backup group ID.";
          }
          leaf priority {
            type string;
            // NCS drop default statement
            description
              "Configured VRRP priority. The value ranges from 1 to 254. A larger value indicates a higher priority.";
          }
          container preempt {
            description
              "Configure a higher priority VRRP backup router to preempt a lower priority VRRP master.";
            leaf preempt-enable {
              type string;
              // NCS drop default statement
              description
                "Enable/disable whether a high priority router can preempt the master state.";
            }
            leaf delay-time {
              // NCS drop when statement
              type string;
              units "s";
              // NCS drop default statement
              description
                "Preemption delay.";
            }
          }
          leaf adver-interval {
            type string;
            units "ms";
            // NCS drop default statement
            description
              "Configure an interval at which the master sends VRRP advertisement packets. This interval must be a multiple of 1000. If the device supports fast advertisement sending, this interval can be set to 100ms 200ms or 500 ms.";
          }
          leaf authentication-mode {
            type ncs_template_vrrpauthen-mode;
            // NCS drop must statement
            // NCS drop default statement
            description
              "Authentication type used for VRRP packet exchanges between virtual routers. The values are as follows: noAuthentication, simpleTextPassword, md5Authentication.";
          }
          leaf isplain {
            // NCS drop when statement
            type string;
            // NCS drop must statement
            // NCS drop default statement
            description
              "Enable/disable selecting the display mode of an authentication key.";
          }
          leaf authentication-key {
            // NCS drop when statement
            type pub-type:ncs_template_password;
            // NCS drop must statement
            description
              "Authentication key, which is set based on the authentication type. Value description: If non-authentication is specified, the value is empty. If simple authentication, MD5 authentication, or HMAC-SHA256 authentication is specified, the value is a string with the length ranging from 1 to 8 bytes or a ciphertext password with the corresponding length.";
          }
          leaf link-bfddown-num {
            type string;
            description
              "Specify the threshold for the number of link BFD sessions in the Down state tracked by the MVRRP backup group.";
          }
          leaf hold-multiper {
            type string;
            // NCS drop default statement
            description
              "Set the hello packet sending interval multiplier.";
          }
          leaf backup-forward {
            type string;
            // NCS drop default statement
            description
              "Enable/disable VRRP backup forward mode.";
          }
          leaf fast-resume {
            // NCS drop when statement
            type string;
            // NCS drop default statement
            description
              "Enable/disable VRRP fast resume mode.";
          }
          leaf v3-sendmode {
            // NCS drop when statement
            type ncs_template_vrrp-v3-sendmode;
            // NCS drop default statement
            description
              "VRRP advertisement packet mode on the interface.";
          }
          choice vrrp-type {
            description
              "Type of VRRP.";
            case member-vrrp {
              description
                "Member VRRP.";
              leaf admin-id {
                type string;
                // NCS drop must statement
                description
                  "Tracked MVRRP ID.";
              }
              leaf admin-if-name {
                type string;
                // NCS drop must statement
                description
                  "Tracked MVRRP interface name.";
              }
              leaf unflowdown {
                // NCS drop when statement
                type string;
                // NCS drop default statement
                description
                  "Enable/disable the flowdown function for service VRRP.";
              }
            }
            case admin-vrrp {
              description
                "Admin VRRP.";
              leaf admin-flag {
                type empty;
                description
                  "Management VRRP.";
              }
              leaf admin-ignore-ifdown {
                // NCS drop when statement
                type string;
                // NCS drop default statement
                description
                  "Enable/disable ignoring an interface down event.";
              }
              leaf init-state-holdtime {
                // NCS drop when statement
                type string;
                units "s";
                description
                  "Hold time of the Initialize state after the management VRRP backup group is configured to ignore an interface down event.";
              }
            }
          }
          // NCS drop config false leaf type
          // NCS drop config false leaf state
          // NCS drop config false leaf 'create-time'
          // NCS drop config false leaf 'last-change-time'
          container virtual-ips {
            description
              "List of IP address table related to virtual routers. A VRRP backup group can have 0 to 16 extended virtual IP addresses.";
            list virtual-ip {
              // NCS patched for predictable order
              ordered-by user;
              key "address";
              // NCS drop max-elements statement
              description
                "Configure virtual IP address configuration. A VRRP backup group can have 0 to 16 extended virtual IP addresses.";
              leaf address {
                type string;
                description
                  "Virtual IP address.";
              }
              leaf mask {
                // NCS drop when statement
                type string;
                description
                  "Virtual IP address mask.";
              }
              leaf vgmp-role {
                type ncs_template_vgmp-type;
                // NCS drop default statement
                description
                  "The configuration state of VRRP.";
              }
            }
          }
          container track-interfaces {
            // NCS drop when statement
            description
              "List of interfaces tracked by a VRRP backup group. A VRRP backup group can track a maximum of 16 interfaces.";
            list track-interface {
              // NCS patched for predictable order
              ordered-by user;
              key "if-name";
              // NCS drop max-elements statement
              description
                "Configure interface tracked by a VRRP backup group.";
              leaf if-name {
                type string;
                description
                  "Name of the interface tracked by the VRRP backup group.";
              }
              leaf priority-change {
                type string;
                // NCS drop mandatory statement
                description
                  "Value by which the priority increases or reduces when the VRRP backup group tracks the interface.";
              }
              leaf track-mode {
                type ncs_template_vrrptrack-mode;
                // NCS drop default statement
                description
                  "Mode in which the VRRP backup group tracks the interface.";
              }
            }
          }
          container track-bfds {
            // NCS drop when statement
            description
              "List of BFD sessions tracked by the VRRP backup group.";
            list track-bfd {
              // NCS patched for predictable order
              ordered-by user;
              key "session-name session-type";
              // NCS drop max-elements statement
              description
                "Configure BFD session tracked by the VRRP backup group.";
              leaf session-name {
                type string;
                description
                  "Name of the BFD session tracked by the VRRP backup group.";
              }
              leaf session-type {
                type ncs_template_vrrp-bfd-type;
                description
                  "Type of the BFD session tracked by the VRRP backup group.";
              }
              leaf priority-change {
                // NCS drop when statement
                type string;
                // NCS drop mandatory statement
                description
                  "Value by which the priority increases or reduces when the VRRP backup group tracks the common BFD session.";
              }
              leaf track-mode {
                // NCS drop when statement
                type ncs_template_vrrp-track-mode;
                // NCS drop default statement
                description
                  "Mode in which the VRRP backup group tracks the BFD session.";
              }
              // NCS drop config false leaf 'session-id'
              // NCS drop config false leaf 'session-state'
            }
          }
          container track-mtgrps {
            description
              "List of VRRP backup groups to track interface monitoring groups.";
            list track-mtgrp {
              // NCS patched for predictable order
              ordered-by user;
              key "monitor-group-name";
              // NCS drop max-elements statement
              description
                "Configure VRRP backup groups to track interface monitoring groups.";
              leaf monitor-group-name {
                type string;
                description
                  "Name of the interface monitoring group tracked by a VRRP backup group.";
              }
              leaf failure-ratio {
                type string;
                // NCS drop mandatory statement
                description
                  "Link failure ratio threshold for an interface monitoring group.";
              }
              leaf priority-change {
                // NCS drop when statement
                type string;
                // NCS drop mandatory statement
                description
                  "Value by which the priority of the VRRP backup group reduces if the status of the tracked interface monitoring group changes to Down.";
              }
              leaf track-mode {
                type ncs_template_mtgrptrack-mode;
                // NCS drop default statement
                description
                  "Mode in which a VRRP backup group tracks an interface monitoring group.";
              }
            }
          }
          container track-nqas {
            description
              "List of NQA sessions tracked by the VRRP backup group.";
            list track-nqa {
              // NCS patched for predictable order
              ordered-by user;
              key "admin-name test-name";
              // NCS drop max-elements statement
              description
                "Configure a VRRP backup group to track NQA test instances.";
              leaf admin-name {
                type string;
                description
                  "Name of the tracked NQA administrator.";
              }
              leaf test-name {
                type string;
                // NCS drop must statement
                description
                  "Name of the tracked NQA test instance.";
              }
              leaf priority-change {
                type string;
                // NCS drop default statement
                description
                  "Value by which the priority reduces when the VRRP backup group tracks NQA.";
              }
            }
          }
          container track-ip-routes {
            description
              "List of VRRP backup groups to track IP routes.";
            list track-ip-route {
              // NCS patched for predictable order
              ordered-by user;
              key "vpn-name ip-address mask-length";
              description
                "Configure VRRP backup groups to track IP route.";
              leaf vpn-name {
                type string;
                description
                  "VPN instance name.";
              }
              leaf ip-address {
                type string;
                description
                  "Specifies the destination IP address of a route to be tracked.";
              }
              leaf mask-length {
                type string;
                // NCS drop must statement
                description
                  "Specifies the destination IP address mask length of a route to be tracked.";
              }
              leaf priority-change {
                type string;
                // NCS drop mandatory statement
                description
                  "Value by which the priority increases or reduces when the VRRP backup group tracks IP route.";
              }
              leaf track-mode {
                type ncs_template_vrrp-track-mode;
                // NCS drop default statement
                description
                  "Mode in which the VRRP backup group tracks IP route.";
              }
            }
          }
        }
      }
    }
  }
  augment "/ncs:devices/ncs:device/ncs:live-status/ifm:ifm/ifm:interfaces/ifm:interface/ip:ipv4" {
    description
      "VRRP configurations on interface.";
    container vrrp {
      tailf:ncs-device-type "netconf";
      tailf:display-when "not(../../../../../../ncs:module) or ../../../../../../ncs:module[ncs:name='huawei-vrrp'] or (../../../../../../ncs:live-status-protocol[not(ncs:capability)]) or (../../../../../../ncs:live-status-protocol/ncs:capability/ncs:module[.='huawei-vrrp'])";
      description
        "Configure all VRRP backup groups.";
      container groups {
        description
          "List of all VRRP backup groups.";
        list group {
          key "id";
          description
            "Configure VRRP operations on a device. It lists a series of VRRP operation entries. You can use this table to query the VRRP configuration on the device. In addition, you can create virtual router instances and modify the configuration.";
          leaf id {
            type uint8 {
              range "1..255";
            }
            description
              "VRRP backup group ID.";
          }
          leaf priority {
            type uint8 {
              range "1..254";
            }
            // NCS drop default statement
            description
              "Configured VRRP priority. The value ranges from 1 to 254. A larger value indicates a higher priority.";
          }
          container preempt {
            description
              "Configure a higher priority VRRP backup router to preempt a lower priority VRRP master.";
            leaf preempt-enable {
              type boolean;
              // NCS drop default statement
              description
                "Enable/disable whether a high priority router can preempt the master state.";
            }
            leaf delay-time {
              // NCS drop when statement
              type uint16 {
                range "0..10800";
              }
              units "s";
              // NCS drop default statement
              description
                "Preemption delay.";
            }
          }
          leaf adver-interval {
            type uint32 {
              range "100..255000";
            }
            units "ms";
            // NCS drop default statement
            description
              "Configure an interval at which the master sends VRRP advertisement packets. This interval must be a multiple of 1000. If the device supports fast advertisement sending, this interval can be set to 100ms 200ms or 500 ms.";
          }
          leaf authentication-mode {
            type live_ncs_vrrpauthen-mode;
            // NCS drop must statement
            // NCS drop default statement
            description
              "Authentication type used for VRRP packet exchanges between virtual routers. The values are as follows: noAuthentication, simpleTextPassword, md5Authentication.";
          }
          leaf isplain {
            // NCS drop when statement
            type boolean;
            // NCS drop must statement
            // NCS drop default statement
            description
              "Enable/disable selecting the display mode of an authentication key.";
          }
          leaf authentication-key {
            // NCS drop when statement
            type pub-type:live_ncs_password;
            // NCS drop must statement
            description
              "Authentication key, which is set based on the authentication type. Value description: If non-authentication is specified, the value is empty. If simple authentication, MD5 authentication, or HMAC-SHA256 authentication is specified, the value is a string with the length ranging from 1 to 8 bytes or a ciphertext password with the corresponding length.";
          }
          leaf link-bfddown-num {
            type uint8 {
              range "1..8";
            }
            description
              "Specify the threshold for the number of link BFD sessions in the Down state tracked by the MVRRP backup group.";
          }
          leaf hold-multiper {
            type uint8 {
              range "3..10";
            }
            // NCS drop default statement
            description
              "Set the hello packet sending interval multiplier.";
          }
          leaf backup-forward {
            type boolean;
            // NCS drop default statement
            description
              "Enable/disable VRRP backup forward mode.";
          }
          leaf fast-resume {
            // NCS drop when statement
            type boolean;
            // NCS drop default statement
            description
              "Enable/disable VRRP fast resume mode.";
          }
          leaf v3-sendmode {
            // NCS drop when statement
            type live_ncs_vrrp-v3-sendmode;
            // NCS drop default statement
            description
              "VRRP advertisement packet mode on the interface.";
          }
          choice vrrp-type {
            description
              "Type of VRRP.";
            case member-vrrp {
              description
                "Member VRRP.";
              leaf admin-id {
                type uint8 {
                  range "1..255";
                }
                // NCS drop must statement
                description
                  "Tracked MVRRP ID.";
              }
              leaf admin-if-name {
                type leafref {
                  path "/ncs:devices/ncs:device/ncs:live-status/ifm:ifm/ifm:interfaces/ifm:interface/ifm:name" {
                    tailf:xpath-root 3;
                  }
                }
                // NCS drop must statement
                description
                  "Tracked MVRRP interface name.";
              }
              leaf unflowdown {
                // NCS drop when statement
                type boolean;
                // NCS drop default statement
                description
                  "Enable/disable the flowdown function for service VRRP.";
              }
            }
            case admin-vrrp {
              description
                "Admin VRRP.";
              leaf admin-flag {
                type empty;
                description
                  "Management VRRP.";
              }
              leaf admin-ignore-ifdown {
                // NCS drop when statement
                type boolean;
                // NCS drop default statement
                description
                  "Enable/disable ignoring an interface down event.";
              }
              leaf init-state-holdtime {
                // NCS drop when statement
                type uint32 {
                  range "0..3600";
                }
                units "s";
                description
                  "Hold time of the Initialize state after the management VRRP backup group is configured to ignore an interface down event.";
              }
            }
          }
          leaf type {
            type live_ncs_vrrp-type;
            // NCS drop default statement
            description
              "Type of a VRRP backup group.";
          }
          leaf state {
            type live_ncs_vrrp-oper-state;
            description
              "Running status of the virtual router. This object has three defined values.
               Initialize: The virtual router is waiting for a startup event.
               Backup: The virtual router is monitoring the availability of the master router.
               Master: The virtual router is forwarding packets for IP addresses that are associated with this router.";
          }
          leaf create-time {
            type yang:date-and-time;
            description
              "Time when the VRRP backup group was created.";
          }
          leaf last-change-time {
            type yang:date-and-time;
            description
              "Time when the status of the VRRP backup group last changed.";
          }
          container virtual-ips {
            description
              "List of IP address table related to virtual routers. A VRRP backup group can have 0 to 16 extended virtual IP addresses.";
            list virtual-ip {
              key "address";
              // NCS drop max-elements statement
              description
                "Configure virtual IP address configuration. A VRRP backup group can have 0 to 16 extended virtual IP addresses.";
              leaf address {
                type inet:ipv4-address-no-zone;
                description
                  "Virtual IP address.";
              }
              leaf mask {
                // NCS drop when statement
                type inet:ipv4-address-no-zone;
                description
                  "Virtual IP address mask.";
              }
              leaf vgmp-role {
                type live_ncs_vgmp-type;
                // NCS drop default statement
                description
                  "The configuration state of VRRP.";
              }
            }
          }
          container track-interfaces {
            // NCS drop when statement
            description
              "List of interfaces tracked by a VRRP backup group. A VRRP backup group can track a maximum of 16 interfaces.";
            list track-interface {
              key "if-name";
              // NCS drop max-elements statement
              description
                "Configure interface tracked by a VRRP backup group.";
              leaf if-name {
                type leafref {
                  path "/ncs:devices/ncs:device/ncs:live-status/ifm:ifm/ifm:interfaces/ifm:interface/ifm:name" {
                    tailf:xpath-root 3;
                  }
                }
                description
                  "Name of the interface tracked by the VRRP backup group.";
              }
              leaf priority-change {
                type uint8 {
                  range "1..255";
                }
                // NCS drop mandatory statement
                description
                  "Value by which the priority increases or reduces when the VRRP backup group tracks the interface.";
              }
              leaf track-mode {
                type live_ncs_vrrptrack-mode;
                // NCS drop default statement
                description
                  "Mode in which the VRRP backup group tracks the interface.";
              }
            }
          }
          container track-bfds {
            // NCS drop when statement
            description
              "List of BFD sessions tracked by the VRRP backup group.";
            list track-bfd {
              key "session-name session-type";
              // NCS drop max-elements statement
              description
                "Configure BFD session tracked by the VRRP backup group.";
              leaf session-name {
                type leafref {
                  path "/ncs:devices/ncs:device/ncs:live-status/bfd:bfd/bfd:sessions/bfd:session/bfd:name" {
                    tailf:xpath-root 3;
                  }
                }
                description
                  "Name of the BFD session tracked by the VRRP backup group.";
              }
              leaf session-type {
                type live_ncs_vrrp-bfd-type;
                description
                  "Type of the BFD session tracked by the VRRP backup group.";
              }
              leaf priority-change {
                // NCS drop when statement
                type uint8 {
                  range "1..255";
                }
                // NCS drop mandatory statement
                description
                  "Value by which the priority increases or reduces when the VRRP backup group tracks the common BFD session.";
              }
              leaf track-mode {
                // NCS drop when statement
                type live_ncs_vrrp-track-mode;
                // NCS drop default statement
                description
                  "Mode in which the VRRP backup group tracks the BFD session.";
              }
              leaf session-id {
                type uint32 {
                  range "1..32768";
                }
                description
                  "ID of the BFD session tracked by the VRRP backup group.";
              }
              leaf session-state {
                type live_ncs_vrrp-track-bfd-state;
                description
                  "State of the BFD session tracked by the VRRP backup group.";
              }
            }
          }
          container track-mtgrps {
            description
              "List of VRRP backup groups to track interface monitoring groups.";
            list track-mtgrp {
              key "monitor-group-name";
              // NCS drop max-elements statement
              description
                "Configure VRRP backup groups to track interface monitoring groups.";
              leaf monitor-group-name {
                type leafref {
                  path "/ncs:devices/ncs:device/ncs:live-status/monitor-group:monitor-group/monitor-group:groups/monitor-group:group/monitor-group:name" {
                    tailf:xpath-root 3;
                  }
                }
                description
                  "Name of the interface monitoring group tracked by a VRRP backup group.";
              }
              leaf failure-ratio {
                type uint8 {
                  range "1..100";
                }
                // NCS drop mandatory statement
                description
                  "Link failure ratio threshold for an interface monitoring group.";
              }
              leaf priority-change {
                // NCS drop when statement
                type uint8 {
                  range "1..255";
                }
                // NCS drop mandatory statement
                description
                  "Value by which the priority of the VRRP backup group reduces if the status of the tracked interface monitoring group changes to Down.";
              }
              leaf track-mode {
                type live_ncs_mtgrptrack-mode;
                // NCS drop default statement
                description
                  "Mode in which a VRRP backup group tracks an interface monitoring group.";
              }
            }
          }
          container track-nqas {
            description
              "List of NQA sessions tracked by the VRRP backup group.";
            list track-nqa {
              key "admin-name test-name";
              // NCS drop max-elements statement
              description
                "Configure a VRRP backup group to track NQA test instances.";
              leaf admin-name {
                type leafref {
                  path "/ncs:devices/ncs:device/ncs:live-status/nqa:nqa/nqa:instances/nqa:instance/nqa:admin-name" {
                    tailf:xpath-root 3;
                  }
                }
                description
                  "Name of the tracked NQA administrator.";
              }
              leaf test-name {
                type leafref {
                  path "/ncs:devices/ncs:device/ncs:live-status/nqa:nqa/nqa:instances/nqa:instance/nqa:test-name" {
                    tailf:xpath-root 3;
                  }
                }
                // NCS drop must statement
                description
                  "Name of the tracked NQA test instance.";
              }
              leaf priority-change {
                type uint8 {
                  range "1..255";
                }
                // NCS drop default statement
                description
                  "Value by which the priority reduces when the VRRP backup group tracks NQA.";
              }
            }
          }
          container track-ip-routes {
            description
              "List of VRRP backup groups to track IP routes.";
            list track-ip-route {
              key "vpn-name ip-address mask-length";
              description
                "Configure VRRP backup groups to track IP route.";
              leaf vpn-name {
                type leafref {
                  path "/ncs:devices/ncs:device/ncs:live-status/ni:network-instance/ni:instances/ni:instance/ni:name" {
                    tailf:xpath-root 3;
                  }
                }
                description
                  "VPN instance name.";
              }
              leaf ip-address {
                type inet:ipv4-address-no-zone;
                description
                  "Specifies the destination IP address of a route to be tracked.";
              }
              leaf mask-length {
                type uint8 {
                  range "0..32";
                }
                // NCS drop must statement
                description
                  "Specifies the destination IP address mask length of a route to be tracked.";
              }
              leaf priority-change {
                type uint8 {
                  range "1..255";
                }
                // NCS drop mandatory statement
                description
                  "Value by which the priority increases or reduces when the VRRP backup group tracks IP route.";
              }
              leaf track-mode {
                type live_ncs_vrrp-track-mode;
                // NCS drop default statement
                description
                  "Mode in which the VRRP backup group tracks IP route.";
              }
            }
          }
        }
      }
    }
  }
  augment "/ncs:devices/ncs:device/ncs:config/ifm:ifm/ifm:interfaces/ifm:interface/ip:ipv4" {
    description
      "VRRP configurations on interface.";
    container vrrp {
      tailf:ncs-device-type "netconf";
      tailf:display-when "not(../../../../../../ncs:module) or ../../../../../../ncs:module[ncs:name='huawei-vrrp']";
      description
        "Configure all VRRP backup groups.";
      container groups {
        description
          "List of all VRRP backup groups.";
        list group {
          key "id";
          description
            "Configure VRRP operations on a device. It lists a series of VRRP operation entries. You can use this table to query the VRRP configuration on the device. In addition, you can create virtual router instances and modify the configuration.";
          leaf id {
            type uint8 {
              range "1..255";
            }
            description
              "VRRP backup group ID.";
          }
          leaf priority {
            type uint8 {
              range "1..254";
            }
            default "100";
            description
              "Configured VRRP priority. The value ranges from 1 to 254. A larger value indicates a higher priority.";
          }
          container preempt {
            description
              "Configure a higher priority VRRP backup router to preempt a lower priority VRRP master.";
            leaf preempt-enable {
              type boolean;
              default "true";
              description
                "Enable/disable whether a high priority router can preempt the master state.";
            }
            leaf delay-time {
              when "../preempt-enable='true'" {
                tailf:xpath-root 3;
              }
              type uint16 {
                range "0..10800";
              }
              units "s";
              default "0";
              description
                "Preemption delay.";
            }
          }
          leaf adver-interval {
            type uint32 {
              range "100..255000";
            }
            units "ms";
            default "1000";
            description
              "Configure an interval at which the master sends VRRP advertisement packets. This interval must be a multiple of 1000. If the device supports fast advertisement sending, this interval can be set to 100ms 200ms or 500 ms.";
          }
          leaf authentication-mode {
            type vrrpauthen-mode;
            must "((not(../../../../../ifm:type='LoopBack') and not(../authentication-mode='hmac-sha256')) or ((../../../../../ifm:type='LoopBack') and not(../authentication-mode='simple'))) and ((../authentication-mode='none' and not(../authentication-key)) or (not(../authentication-mode='none') and ../authentication-key))" {
              tailf:xpath-root 3;
            }
            default "none";
            description
              "Authentication type used for VRRP packet exchanges between virtual routers. The values are as follows: noAuthentication, simpleTextPassword, md5Authentication.";
          }
          leaf isplain {
            when "../authentication-mode='simple'" {
              tailf:xpath-root 3;
            }
            type boolean;
            must "../authentication-mode='simple' and ../authentication-key" {
              tailf:xpath-root 3;
            }
            default "false";
            description
              "Enable/disable selecting the display mode of an authentication key.";
          }
          leaf authentication-key {
            when "not(../authentication-mode='none')" {
              tailf:xpath-root 3;
            }
            type pub-type:password {
              length "1..128";
              pattern '(\S+.*\S+|\S*)';
            }
            must "(../authentication-mode='none' and not(../authentication-key)) or (not(../authentication-mode='none') and ../authentication-key)" {
              tailf:xpath-root 3;
            }
            description
              "Authentication key, which is set based on the authentication type. Value description: If non-authentication is specified, the value is empty. If simple authentication, MD5 authentication, or HMAC-SHA256 authentication is specified, the value is a string with the length ranging from 1 to 8 bytes or a ciphertext password with the corresponding length.";
          }
          leaf link-bfddown-num {
            type uint8 {
              range "1..8";
            }
            description
              "Specify the threshold for the number of link BFD sessions in the Down state tracked by the MVRRP backup group.";
          }
          leaf hold-multiper {
            type uint8 {
              range "3..10";
            }
            default "3";
            description
              "Set the hello packet sending interval multiplier.";
          }
          leaf backup-forward {
            type boolean;
            default "false";
            description
              "Enable/disable VRRP backup forward mode.";
          }
          leaf fast-resume {
            when '../admin-flag' {
              tailf:xpath-root 3;
            }
            type boolean;
            default "false";
            description
              "Enable/disable VRRP fast resume mode.";
          }
          leaf v3-sendmode {
            when "/vrrp:vrrp/vrrp:global/vrrp:version='v3'" {
              tailf:xpath-root 3;
            }
            type vrrp-v3-sendmode;
            default "v3-only";
            description
              "VRRP advertisement packet mode on the interface.";
          }
          choice vrrp-type {
            description
              "Type of VRRP.";
            case member-vrrp {
              description
                "Member VRRP.";
              leaf admin-id {
                type uint8 {
                  range "1..255";
                }
                must '/ifm:ifm/ifm:interfaces/ifm:interface[ifm:name=current()/../vrrp:admin-if-name]/ip:ipv4/vrrp:vrrp/vrrp:groups/vrrp:group[vrrp:id=current()]/vrrp:admin-flag' {
                  tailf:xpath-root 3;
                }
                description
                  "Tracked MVRRP ID.";
              }
              leaf admin-if-name {
                type leafref {
                  path "/ncs:devices/ncs:device/ncs:config/ifm:ifm/ifm:interfaces/ifm:interface/ifm:name" {
                    tailf:xpath-root 3;
                  }
                }
                must '/ifm:ifm/ifm:interfaces/ifm:interface[ifm:name=current()]/ip:ipv4/vrrp:vrrp/vrrp:groups/vrrp:group[vrrp:id=current()/../vrrp:admin-id]/vrrp:admin-flag' {
                  tailf:xpath-root 3;
                }
                description
                  "Tracked MVRRP interface name.";
              }
              leaf unflowdown {
                when '../admin-id and ../admin-if-name' {
                  tailf:xpath-root 3;
                }
                type boolean;
                default "false";
                description
                  "Enable/disable the flowdown function for service VRRP.";
              }
            }
            case admin-vrrp {
              description
                "Admin VRRP.";
              leaf admin-flag {
                type empty;
                description
                  "Management VRRP.";
              }
              leaf admin-ignore-ifdown {
                when '../admin-flag' {
                  tailf:xpath-root 3;
                }
                type boolean;
                default "false";
                description
                  "Enable/disable ignoring an interface down event.";
              }
              leaf init-state-holdtime {
                when "../admin-ignore-ifdown='true'" {
                  tailf:xpath-root 3;
                }
                type uint32 {
                  range "0..3600";
                }
                units "s";
                description
                  "Hold time of the Initialize state after the management VRRP backup group is configured to ignore an interface down event.";
              }
            }
          }
          // NCS drop config false leaf type
          // NCS drop config false leaf state
          // NCS drop config false leaf 'create-time'
          // NCS drop config false leaf 'last-change-time'
          container virtual-ips {
            description
              "List of IP address table related to virtual routers. A VRRP backup group can have 0 to 16 extended virtual IP addresses.";
            list virtual-ip {
              key "address";
              max-elements 16;
              description
                "Configure virtual IP address configuration. A VRRP backup group can have 0 to 16 extended virtual IP addresses.";
              leaf address {
                type inet:ipv4-address-no-zone;
                description
                  "Virtual IP address.";
              }
              leaf mask {
                when "../vgmp-role='active' or ../vgmp-role='standby'" {
                  tailf:xpath-root 3;
                }
                type inet:ipv4-address-no-zone;
                description
                  "Virtual IP address mask.";
              }
              leaf vgmp-role {
                type vgmp-type;
                default "none";
                description
                  "The configuration state of VRRP.";
              }
            }
          }
          container track-interfaces {
            when 'not(../admin-id)' {
              tailf:xpath-root 3;
            }
            description
              "List of interfaces tracked by a VRRP backup group. A VRRP backup group can track a maximum of 16 interfaces.";
            list track-interface {
              key "if-name";
              max-elements 16;
              description
                "Configure interface tracked by a VRRP backup group.";
              leaf if-name {
                type leafref {
                  path "/ncs:devices/ncs:device/ncs:config/ifm:ifm/ifm:interfaces/ifm:interface/ifm:name" {
                    tailf:xpath-root 3;
                  }
                }
                description
                  "Name of the interface tracked by the VRRP backup group.";
              }
              leaf priority-change {
                type uint8 {
                  range "1..255";
                }
                mandatory true;
                description
                  "Value by which the priority increases or reduces when the VRRP backup group tracks the interface.";
              }
              leaf track-mode {
                type vrrptrack-mode;
                default "reduce";
                description
                  "Mode in which the VRRP backup group tracks the interface.";
              }
            }
          }
          container track-bfds {
            when 'not(../admin-id)' {
              tailf:xpath-root 3;
            }
            description
              "List of BFD sessions tracked by the VRRP backup group.";
            list track-bfd {
              key "session-name session-type";
              max-elements 17;
              description
                "Configure BFD session tracked by the VRRP backup group.";
              leaf session-name {
                type leafref {
                  path "/ncs:devices/ncs:device/ncs:config/bfd:bfd/bfd:sessions/bfd:session/bfd:name" {
                    tailf:xpath-root 3;
                  }
                }
                description
                  "Name of the BFD session tracked by the VRRP backup group.";
              }
              leaf session-type {
                type vrrp-bfd-type;
                description
                  "Type of the BFD session tracked by the VRRP backup group.";
              }
              leaf priority-change {
                when "../session-type='normal'" {
                  tailf:xpath-root 3;
                }
                type uint8 {
                  range "1..255";
                }
                mandatory true;
                description
                  "Value by which the priority increases or reduces when the VRRP backup group tracks the common BFD session.";
              }
              leaf track-mode {
                when "../session-type='normal'" {
                  tailf:xpath-root 3;
                }
                type vrrp-track-mode;
                default "reduce";
                description
                  "Mode in which the VRRP backup group tracks the BFD session.";
              }
              // NCS drop config false leaf 'session-id'
              // NCS drop config false leaf 'session-state'
            }
          }
          container track-mtgrps {
            description
              "List of VRRP backup groups to track interface monitoring groups.";
            list track-mtgrp {
              key "monitor-group-name";
              max-elements 3;
              description
                "Configure VRRP backup groups to track interface monitoring groups.";
              leaf monitor-group-name {
                type leafref {
                  path "/ncs:devices/ncs:device/ncs:config/monitor-group:monitor-group/monitor-group:groups/monitor-group:group/monitor-group:name" {
                    tailf:xpath-root 3;
                  }
                }
                description
                  "Name of the interface monitoring group tracked by a VRRP backup group.";
              }
              leaf failure-ratio {
                type uint8 {
                  range "1..100";
                }
                mandatory true;
                description
                  "Link failure ratio threshold for an interface monitoring group.";
              }
              leaf priority-change {
                when "../track-mode='reduce'" {
                  tailf:xpath-root 3;
                }
                type uint8 {
                  range "1..255";
                }
                mandatory true;
                description
                  "Value by which the priority of the VRRP backup group reduces if the status of the tracked interface monitoring group changes to Down.";
              }
              leaf track-mode {
                type mtgrptrack-mode;
                default "reduce";
                description
                  "Mode in which a VRRP backup group tracks an interface monitoring group.";
              }
            }
          }
          container track-nqas {
            description
              "List of NQA sessions tracked by the VRRP backup group.";
            list track-nqa {
              key "admin-name test-name";
              max-elements 8;
              description
                "Configure a VRRP backup group to track NQA test instances.";
              leaf admin-name {
                type leafref {
                  path "/ncs:devices/ncs:device/ncs:config/nqa:nqa/nqa:instances/nqa:instance/nqa:admin-name" {
                    tailf:xpath-root 3;
                  }
                }
                description
                  "Name of the tracked NQA administrator.";
              }
              leaf test-name {
                type leafref {
                  path "/ncs:devices/ncs:device/ncs:config/nqa:nqa/nqa:instances/nqa:instance/nqa:test-name" {
                    tailf:xpath-root 3;
                  }
                }
                must '(/nqa:nqa/nqa:instances/nqa:instance[nqa:test-name=current()]/nqa:icmp-input/nqa:ni-name) and (/nqa:nqa/nqa:instances/nqa:instance[nqa:admin-name=current()/../vrrp:admin-name]/nqa:icmp-input/nqa:ni-name)' {
                  tailf:xpath-root 3;
                }
                description
                  "Name of the tracked NQA test instance.";
              }
              leaf priority-change {
                type uint8 {
                  range "1..255";
                }
                default "10";
                description
                  "Value by which the priority reduces when the VRRP backup group tracks NQA.";
              }
            }
          }
          container track-ip-routes {
            description
              "List of VRRP backup groups to track IP routes.";
            list track-ip-route {
              key "vpn-name ip-address mask-length";
              description
                "Configure VRRP backup groups to track IP route.";
              leaf vpn-name {
                type leafref {
                  path "/ncs:devices/ncs:device/ncs:config/ni:network-instance/ni:instances/ni:instance/ni:name" {
                    tailf:xpath-root 3;
                  }
                }
                description
                  "VPN instance name.";
              }
              leaf ip-address {
                type inet:ipv4-address-no-zone;
                description
                  "Specifies the destination IP address of a route to be tracked.";
              }
              leaf mask-length {
                type uint8 {
                  range "0..32";
                }
                must "not(../ip-address!='0.0.0.0' and ../mask-length=0)" {
                  tailf:xpath-root 3;
                }
                description
                  "Specifies the destination IP address mask length of a route to be tracked.";
              }
              leaf priority-change {
                type uint8 {
                  range "1..255";
                }
                mandatory true;
                description
                  "Value by which the priority increases or reduces when the VRRP backup group tracks IP route.";
              }
              leaf track-mode {
                type vrrp-track-mode;
                default "reduce";
                description
                  "Mode in which the VRRP backup group tracks IP route.";
              }
            }
          }
        }
      }
    }
  }
  augment "/ncs:devices/ncs:template/ncs:ned-id/ncs:config/ifm:ifm/ifm:interfaces/ifm:interface/ip:ipv6" {
    description
      "VRRP6 configurations on interface.";
    container vrrp6 {
      description
        "Configure all VRRP6 backup groups.";
      container group6s {
        description
          "List of all VRRP6 backup groups.";
        list group6 {
          // NCS patched for predictable order
          ordered-by user;
          key "id";
          unique "link-local-ip";
          description
            "Configure this table for VRRP6 operations on a device. It lists a series of VRRP6 operation entries. You can use this table to query the VRRP6 configuration on the device. In addition, you can create virtual router instances and modify the configuration.";
          leaf id {
            type string;
            description
              "VRRP6 backup group ID.";
          }
          leaf priority {
            type string;
            // NCS drop default statement
            description
              "Configured VRRP6 priority. A larger value indicates a higher priority.";
          }
          container preempt {
            description
              "Configure a higher priority VRRP6 backup router to preempt a lower priority VRRP6 master.";
            leaf preempt-enable {
              type string;
              // NCS drop default statement
              description
                "Enable/disable the value of this object to control whether a high-priority router can preempt the master state.";
            }
            leaf delay-time {
              // NCS drop when statement
              type string;
              units "s";
              // NCS drop default statement
              description
                "Preemption delay.";
            }
          }
          leaf adver-interval {
            type string;
            units "ms";
            // NCS drop default statement
            description
              "Configure an interval (in milliseconds) at which the master sends VRRP advertisement packets. This interval must be a multiple of 10 that is no less than 1000ms. If the device supports fast advertisement sending, this interval can be set to 500ms.";
          }
          leaf link-local-ip {
            type string;
            description
              "Link local IP address of the interface in the VRRP6 backup group.";
            ext:operation-exclude "update" {
              description
                "The link-local-ip can not be modified.";
            }
          }
          leaf vgmp-role {
            // NCS drop when statement
            type ncs_template_vgmp-type;
            // NCS drop default statement
            description
              "The configuration state of VRRP6.";
          }
          container virtual-ips {
            // NCS drop when statement
            description
              "List of IP addresses related to virtual routers. A VRRP6 backup group can have 0 to 15 extended virtual IP addresses.";
            list virtual-ip {
              // NCS patched for predictable order
              ordered-by user;
              key "ip-address";
              // NCS drop max-elements statement
              description
                "Configure virtual IP address.";
              leaf ip-address {
                type string;
                description
                  "The link local address must be configured first and the virtual IP address must be in the same network segment as the IP address of the interface.";
              }
            }
          }
          container track-bfds {
            description
              "List of BFD sessions tracked by the VRRP6 backup group.";
            list track-bfd {
              // NCS patched for predictable order
              ordered-by user;
              key "bfd-sessname";
              // NCS drop max-elements statement
              description
                "Configure BFD session tracked by the VRRP6 backup group.";
              leaf bfd-sessname {
                type string;
                description
                  "Name of the BFD session tracked by the VRRP6 backup group.";
              }
              leaf bfd-type {
                type ncs_template_vrrp-bfd-type;
                // NCS drop mandatory statement
                description
                  "Type of the BFD session tracked by the VRRP6 backup group.";
              }
              leaf priority-change {
                // NCS drop when statement
                type string;
                // NCS drop mandatory statement
                description
                  "Value by which the priority increases or reduces when the VRRP6 backup group tracks the common BFD session.";
              }
              leaf track-mode {
                // NCS drop when statement
                type ncs_template_vrrp-track-mode;
                // NCS drop default statement
                description
                  "Mode in which the VRRP6 backup group tracks the BFD session.";
              }
              // NCS drop config false leaf 'bfd-sessid'
            }
          }
        }
      }
    }
  }
  augment "/ncs:devices/ncs:device/ncs:live-status/ifm:ifm/ifm:interfaces/ifm:interface/ip:ipv6" {
    description
      "VRRP6 configurations on interface.";
    container vrrp6 {
      tailf:ncs-device-type "netconf";
      tailf:display-when "not(../../../../../../ncs:module) or ../../../../../../ncs:module[ncs:name='huawei-vrrp'] or (../../../../../../ncs:live-status-protocol[not(ncs:capability)]) or (../../../../../../ncs:live-status-protocol/ncs:capability/ncs:module[.='huawei-vrrp'])";
      description
        "Configure all VRRP6 backup groups.";
      container group6s {
        description
          "List of all VRRP6 backup groups.";
        list group6 {
          key "id";
          unique "link-local-ip";
          description
            "Configure this table for VRRP6 operations on a device. It lists a series of VRRP6 operation entries. You can use this table to query the VRRP6 configuration on the device. In addition, you can create virtual router instances and modify the configuration.";
          leaf id {
            type uint8 {
              range "1..255";
            }
            description
              "VRRP6 backup group ID.";
          }
          leaf priority {
            type uint8 {
              range "1..254";
            }
            // NCS drop default statement
            description
              "Configured VRRP6 priority. A larger value indicates a higher priority.";
          }
          container preempt {
            description
              "Configure a higher priority VRRP6 backup router to preempt a lower priority VRRP6 master.";
            leaf preempt-enable {
              type boolean;
              // NCS drop default statement
              description
                "Enable/disable the value of this object to control whether a high-priority router can preempt the master state.";
            }
            leaf delay-time {
              // NCS drop when statement
              type uint16 {
                range "0..3600";
              }
              units "s";
              // NCS drop default statement
              description
                "Preemption delay.";
            }
          }
          leaf adver-interval {
            type uint32 {
              range "1000..40950";
            }
            units "ms";
            // NCS drop default statement
            description
              "Configure an interval (in milliseconds) at which the master sends VRRP advertisement packets. This interval must be a multiple of 10 that is no less than 1000ms. If the device supports fast advertisement sending, this interval can be set to 500ms.";
          }
          leaf link-local-ip {
            type inet:ipv6-address-no-zone;
            description
              "Link local IP address of the interface in the VRRP6 backup group.";
            ext:operation-exclude "update" {
              description
                "The link-local-ip can not be modified.";
            }
          }
          leaf vgmp-role {
            // NCS drop when statement
            type live_ncs_vgmp-type;
            // NCS drop default statement
            description
              "The configuration state of VRRP6.";
          }
          container virtual-ips {
            // NCS drop when statement
            description
              "List of IP addresses related to virtual routers. A VRRP6 backup group can have 0 to 15 extended virtual IP addresses.";
            list virtual-ip {
              key "ip-address";
              // NCS drop max-elements statement
              description
                "Configure virtual IP address.";
              leaf ip-address {
                type inet:ipv6-address-no-zone;
                description
                  "The link local address must be configured first and the virtual IP address must be in the same network segment as the IP address of the interface.";
              }
            }
          }
          container track-bfds {
            description
              "List of BFD sessions tracked by the VRRP6 backup group.";
            list track-bfd {
              key "bfd-sessname";
              // NCS drop max-elements statement
              description
                "Configure BFD session tracked by the VRRP6 backup group.";
              leaf bfd-sessname {
                type leafref {
                  path "/ncs:devices/ncs:device/ncs:live-status/bfd:bfd/bfd:sessions/bfd:session/bfd:name" {
                    tailf:xpath-root 3;
                  }
                }
                description
                  "Name of the BFD session tracked by the VRRP6 backup group.";
              }
              leaf bfd-type {
                type live_ncs_vrrp-bfd-type;
                // NCS drop mandatory statement
                description
                  "Type of the BFD session tracked by the VRRP6 backup group.";
              }
              leaf priority-change {
                // NCS drop when statement
                type uint8 {
                  range "1..255";
                }
                // NCS drop mandatory statement
                description
                  "Value by which the priority increases or reduces when the VRRP6 backup group tracks the common BFD session.";
              }
              leaf track-mode {
                // NCS drop when statement
                type live_ncs_vrrp-track-mode;
                // NCS drop default statement
                description
                  "Mode in which the VRRP6 backup group tracks the BFD session.";
              }
              leaf bfd-sessid {
                type uint32 {
                  range "1..32768";
                }
                description
                  "ID of the BFD session tracked by the VRRP6 backup group.";
              }
            }
          }
        }
      }
    }
  }
  augment "/ncs:devices/ncs:device/ncs:config/ifm:ifm/ifm:interfaces/ifm:interface/ip:ipv6" {
    description
      "VRRP6 configurations on interface.";
    container vrrp6 {
      tailf:ncs-device-type "netconf";
      tailf:display-when "not(../../../../../../ncs:module) or ../../../../../../ncs:module[ncs:name='huawei-vrrp']";
      description
        "Configure all VRRP6 backup groups.";
      container group6s {
        description
          "List of all VRRP6 backup groups.";
        list group6 {
          key "id";
          unique "link-local-ip";
          description
            "Configure this table for VRRP6 operations on a device. It lists a series of VRRP6 operation entries. You can use this table to query the VRRP6 configuration on the device. In addition, you can create virtual router instances and modify the configuration.";
          leaf id {
            type uint8 {
              range "1..255";
            }
            description
              "VRRP6 backup group ID.";
          }
          leaf priority {
            type uint8 {
              range "1..254";
            }
            default "100";
            description
              "Configured VRRP6 priority. A larger value indicates a higher priority.";
          }
          container preempt {
            description
              "Configure a higher priority VRRP6 backup router to preempt a lower priority VRRP6 master.";
            leaf preempt-enable {
              type boolean;
              default "true";
              description
                "Enable/disable the value of this object to control whether a high-priority router can preempt the master state.";
            }
            leaf delay-time {
              when "../preempt-enable='true'" {
                tailf:xpath-root 3;
              }
              type uint16 {
                range "0..3600";
              }
              units "s";
              default "0";
              description
                "Preemption delay.";
            }
          }
          leaf adver-interval {
            type uint32 {
              range "1000..40950";
            }
            units "ms";
            default "1000";
            description
              "Configure an interval (in milliseconds) at which the master sends VRRP advertisement packets. This interval must be a multiple of 10 that is no less than 1000ms. If the device supports fast advertisement sending, this interval can be set to 500ms.";
          }
          leaf link-local-ip {
            type inet:ipv6-address-no-zone;
            description
              "Link local IP address of the interface in the VRRP6 backup group.";
            ext:operation-exclude "update" {
              description
                "The link-local-ip can not be modified.";
            }
          }
          leaf vgmp-role {
            when '../link-local-ip' {
              tailf:xpath-root 3;
            }
            type vgmp-type;
            default "none";
            description
              "The configuration state of VRRP6.";
          }
          container virtual-ips {
            when '../link-local-ip' {
              tailf:xpath-root 3;
            }
            description
              "List of IP addresses related to virtual routers. A VRRP6 backup group can have 0 to 15 extended virtual IP addresses.";
            list virtual-ip {
              key "ip-address";
              max-elements 15;
              description
                "Configure virtual IP address.";
              leaf ip-address {
                type inet:ipv6-address-no-zone;
                description
                  "The link local address must be configured first and the virtual IP address must be in the same network segment as the IP address of the interface.";
              }
            }
          }
          container track-bfds {
            description
              "List of BFD sessions tracked by the VRRP6 backup group.";
            list track-bfd {
              key "bfd-sessname";
              max-elements 17;
              description
                "Configure BFD session tracked by the VRRP6 backup group.";
              leaf bfd-sessname {
                type leafref {
                  path "/ncs:devices/ncs:device/ncs:config/bfd:bfd/bfd:sessions/bfd:session/bfd:name" {
                    tailf:xpath-root 3;
                  }
                }
                description
                  "Name of the BFD session tracked by the VRRP6 backup group.";
              }
              leaf bfd-type {
                type vrrp-bfd-type;
                mandatory true;
                description
                  "Type of the BFD session tracked by the VRRP6 backup group.";
              }
              leaf priority-change {
                when "../bfd-type='normal'" {
                  tailf:xpath-root 3;
                }
                type uint8 {
                  range "1..255";
                }
                mandatory true;
                description
                  "Value by which the priority increases or reduces when the VRRP6 backup group tracks the common BFD session.";
              }
              leaf track-mode {
                when "../bfd-type='normal'" {
                  tailf:xpath-root 3;
                }
                type vrrp-track-mode;
                default "reduce";
                description
                  "Mode in which the VRRP6 backup group tracks the BFD session.";
              }
              // NCS drop config false leaf 'bfd-sessid'
            }
          }
        }
      }
    }
  }
}
