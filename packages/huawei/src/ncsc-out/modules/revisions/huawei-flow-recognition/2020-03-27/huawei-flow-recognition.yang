module huawei-flow-recognition {
  // Generated by yanger -t ncs
  tailf:mount-id "huawei-nc-1.0:huawei-nc-1.0";
  tailf:ncs-device-type "netconf";

  yang-version 1;
  namespace "urn:huawei:yang:huawei-flow-recognition";
  prefix flow-recognition;

  import huawei-pub-type {
    prefix pub-type;
  }
  import huawei-extension {
    prefix ext;
  }
  import ietf-inet-types {
    prefix inet;
  }
  import huawei-ifm {
    prefix ifm;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Flow recognition.";
  reference "Huawei private.";

  revision 2020-03-27 {
    description
      "Added configure function to the YANG file.";
    reference "Huawei private.";
  }
  revision 2019-06-13 {
    description
      "Initial revision.";
    reference "Huawei private.";
  }
  ext:task-name "esqm";

  augment "/ncs:devices/ncs:device/ncs:config" {
    container flow-recognition {
      tailf:ncs-device-type "netconf";
      tailf:display-when "not(../../ncs:module) or ../../ncs:module[ncs:name='huawei-flow-recognition']";
      description
        "Collect flow information.";
      // NCS drop config false container streaminfos
    }
  }
  augment "/ncs:devices/ncs:device/ncs:live-status" {
    container flow-recognition {
      tailf:ncs-device-type "netconf";
      tailf:display-when "not(../../ncs:module) or ../../ncs:module[ncs:name='huawei-flow-recognition'] or (../../ncs:live-status-protocol[not(ncs:capability)]) or (../../ncs:live-status-protocol/ncs:capability/ncs:module[.='huawei-flow-recognition'])";
      description
        "Collect flow information.";
      container streaminfos {
        description
          "List of flow information.";
        list streaminfo {
          key "src-mac dst-mac src-ip-addr dst-ip-addr src-port dst-port protocol";
          description
            "Statistics of flow information.";
          leaf src-mac {
            type pub-type:live_ncs_mac-address;
            description
              "\"Source mac address.\"";
          }
          leaf dst-mac {
            type pub-type:live_ncs_mac-address;
            description
              "\"Destination mac address.\"";
          }
          leaf src-ip-addr {
            type inet:ip-address-no-zone;
            description
              "\"IP source address.\"";
          }
          leaf dst-ip-addr {
            type inet:ip-address-no-zone;
            description
              "\"IP destination address.\"";
          }
          leaf src-port {
            type uint16;
            description
              "\"Source port.\"";
          }
          leaf dst-port {
            type uint16;
            description
              "\"Destination port.\"";
          }
          leaf protocol {
            type uint8;
            description
              "\"Protocol,eg 6 (TCP).\"";
          }
          leaf direction {
            type uint8;
            description
              "\"Direction.\"";
          }
          leaf if-name {
            type pub-type:live_ncs_if-name;
            description
              "\"Interface Name.\"";
          }
          leaf time-stamp-sec {
            type uint32;
            units "s";
            description
              "\"Seconds from 1970.\"";
          }
          leaf time-stamp-nsec {
            type uint32;
            units "ns";
            description
              "\"Nano-seconds in 1 sec.\"";
          }
          leaf packet-num {
            type uint64;
            description
              "\"The packets num of the flow.\"";
          }
          leaf bytes-num {
            type uint64;
            description
              "\"The bytes num of the flow.\"";
          }
        }
      }
    }
  }
  augment "/ncs:devices/ncs:template/ncs:ned-id/ncs:config" {
    container flow-recognition {
      description
        "Collect flow information.";
      // NCS drop config false container streaminfos
    }
  }
  augment "/ncs:devices/ncs:template/ncs:ned-id/ncs:config/ifm:ifm/ifm:interfaces/ifm:interface" {
    description
      "Configure the flow recognition for interface.";
    container flow-recognition {
      description
        "Configure the flow recognition management.";
      container flow-enables {
        description
          "List of the interface flow recognition.";
        list flow-enable {
          // NCS patched for predictable order
          ordered-by user;
          key "direction";
          leaf direction {
            type string;
            description
              "Direction of interface flow recognition mode.";
          }
          description
            "Configure the interface flow recognition mode.";
        }
      }
    }
  }
  augment "/ncs:devices/ncs:device/ncs:live-status/ifm:ifm/ifm:interfaces/ifm:interface" {
    description
      "Configure the flow recognition for interface.";
    container flow-recognition {
      tailf:ncs-device-type "netconf";
      tailf:display-when "not(../../../../../ncs:module) or ../../../../../ncs:module[ncs:name='huawei-flow-recognition'] or (../../../../../ncs:live-status-protocol[not(ncs:capability)]) or (../../../../../ncs:live-status-protocol/ncs:capability/ncs:module[.='huawei-flow-recognition'])";
      description
        "Configure the flow recognition management.";
      container flow-enables {
        description
          "List of the interface flow recognition.";
        list flow-enable {
          key "direction";
          leaf direction {
            type enumeration {
              enum "inbound" {
                value 0;
                description
                  "Indicates the interface flow recognition inbound mode.";
              }
            }
            description
              "Direction of interface flow recognition mode.";
          }
          description
            "Configure the interface flow recognition mode.";
        }
      }
    }
  }
  augment "/ncs:devices/ncs:device/ncs:config/ifm:ifm/ifm:interfaces/ifm:interface" {
    description
      "Configure the flow recognition for interface.";
    container flow-recognition {
      tailf:ncs-device-type "netconf";
      tailf:display-when "not(../../../../../ncs:module) or ../../../../../ncs:module[ncs:name='huawei-flow-recognition']";
      description
        "Configure the flow recognition management.";
      container flow-enables {
        description
          "List of the interface flow recognition.";
        list flow-enable {
          key "direction";
          leaf direction {
            type enumeration {
              enum "inbound" {
                value 0;
                description
                  "Indicates the interface flow recognition inbound mode.";
              }
            }
            description
              "Direction of interface flow recognition mode.";
          }
          description
            "Configure the interface flow recognition mode.";
        }
      }
    }
  }
}
