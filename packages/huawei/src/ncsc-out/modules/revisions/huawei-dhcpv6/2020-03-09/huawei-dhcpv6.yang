module huawei-dhcpv6 {
  // Generated by yanger -t ncs
  tailf:mount-id "huawei-nc-1.0:huawei-nc-1.0";
  tailf:ncs-device-type "netconf";

  yang-version 1;
  namespace "urn:huawei:yang:huawei-dhcpv6";
  prefix dhcpv6;

  import huawei-extension {
    prefix ext;
  }
  import ietf-inet-types {
    prefix inet;
  }
  import huawei-ifm {
    prefix ifm;
  }
  import huawei-ethernet {
    prefix ethernet;
  }
  import huawei-pub-type {
    prefix pub-type;
  }
  include huawei-dhcpv6-relay;
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Dynamic Host Configuration Protocol for IPv6.";

  revision 2020-03-09 {
    description
      "Modify description.";
    reference "Huawei private.";
  }
  revision 2020-02-25 {
    description
      "Initial revision.";
    reference "Huawei private.";
  }
  ext:task-name "dhcp";

  typedef ncs_template_dhcpv6-duid {
    type string;
    description
      "The type of DHCPv6 DUID.";
  }

  typedef ncs_template_remote-id-format {
    type string;
    description
      "The type of DHCPv6 remote-id format.";
  }

  typedef ncs_rpc_notif_dhcpv6-duid {
    type enumeration {
      enum "invalid" {
        value 0;
        description
          "-";
      }
      enum "llt" {
        value 1;
        description
          "Link-layer address plus time.";
      }
      enum "ll" {
        value 2;
        description
          "Link-layer address.";
      }
      enum "user-defined" {
        value 3;
        description
          "User-defined.";
      }
    }
    description
      "The type of DHCPv6 DUID.";
  }

  typedef ncs_rpc_notif_remote-id-format {
    type enumeration {
      enum "default" {
        value 0;
        description
          "Default format.";
      }
      enum "user-defined" {
        value 1;
        description
          "User-defined format.";
      }
    }
    description
      "The type of DHCPv6 remote-id format.";
  }

  typedef live_ncs_dhcpv6-duid {
    type enumeration {
      enum "invalid" {
        value 0;
        description
          "-";
      }
      enum "llt" {
        value 1;
        description
          "Link-layer address plus time.";
      }
      enum "ll" {
        value 2;
        description
          "Link-layer address.";
      }
      enum "user-defined" {
        value 3;
        description
          "User-defined.";
      }
    }
    description
      "The type of DHCPv6 DUID.";
  }

  typedef live_ncs_remote-id-format {
    type enumeration {
      enum "default" {
        value 0;
        description
          "Default format.";
      }
      enum "user-defined" {
        value 1;
        description
          "User-defined format.";
      }
    }
    description
      "The type of DHCPv6 remote-id format.";
  }

  typedef dhcpv6-duid {
    type enumeration {
      enum "invalid" {
        value 0;
        description
          "-";
      }
      enum "llt" {
        value 1;
        description
          "Link-layer address plus time.";
      }
      enum "ll" {
        value 2;
        description
          "Link-layer address.";
      }
      enum "user-defined" {
        value 3;
        description
          "User-defined.";
      }
    }
    description
      "The type of DHCPv6 DUID.";
  }

  typedef remote-id-format {
    type enumeration {
      enum "default" {
        value 0;
        description
          "Default format.";
      }
      enum "user-defined" {
        value 1;
        description
          "User-defined format.";
      }
    }
    description
      "The type of DHCPv6 remote-id format.";
  }

  augment "/ncs:devices/ncs:device/ncs:config" {
    container dhcpv6 {
      tailf:ncs-device-type "netconf";
      tailf:display-when "not(../../ncs:module) or ../../ncs:module[ncs:name='huawei-dhcpv6']";
      description
        "Configure a Dynamic Host Configuration Protocol for IPv6.";
      container common {
        description
          "Configure basic attributes.";
        container global {
          description
            "Configure DHCPv6 global attributes.";
          leaf enable {
            type boolean;
            default "true";
            description
              "Enable/disable Dynamic Host Configuration Protocol for IPv6.";
          }
          leaf duid-format {
            type dhcpv6-duid;
            must "(../duid-format = 'user-defined' and ../duid-string) or (../duid-format != 'user-defined')" {
              tailf:xpath-root 3;
            }
            default "invalid";
            description
              "DHCPv6 unique identifier format.";
          }
          leaf duid-string {
            when "../duid-format='user-defined'" {
              tailf:xpath-root 3;
            }
            type string {
              length "8..28";
              pattern '([^\t]{8,})';
            }
            description
              "DUID string, in hexadecimal notation.";
          }
          leaf rate-limit-enable {
            type boolean;
            default "true";
            description
              "Enable/disable DHCPv6 packets rate limit.";
          }
          leaf rate-limit {
            type uint32 {
              range "1..2000";
            }
            units "pps";
            default "512";
            description
              "DHCPv6 packets rate limit value.";
          }
          leaf source-ip-adaptive {
            type boolean;
            default "false";
            description
              "Enable/disable DHCPv6 source-ip-address format adaptive.";
          }
          leaf aging-time {
            type uint32 {
              range "1..1440";
            }
            units "min";
            default "30";
            description
              "DHCPv6 session CAR aging time.";
          }
          // NCS drop config false leaf 'active-duid'
        }
        container session-car {
          must 'pir-value >= cir-value and pbs-value >= cbs-value' {
            tailf:xpath-root 3;
          }
          description
            "Configure session CAR.";
          leaf enable {
            type boolean;
            default "true";
            description
              "Enable/disable session CAR.";
          }
          leaf cir-value {
            type uint32 {
              range "0..1000000";
            }
            units "kbit/s";
            default "256";
            description
              "Specify the session CAR CIR value.";
          }
          leaf cbs-value {
            type uint32 {
              range "0..9000000";
            }
            units "Byte";
            default "32000";
            description
              "Specify the session CAR CBS value.";
          }
          leaf pir-value {
            type uint32 {
              range "0..1000000";
            }
            units "kbit/s";
            default "512";
            description
              "Specify the session CAR PIR value.";
          }
          leaf pbs-value {
            type uint32 {
              range "0..9000000";
            }
            units "Byte";
            default "64000";
            description
              "Specify the session CAR PBS value.";
          }
        }
      }
      container relay {
        description
          "Configure DHCPv6 Relay.";
        uses dhcpv6:dhcpv6-relay-type;
      }
    }
  }
  augment "/ncs:devices/ncs:device/ncs:live-status" {
    container dhcpv6 {
      tailf:ncs-device-type "netconf";
      tailf:display-when "not(../../ncs:module) or ../../ncs:module[ncs:name='huawei-dhcpv6'] or (../../ncs:live-status-protocol[not(ncs:capability)]) or (../../ncs:live-status-protocol/ncs:capability/ncs:module[.='huawei-dhcpv6'])";
      description
        "Configure a Dynamic Host Configuration Protocol for IPv6.";
      container common {
        description
          "Configure basic attributes.";
        container global {
          description
            "Configure DHCPv6 global attributes.";
          leaf enable {
            type boolean;
            // NCS drop default statement
            description
              "Enable/disable Dynamic Host Configuration Protocol for IPv6.";
          }
          leaf duid-format {
            type live_ncs_dhcpv6-duid;
            // NCS drop must statement
            // NCS drop default statement
            description
              "DHCPv6 unique identifier format.";
          }
          leaf duid-string {
            // NCS drop when statement
            type string {
              length "8..28";
              pattern '([^\t]{8,})';
            }
            description
              "DUID string, in hexadecimal notation.";
          }
          leaf rate-limit-enable {
            type boolean;
            // NCS drop default statement
            description
              "Enable/disable DHCPv6 packets rate limit.";
          }
          leaf rate-limit {
            type uint32 {
              range "1..2000";
            }
            units "pps";
            // NCS drop default statement
            description
              "DHCPv6 packets rate limit value.";
          }
          leaf source-ip-adaptive {
            type boolean;
            // NCS drop default statement
            description
              "Enable/disable DHCPv6 source-ip-address format adaptive.";
          }
          leaf aging-time {
            type uint32 {
              range "1..1440";
            }
            units "min";
            // NCS drop default statement
            description
              "DHCPv6 session CAR aging time.";
          }
          leaf active-duid {
            type string {
              length "8..28";
              pattern '([^\t]{8,})';
            }
            description
              "DUID string, in hexadecimal notation.";
          }
        }
        container session-car {
          // NCS drop must statement
          description
            "Configure session CAR.";
          leaf enable {
            type boolean;
            // NCS drop default statement
            description
              "Enable/disable session CAR.";
          }
          leaf cir-value {
            type uint32 {
              range "0..1000000";
            }
            units "kbit/s";
            // NCS drop default statement
            description
              "Specify the session CAR CIR value.";
          }
          leaf cbs-value {
            type uint32 {
              range "0..9000000";
            }
            units "Byte";
            // NCS drop default statement
            description
              "Specify the session CAR CBS value.";
          }
          leaf pir-value {
            type uint32 {
              range "0..1000000";
            }
            units "kbit/s";
            // NCS drop default statement
            description
              "Specify the session CAR PIR value.";
          }
          leaf pbs-value {
            type uint32 {
              range "0..9000000";
            }
            units "Byte";
            // NCS drop default statement
            description
              "Specify the session CAR PBS value.";
          }
        }
      }
      container relay {
        description
          "Configure DHCPv6 Relay.";
        uses dhcpv6:live_ncs_dhcpv6-relay-type;
      }
    }
  }
  augment "/ncs:devices/ncs:template/ncs:ned-id/ncs:config" {
    container dhcpv6 {
      description
        "Configure a Dynamic Host Configuration Protocol for IPv6.";
      container common {
        description
          "Configure basic attributes.";
        container global {
          description
            "Configure DHCPv6 global attributes.";
          leaf enable {
            type string;
            // NCS drop default statement
            description
              "Enable/disable Dynamic Host Configuration Protocol for IPv6.";
          }
          leaf duid-format {
            type ncs_template_dhcpv6-duid;
            // NCS drop must statement
            // NCS drop default statement
            description
              "DHCPv6 unique identifier format.";
          }
          leaf duid-string {
            // NCS drop when statement
            type string;
            description
              "DUID string, in hexadecimal notation.";
          }
          leaf rate-limit-enable {
            type string;
            // NCS drop default statement
            description
              "Enable/disable DHCPv6 packets rate limit.";
          }
          leaf rate-limit {
            type string;
            units "pps";
            // NCS drop default statement
            description
              "DHCPv6 packets rate limit value.";
          }
          leaf source-ip-adaptive {
            type string;
            // NCS drop default statement
            description
              "Enable/disable DHCPv6 source-ip-address format adaptive.";
          }
          leaf aging-time {
            type string;
            units "min";
            // NCS drop default statement
            description
              "DHCPv6 session CAR aging time.";
          }
          // NCS drop config false leaf 'active-duid'
        }
        container session-car {
          // NCS drop must statement
          description
            "Configure session CAR.";
          leaf enable {
            type string;
            // NCS drop default statement
            description
              "Enable/disable session CAR.";
          }
          leaf cir-value {
            type string;
            units "kbit/s";
            // NCS drop default statement
            description
              "Specify the session CAR CIR value.";
          }
          leaf cbs-value {
            type string;
            units "Byte";
            // NCS drop default statement
            description
              "Specify the session CAR CBS value.";
          }
          leaf pir-value {
            type string;
            units "kbit/s";
            // NCS drop default statement
            description
              "Specify the session CAR PIR value.";
          }
          leaf pbs-value {
            type string;
            units "Byte";
            // NCS drop default statement
            description
              "Specify the session CAR PBS value.";
          }
        }
      }
      container relay {
        description
          "Configure DHCPv6 Relay.";
        uses dhcpv6:ncs_template_dhcpv6-relay-type;
      }
    }
  }
  augment "/ncs:devices/ncs:template/ncs:ned-id/ncs:config/ifm:ifm/ifm:interfaces/ifm:interface" {
    description
      "Extend interface attribute.";
    container dhcpv6-relay-attribute {
      // NCS drop must statement
      description
        "Configure DHCPv6 relay attributes on an interface.";
      leaf source-address {
        type string;
        description
          "Source address.";
      }
      leaf link-address {
        type string;
        description
          "Link address.";
      }
      leaf strict-check {
        type string;
        // NCS drop default statement
        description
          "Enable/disable strict check on interfaces.";
      }
      leaf server-group-name {
        type string;
        description
          "DHCPv6 relay server group name.";
      }
      leaf source-interface {
        type string;
        description
          "Configure the IPv6 address of an interface as the source IPv6 address of packets.";
      }
      container destination-addresses {
        description
          "List of DHCPv6 relay destination addresses.";
        list destination-address {
          // NCS patched for predictable order
          ordered-by user;
          key "ipv6-address";
          // NCS drop max-elements statement
          description
            "Configure the DHCPv6 relay destination address.";
          leaf ipv6-address {
            type string;
            description
              "Destination address.";
          }
        }
      }
      container destination-ifs {
        description
          "List of DHCPv6 relay destination interfaces.";
        list destination-if {
          // NCS patched for predictable order
          ordered-by user;
          key "if-name";
          // NCS drop max-elements statement
          description
            "Configure DHCPv6 relay destination interface.";
          leaf if-name {
            type string;
            // NCS drop must statement
            description
              "Destination interface name.";
          }
        }
      }
      container option {
        description
          "Configure DHCPv6 relay option attributes.";
        choice interface-id-mode {
          description
            "Configure the interface-id-mode.";
          case cn-telecom {
            description
              "CN-telecom interface-id mode.";
            leaf cn-telecom-mode {
              type empty;
              description
                "CN-telecom interface-id mode.";
            }
          }
          case cn-telecom-inherit {
            description
              "CN-telecom-inherit interface-id mode.";
            leaf cn-telecom-inherit-mode {
              type empty;
              description
                "CN-telecom-inherit interface-id mode.";
            }
          }
          case tr-101 {
            description
              "TR-101 interface-id mode.";
            leaf tr-101-mode {
              type empty;
              description
                "TR-101 interface-id mode.";
            }
          }
          case user-defined {
            description
              "User-defined interface-id mode.";
            leaf interface-id-text {
              type string;
              description
                "DHCPv6 interface-id string defined by users.";
            }
          }
        }
        choice remote-id-mode {
          description
            "Configure the remote-id mode.";
          case default {
            description
              "Default remote-id mode.";
            leaf default-format {
              type empty;
              description
                "Default remote-id mode.";
            }
          }
          case user-defined {
            description
              "User-defined remote-id mode.";
            leaf remote-id-text {
              type string;
              description
                "DHCPv6 remote-id string defined by users.";
            }
          }
        }
        leaf insert-subscriber-id {
          type string;
          // NCS drop default statement
          description
            "Enable/disable to insert the subscriber-id option.";
        }
      }
      container rebuild-option {
        description
          "Configure DHCPv6 relay option rebuild attributes.";
        leaf rebuild-interface-id {
          type empty;
          description
            "Rebuild the interface-id option.";
        }
        leaf rebuild-remote-id {
          type empty;
          description
            "Rebuild the remote-id option.";
        }
      }
      container access-limit-setting {
        description
          "Configure the maximum number of access users on an interface.";
        leaf access-limit {
          type string;
          description
            "Maximum number of access users on an interface.";
        }
        leaf access-vlan-limit {
          // NCS drop when statement
          type string;
          description
            "Maximum number of access users in any VLAN.";
        }
      }
      container pd-route-track-vrrp {
        description
          "Configure DHCPv6 relay PD routes track VRRP.";
        leaf degrade-cost {
          type string;
          description
            "Cost value to be adjusted for DHCPv6 relay PD route.";
        }
      }
      container dot1q-access-limits {
        description
          "List of maximum number of access users on dot1q interfaces.";
        list dot1q-access-limit {
          // NCS patched for predictable order
          ordered-by user;
          // NCS drop must statement
          key "access-limit";
          description
            "Configure maximum number of access users on a dot1q interface.";
          leaf access-limit {
            type string;
            description
              "Maximum number of users allowed.";
          }
          leaf vlan-list {
            type pub-type:ncs_template_vlan-range;
            // NCS drop mandatory statement
            description
              "VLAN list.";
          }
        }
      }
      container qinq-access-limits {
        description
          "List of maximum number of access users on QinQ interfaces.";
        list qinq-access-limit {
          // NCS patched for predictable order
          ordered-by user;
          // NCS drop must statement
          key "access-limit pe-vlan-id";
          description
            "Configure maximum number of access users on a QinQ interface.";
          leaf access-limit {
            type string;
            description
              "Maximum number of users allowed.";
          }
          leaf pe-vlan-id {
            type string;
            description
              "PE VLAN ID.";
          }
          leaf ce-vlan-list {
            type pub-type:ncs_template_vlan-range;
            // NCS drop mandatory statement
            description
              "CE VLAN ID list.";
          }
        }
      }
      container qinq-any-access-limits {
        description
          "List of maximum number of access users on QinQ interfaces.";
        list qinq-any-access-limit {
          // NCS patched for predictable order
          ordered-by user;
          // NCS drop must statement
          key "pe-vlan-id";
          // NCS drop max-elements statement
          description
            "Configure maximum number of access users on a QinQ interface.";
          leaf pe-vlan-id {
            type string;
            description
              "PE VLAN ID.";
          }
          leaf access-limit {
            type string;
            // NCS drop mandatory statement
            description
              "Maximum number of users allowed.";
          }
        }
      }
    }
  }
  augment "/ncs:devices/ncs:device/ncs:live-status/ifm:ifm/ifm:interfaces/ifm:interface" {
    description
      "Extend interface attribute.";
    container dhcpv6-relay-attribute {
      tailf:ncs-device-type "netconf";
      tailf:display-when "not(../../../../../ncs:module) or ../../../../../ncs:module[ncs:name='huawei-dhcpv6'] or (../../../../../ncs:live-status-protocol[not(ncs:capability)]) or (../../../../../ncs:live-status-protocol/ncs:capability/ncs:module[.='huawei-dhcpv6'])";
      // NCS drop must statement
      description
        "Configure DHCPv6 relay attributes on an interface.";
      leaf source-address {
        type inet:ipv6-address-no-zone;
        description
          "Source address.";
      }
      leaf link-address {
        type inet:ipv6-address-no-zone;
        description
          "Link address.";
      }
      leaf strict-check {
        type boolean;
        // NCS drop default statement
        description
          "Enable/disable strict check on interfaces.";
      }
      leaf server-group-name {
        type leafref {
          path "/ncs:devices/ncs:device/ncs:live-status/dhcpv6:dhcpv6/dhcpv6:relay/dhcpv6:server-groups/dhcpv6:server-group/dhcpv6:name" {
            tailf:xpath-root 3;
          }
        }
        description
          "DHCPv6 relay server group name.";
      }
      leaf source-interface {
        type leafref {
          path "/ncs:devices/ncs:device/ncs:live-status/ifm:ifm/ifm:interfaces/ifm:interface/ifm:name" {
            tailf:xpath-root 3;
          }
        }
        description
          "Configure the IPv6 address of an interface as the source IPv6 address of packets.";
      }
      container destination-addresses {
        description
          "List of DHCPv6 relay destination addresses.";
        list destination-address {
          key "ipv6-address";
          // NCS drop max-elements statement
          description
            "Configure the DHCPv6 relay destination address.";
          leaf ipv6-address {
            type inet:ipv6-address-no-zone;
            description
              "Destination address.";
          }
        }
      }
      container destination-ifs {
        description
          "List of DHCPv6 relay destination interfaces.";
        list destination-if {
          key "if-name";
          // NCS drop max-elements statement
          description
            "Configure DHCPv6 relay destination interface.";
          leaf if-name {
            type leafref {
              path "/ncs:devices/ncs:device/ncs:live-status/ifm:ifm/ifm:interfaces/ifm:interface/ifm:name" {
                tailf:xpath-root 3;
              }
            }
            // NCS drop must statement
            description
              "Destination interface name.";
          }
        }
      }
      container option {
        description
          "Configure DHCPv6 relay option attributes.";
        choice interface-id-mode {
          description
            "Configure the interface-id-mode.";
          case cn-telecom {
            description
              "CN-telecom interface-id mode.";
            leaf cn-telecom-mode {
              type empty;
              description
                "CN-telecom interface-id mode.";
            }
          }
          case cn-telecom-inherit {
            description
              "CN-telecom-inherit interface-id mode.";
            leaf cn-telecom-inherit-mode {
              type empty;
              description
                "CN-telecom-inherit interface-id mode.";
            }
          }
          case tr-101 {
            description
              "TR-101 interface-id mode.";
            leaf tr-101-mode {
              type empty;
              description
                "TR-101 interface-id mode.";
            }
          }
          case user-defined {
            description
              "User-defined interface-id mode.";
            leaf interface-id-text {
              type string {
                length "1..255";
                pattern '([^\t]{1,})';
              }
              description
                "DHCPv6 interface-id string defined by users.";
            }
          }
        }
        choice remote-id-mode {
          description
            "Configure the remote-id mode.";
          case default {
            description
              "Default remote-id mode.";
            leaf default-format {
              type empty;
              description
                "Default remote-id mode.";
            }
          }
          case user-defined {
            description
              "User-defined remote-id mode.";
            leaf remote-id-text {
              type string {
                length "1..255";
                pattern '([^\t]{1,})';
              }
              description
                "DHCPv6 remote-id string defined by users.";
            }
          }
        }
        leaf insert-subscriber-id {
          type boolean;
          // NCS drop default statement
          description
            "Enable/disable to insert the subscriber-id option.";
        }
      }
      container rebuild-option {
        description
          "Configure DHCPv6 relay option rebuild attributes.";
        leaf rebuild-interface-id {
          type empty;
          description
            "Rebuild the interface-id option.";
        }
        leaf rebuild-remote-id {
          type empty;
          description
            "Rebuild the remote-id option.";
        }
      }
      container access-limit-setting {
        description
          "Configure the maximum number of access users on an interface.";
        leaf access-limit {
          type uint32 {
            range "0..65536";
          }
          description
            "Maximum number of access users on an interface.";
        }
        leaf access-vlan-limit {
          // NCS drop when statement
          type uint32 {
            range "0..65536";
          }
          description
            "Maximum number of access users in any VLAN.";
        }
      }
      container pd-route-track-vrrp {
        description
          "Configure DHCPv6 relay PD routes track VRRP.";
        leaf degrade-cost {
          type uint32 {
            range "1..4294967295";
          }
          description
            "Cost value to be adjusted for DHCPv6 relay PD route.";
        }
      }
      container dot1q-access-limits {
        description
          "List of maximum number of access users on dot1q interfaces.";
        list dot1q-access-limit {
          // NCS drop must statement
          key "access-limit";
          description
            "Configure maximum number of access users on a dot1q interface.";
          leaf access-limit {
            type uint32 {
              range "0..65536";
            }
            description
              "Maximum number of users allowed.";
          }
          leaf vlan-list {
            type pub-type:live_ncs_vlan-range;
            // NCS drop mandatory statement
            description
              "VLAN list.";
          }
        }
      }
      container qinq-access-limits {
        description
          "List of maximum number of access users on QinQ interfaces.";
        list qinq-access-limit {
          // NCS drop must statement
          key "access-limit pe-vlan-id";
          description
            "Configure maximum number of access users on a QinQ interface.";
          leaf access-limit {
            type uint32 {
              range "0..65536";
            }
            description
              "Maximum number of users allowed.";
          }
          leaf pe-vlan-id {
            type uint16 {
              range "1..4094";
            }
            description
              "PE VLAN ID.";
          }
          leaf ce-vlan-list {
            type pub-type:live_ncs_vlan-range;
            // NCS drop mandatory statement
            description
              "CE VLAN ID list.";
          }
        }
      }
      container qinq-any-access-limits {
        description
          "List of maximum number of access users on QinQ interfaces.";
        list qinq-any-access-limit {
          // NCS drop must statement
          key "pe-vlan-id";
          // NCS drop max-elements statement
          description
            "Configure maximum number of access users on a QinQ interface.";
          leaf pe-vlan-id {
            type uint16 {
              range "1..4094";
            }
            description
              "PE VLAN ID.";
          }
          leaf access-limit {
            type uint32 {
              range "0..65536";
            }
            // NCS drop mandatory statement
            description
              "Maximum number of users allowed.";
          }
        }
      }
    }
  }
  augment "/ncs:devices/ncs:device/ncs:config/ifm:ifm/ifm:interfaces/ifm:interface" {
    description
      "Extend interface attribute.";
    container dhcpv6-relay-attribute {
      tailf:ncs-device-type "netconf";
      tailf:display-when "not(../../../../../ncs:module) or ../../../../../ncs:module[ncs:name='huawei-dhcpv6']";
      must 'not(source-address and source-interface)' {
        tailf:xpath-root 3;
      }
      description
        "Configure DHCPv6 relay attributes on an interface.";
      leaf source-address {
        type inet:ipv6-address-no-zone;
        description
          "Source address.";
      }
      leaf link-address {
        type inet:ipv6-address-no-zone;
        description
          "Link address.";
      }
      leaf strict-check {
        type boolean;
        default "false";
        description
          "Enable/disable strict check on interfaces.";
      }
      leaf server-group-name {
        type leafref {
          path "/ncs:devices/ncs:device/ncs:config/dhcpv6:dhcpv6/dhcpv6:relay/dhcpv6:server-groups/dhcpv6:server-group/dhcpv6:name" {
            tailf:xpath-root 3;
          }
        }
        description
          "DHCPv6 relay server group name.";
      }
      leaf source-interface {
        type leafref {
          path "/ncs:devices/ncs:device/ncs:config/ifm:ifm/ifm:interfaces/ifm:interface/ifm:name" {
            tailf:xpath-root 3;
          }
        }
        description
          "Configure the IPv6 address of an interface as the source IPv6 address of packets.";
      }
      container destination-addresses {
        description
          "List of DHCPv6 relay destination addresses.";
        list destination-address {
          key "ipv6-address";
          max-elements 8;
          description
            "Configure the DHCPv6 relay destination address.";
          leaf ipv6-address {
            type inet:ipv6-address-no-zone;
            description
              "Destination address.";
          }
        }
      }
      container destination-ifs {
        description
          "List of DHCPv6 relay destination interfaces.";
        list destination-if {
          key "if-name";
          max-elements 8;
          description
            "Configure DHCPv6 relay destination interface.";
          leaf if-name {
            type leafref {
              path "/ncs:devices/ncs:device/ncs:config/ifm:ifm/ifm:interfaces/ifm:interface/ifm:name" {
                tailf:xpath-root 3;
              }
            }
            must "not(((../../../../ifm:type = 'Virtual-Ethernet') or (../../../../ifm:type = 'Global-VE')) and (../../../../ifm:class = 'main-interface'))" {
              tailf:xpath-root 3;
            }
            description
              "Destination interface name.";
          }
        }
      }
      container option {
        description
          "Configure DHCPv6 relay option attributes.";
        choice interface-id-mode {
          description
            "Configure the interface-id-mode.";
          case cn-telecom {
            description
              "CN-telecom interface-id mode.";
            leaf cn-telecom-mode {
              type empty;
              description
                "CN-telecom interface-id mode.";
            }
          }
          case cn-telecom-inherit {
            description
              "CN-telecom-inherit interface-id mode.";
            leaf cn-telecom-inherit-mode {
              type empty;
              description
                "CN-telecom-inherit interface-id mode.";
            }
          }
          case tr-101 {
            description
              "TR-101 interface-id mode.";
            leaf tr-101-mode {
              type empty;
              description
                "TR-101 interface-id mode.";
            }
          }
          case user-defined {
            description
              "User-defined interface-id mode.";
            leaf interface-id-text {
              type string {
                length "1..255";
                pattern '([^\t]{1,})';
              }
              description
                "DHCPv6 interface-id string defined by users.";
            }
          }
        }
        choice remote-id-mode {
          description
            "Configure the remote-id mode.";
          case default {
            description
              "Default remote-id mode.";
            leaf default-format {
              type empty;
              description
                "Default remote-id mode.";
            }
          }
          case user-defined {
            description
              "User-defined remote-id mode.";
            leaf remote-id-text {
              type string {
                length "1..255";
                pattern '([^\t]{1,})';
              }
              description
                "DHCPv6 remote-id string defined by users.";
            }
          }
        }
        leaf insert-subscriber-id {
          type boolean;
          default "false";
          description
            "Enable/disable to insert the subscriber-id option.";
        }
      }
      container rebuild-option {
        description
          "Configure DHCPv6 relay option rebuild attributes.";
        leaf rebuild-interface-id {
          type empty;
          description
            "Rebuild the interface-id option.";
        }
        leaf rebuild-remote-id {
          type empty;
          description
            "Rebuild the remote-id option.";
        }
      }
      container access-limit-setting {
        description
          "Configure the maximum number of access users on an interface.";
        leaf access-limit {
          type uint32 {
            range "0..65536";
          }
          description
            "Maximum number of access users on an interface.";
        }
        leaf access-vlan-limit {
          when '(../../../ethernet:ethernet/ethernet:l3-sub-interface/ethernet:dot1q-termination) or (../../../ethernet:ethernet/ethernet:l3-sub-interface/ethernet:qinq-termination) or (../../../ethernet:ethernet/ethernet:l3-sub-interface/ethernet:vlan-type-dot1q)' {
            tailf:xpath-root 3;
          }
          type uint32 {
            range "0..65536";
          }
          description
            "Maximum number of access users in any VLAN.";
        }
      }
      container pd-route-track-vrrp {
        description
          "Configure DHCPv6 relay PD routes track VRRP.";
        leaf degrade-cost {
          type uint32 {
            range "1..4294967295";
          }
          description
            "Cost value to be adjusted for DHCPv6 relay PD route.";
        }
      }
      container dot1q-access-limits {
        description
          "List of maximum number of access users on dot1q interfaces.";
        list dot1q-access-limit {
          must '(../../../ethernet:ethernet/ethernet:l3-sub-interface/ethernet:dot1q-termination) or (../../../ethernet:ethernet/ethernet:l3-sub-interface/ethernet:vlan-type-dot1q)' {
            tailf:xpath-root 3;
          }
          key "access-limit";
          description
            "Configure maximum number of access users on a dot1q interface.";
          leaf access-limit {
            type uint32 {
              range "0..65536";
            }
            description
              "Maximum number of users allowed.";
          }
          leaf vlan-list {
            type pub-type:vlan-range;
            mandatory true;
            description
              "VLAN list.";
          }
        }
      }
      container qinq-access-limits {
        description
          "List of maximum number of access users on QinQ interfaces.";
        list qinq-access-limit {
          must '../../../ethernet:ethernet/ethernet:l3-sub-interface/ethernet:qinq-termination' {
            tailf:xpath-root 3;
          }
          key "access-limit pe-vlan-id";
          description
            "Configure maximum number of access users on a QinQ interface.";
          leaf access-limit {
            type uint32 {
              range "0..65536";
            }
            description
              "Maximum number of users allowed.";
          }
          leaf pe-vlan-id {
            type uint16 {
              range "1..4094";
            }
            description
              "PE VLAN ID.";
          }
          leaf ce-vlan-list {
            type pub-type:vlan-range;
            mandatory true;
            description
              "CE VLAN ID list.";
          }
        }
      }
      container qinq-any-access-limits {
        description
          "List of maximum number of access users on QinQ interfaces.";
        list qinq-any-access-limit {
          must '../../../ethernet:ethernet/ethernet:l3-sub-interface/ethernet:qinq-termination' {
            tailf:xpath-root 3;
          }
          key "pe-vlan-id";
          max-elements 16;
          description
            "Configure maximum number of access users on a QinQ interface.";
          leaf pe-vlan-id {
            type uint16 {
              range "1..4094";
            }
            description
              "PE VLAN ID.";
          }
          leaf access-limit {
            type uint32 {
              range "0..65536";
            }
            mandatory true;
            description
              "Maximum number of users allowed.";
          }
        }
      }
    }
  }
}
