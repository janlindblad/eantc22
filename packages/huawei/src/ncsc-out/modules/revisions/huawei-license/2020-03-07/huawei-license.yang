module huawei-license {
  // Generated by yanger -t ncs
  tailf:mount-id "huawei-nc-1.0:huawei-nc-1.0";
  tailf:ncs-device-type "netconf";

  namespace "urn:huawei:yang:huawei-license";
  prefix lcs;

  import huawei-pub-type {
    prefix pub-type;
  }
  import ietf-yang-types {
    prefix yang;
  }
  import huawei-extension {
    prefix ext;
  }
  import ietf-inet-types {
    prefix inet;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Proof of permission granted.";

  revision 2020-03-07 {
    description
      "Init revision.";
    reference "Huawei private.";
  }
  ext:task-name "license";

  typedef ncs_template_auth-type {
    type string;
    description
      "Type of license authority.";
  }

  typedef ncs_template_spec-type {
    type string;
    description
      "Type of license spec.";
  }

  typedef ncs_template_state-type {
    type string;
    description
      "Type of license state.";
  }

  typedef ncs_template_item-status-type {
    type string;
    description
      "Type of license item status.";
  }

  typedef ncs_template_item-type {
    type string;
    description
      "Type of license item.";
  }

  typedef ncs_template_enable-status {
    type string;
    description
      "Type of enable status.";
  }

  typedef ncs_template_mode-type {
    type string;
    description
      "Type of license mode.";
  }

  typedef ncs_template_register-state {
    type string;
    description
      "The register state.";
  }

  typedef ncs_rpc_notif_auth-type {
    type enumeration {
      enum "demo" {
        value 0;
        description
          "Demo of a license file.";
      }
      enum "commercial" {
        value 1;
        description
          "Commercial of a license file.";
      }
    }
    description
      "Type of license authority.";
  }

  typedef ncs_rpc_notif_spec-type {
    type enumeration {
      enum "resource" {
        value 0;
        description
          "The resource of item.";
      }
      enum "function" {
        value 1;
        description
          "The function of item.";
      }
      enum "minimum" {
        value 2;
        description
          "The minimum of item.";
      }
      enum "default" {
        value 3;
        description
          "The default of item.";
      }
      enum "maximum" {
        value 4;
        description
          "The maximum of item.";
      }
    }
    description
      "Type of license spec.";
  }

  typedef ncs_rpc_notif_state-type {
    type enumeration {
      enum "default" {
        value 0;
        description
          "To indicate the license activating state of the system, the value is 'default'.";
      }
      enum "trial" {
        value 1;
        description
          "To indicate the license activating state of the system, the value is 'trial'.";
      }
      enum "normal" {
        value 2;
        description
          "To indicate the license activating state of the system, the value is 'normal'.";
      }
      enum "emergency" {
        value 3;
        description
          "To indicate the license activating state of the system, the value is 'emergency'.";
      }
      enum "demo" {
        value 4;
        description
          "To indicate the license activating state of the system, the value is 'demo'.";
      }
    }
    description
      "Type of license state.";
  }

  typedef ncs_rpc_notif_item-status-type {
    type enumeration {
      enum "default" {
        value 0;
        description
          "To indicate the license item status, the value is 'default'.";
      }
      enum "trial" {
        value 1;
        description
          "To indicate the license item status, the value is 'trial'.";
      }
      enum "normal" {
        value 2;
        description
          "To indicate the license item status, the value is 'normal'.";
      }
      enum "emergency" {
        value 3;
        description
          "To indicate the license item status, the value is 'emergency'.";
      }
      enum "demo" {
        value 4;
        description
          "To indicate the license item status, the value is 'demo'.";
      }
      enum "inactive" {
        value 5;
        description
          "To indicate the license item status, the value is 'inactive'.";
      }
    }
    description
      "Type of license item status.";
  }

  typedef ncs_rpc_notif_item-type {
    type enumeration {
      enum "resource" {
        value 0;
        description
          "The resource of license item.";
      }
      enum "function" {
        value 1;
        description
          "The function of license item.";
      }
    }
    description
      "Type of license item.";
  }

  typedef ncs_rpc_notif_enable-status {
    type enumeration {
      enum "disable" {
        value 0;
        description
          "The disable status.";
      }
      enum "enable" {
        value 1;
        description
          "The enable status.";
      }
      enum "not-supported" {
        value 2;
        description
          "The not supported status.";
      }
    }
    description
      "Type of enable status.";
  }

  typedef ncs_rpc_notif_mode-type {
    type enumeration {
      enum "common" {
        value 1;
        description
          "Common type.";
      }
      enum "cloud" {
        value 2;
        description
          "Cloud type.";
      }
    }
    description
      "Type of license mode.";
  }

  typedef ncs_rpc_notif_register-state {
    type enumeration {
      enum "register" {
        value 1;
        description
          "Register state.";
      }
      enum "unregister" {
        value 2;
        description
          "Unregister state.";
      }
    }
    description
      "The register state.";
  }

  typedef live_ncs_auth-type {
    type enumeration {
      enum "demo" {
        value 0;
        description
          "Demo of a license file.";
      }
      enum "commercial" {
        value 1;
        description
          "Commercial of a license file.";
      }
    }
    description
      "Type of license authority.";
  }

  typedef live_ncs_spec-type {
    type enumeration {
      enum "resource" {
        value 0;
        description
          "The resource of item.";
      }
      enum "function" {
        value 1;
        description
          "The function of item.";
      }
      enum "minimum" {
        value 2;
        description
          "The minimum of item.";
      }
      enum "default" {
        value 3;
        description
          "The default of item.";
      }
      enum "maximum" {
        value 4;
        description
          "The maximum of item.";
      }
    }
    description
      "Type of license spec.";
  }

  typedef live_ncs_state-type {
    type enumeration {
      enum "default" {
        value 0;
        description
          "To indicate the license activating state of the system, the value is 'default'.";
      }
      enum "trial" {
        value 1;
        description
          "To indicate the license activating state of the system, the value is 'trial'.";
      }
      enum "normal" {
        value 2;
        description
          "To indicate the license activating state of the system, the value is 'normal'.";
      }
      enum "emergency" {
        value 3;
        description
          "To indicate the license activating state of the system, the value is 'emergency'.";
      }
      enum "demo" {
        value 4;
        description
          "To indicate the license activating state of the system, the value is 'demo'.";
      }
    }
    description
      "Type of license state.";
  }

  typedef live_ncs_item-status-type {
    type enumeration {
      enum "default" {
        value 0;
        description
          "To indicate the license item status, the value is 'default'.";
      }
      enum "trial" {
        value 1;
        description
          "To indicate the license item status, the value is 'trial'.";
      }
      enum "normal" {
        value 2;
        description
          "To indicate the license item status, the value is 'normal'.";
      }
      enum "emergency" {
        value 3;
        description
          "To indicate the license item status, the value is 'emergency'.";
      }
      enum "demo" {
        value 4;
        description
          "To indicate the license item status, the value is 'demo'.";
      }
      enum "inactive" {
        value 5;
        description
          "To indicate the license item status, the value is 'inactive'.";
      }
    }
    description
      "Type of license item status.";
  }

  typedef live_ncs_item-type {
    type enumeration {
      enum "resource" {
        value 0;
        description
          "The resource of license item.";
      }
      enum "function" {
        value 1;
        description
          "The function of license item.";
      }
    }
    description
      "Type of license item.";
  }

  typedef live_ncs_enable-status {
    type enumeration {
      enum "disable" {
        value 0;
        description
          "The disable status.";
      }
      enum "enable" {
        value 1;
        description
          "The enable status.";
      }
      enum "not-supported" {
        value 2;
        description
          "The not supported status.";
      }
    }
    description
      "Type of enable status.";
  }

  typedef live_ncs_mode-type {
    type enumeration {
      enum "common" {
        value 1;
        description
          "Common type.";
      }
      enum "cloud" {
        value 2;
        description
          "Cloud type.";
      }
    }
    description
      "Type of license mode.";
  }

  typedef live_ncs_register-state {
    type enumeration {
      enum "register" {
        value 1;
        description
          "Register state.";
      }
      enum "unregister" {
        value 2;
        description
          "Unregister state.";
      }
    }
    description
      "The register state.";
  }

  typedef auth-type {
    type enumeration {
      enum "demo" {
        value 0;
        description
          "Demo of a license file.";
      }
      enum "commercial" {
        value 1;
        description
          "Commercial of a license file.";
      }
    }
    description
      "Type of license authority.";
  }

  typedef spec-type {
    type enumeration {
      enum "resource" {
        value 0;
        description
          "The resource of item.";
      }
      enum "function" {
        value 1;
        description
          "The function of item.";
      }
      enum "minimum" {
        value 2;
        description
          "The minimum of item.";
      }
      enum "default" {
        value 3;
        description
          "The default of item.";
      }
      enum "maximum" {
        value 4;
        description
          "The maximum of item.";
      }
    }
    description
      "Type of license spec.";
  }

  typedef state-type {
    type enumeration {
      enum "default" {
        value 0;
        description
          "To indicate the license activating state of the system, the value is 'default'.";
      }
      enum "trial" {
        value 1;
        description
          "To indicate the license activating state of the system, the value is 'trial'.";
      }
      enum "normal" {
        value 2;
        description
          "To indicate the license activating state of the system, the value is 'normal'.";
      }
      enum "emergency" {
        value 3;
        description
          "To indicate the license activating state of the system, the value is 'emergency'.";
      }
      enum "demo" {
        value 4;
        description
          "To indicate the license activating state of the system, the value is 'demo'.";
      }
    }
    description
      "Type of license state.";
  }

  typedef item-status-type {
    type enumeration {
      enum "default" {
        value 0;
        description
          "To indicate the license item status, the value is 'default'.";
      }
      enum "trial" {
        value 1;
        description
          "To indicate the license item status, the value is 'trial'.";
      }
      enum "normal" {
        value 2;
        description
          "To indicate the license item status, the value is 'normal'.";
      }
      enum "emergency" {
        value 3;
        description
          "To indicate the license item status, the value is 'emergency'.";
      }
      enum "demo" {
        value 4;
        description
          "To indicate the license item status, the value is 'demo'.";
      }
      enum "inactive" {
        value 5;
        description
          "To indicate the license item status, the value is 'inactive'.";
      }
    }
    description
      "Type of license item status.";
  }

  typedef item-type {
    type enumeration {
      enum "resource" {
        value 0;
        description
          "The resource of license item.";
      }
      enum "function" {
        value 1;
        description
          "The function of license item.";
      }
    }
    description
      "Type of license item.";
  }

  typedef enable-status {
    type enumeration {
      enum "disable" {
        value 0;
        description
          "The disable status.";
      }
      enum "enable" {
        value 1;
        description
          "The enable status.";
      }
      enum "not-supported" {
        value 2;
        description
          "The not supported status.";
      }
    }
    description
      "Type of enable status.";
  }

  typedef mode-type {
    type enumeration {
      enum "common" {
        value 1;
        description
          "Common type.";
      }
      enum "cloud" {
        value 2;
        description
          "Cloud type.";
      }
    }
    description
      "Type of license mode.";
  }

  typedef register-state {
    type enumeration {
      enum "register" {
        value 1;
        description
          "Register state.";
      }
      enum "unregister" {
        value 2;
        description
          "Unregister state.";
      }
    }
    description
      "The register state.";
  }

  augment "/ncs:devices/ncs:device/ncs:rpc" {
    container rpc-license-switch-mode {
      tailf:ncs-device-type "netconf";
      tailf:display-when "not(../../ncs:module) or ../../ncs:module[ncs:name='huawei-license']";
      tailf:action license-switch-mode {
        tailf:actionpoint ncsproxy {
          tailf:internal;
        }
        description
          "Switch license mode.";
        input {
          leaf license-mode {
            type ncs_rpc_notif_mode-type;
            description
              "License mode.";
          }
        }
      }
    }
  }
  augment "/ncs:devices/ncs:device-group/ncs:ned-id/ncs:rpc" {
    container rpc-license-switch-mode {
      tailf:ncs-device-type "netconf";
      tailf:display-when "/ncs:devices/ncs:device[ncs:name=current()/../../../ncs:member]/ncs:module[ncs:name='huawei-license']";
      tailf:action license-switch-mode {
        tailf:actionpoint ncsproxy {
          tailf:internal;
        }
        description
          "Switch license mode.";
        input {
          leaf license-mode {
            type ncs_rpc_notif_mode-type;
            description
              "License mode.";
          }
        }
      }
    }
  }
  augment "/ncs:devices/ncs:device/ncs:rpc" {
    container rpc-license-smooth {
      tailf:ncs-device-type "netconf";
      tailf:display-when "not(../../ncs:module) or ../../ncs:module[ncs:name='huawei-license']";
      tailf:action license-smooth {
        tailf:actionpoint ncsproxy {
          tailf:internal;
        }
        description
          "Smooth license.";
      }
    }
  }
  augment "/ncs:devices/ncs:device-group/ncs:ned-id/ncs:rpc" {
    container rpc-license-smooth {
      tailf:ncs-device-type "netconf";
      tailf:display-when "/ncs:devices/ncs:device[ncs:name=current()/../../../ncs:member]/ncs:module[ncs:name='huawei-license']";
      tailf:action license-smooth {
        tailf:actionpoint ncsproxy {
          tailf:internal;
        }
        description
          "Smooth license.";
      }
    }
  }
  augment "/ncs:devices/ncs:device/ncs:rpc" {
    container rpc-license-assign {
      tailf:ncs-device-type "netconf";
      tailf:display-when "not(../../ncs:module) or ../../ncs:module[ncs:name='huawei-license']";
      tailf:action license-assign {
        tailf:actionpoint ncsproxy {
          tailf:internal;
        }
        description
          "Assign cloud license.";
        input {
          leaf item-name {
            type string {
              length "1..31";
            }
            description
              "License item.";
          }
          leaf item-num {
            type uint32;
            description
              "License number.";
          }
        }
      }
    }
  }
  augment "/ncs:devices/ncs:device-group/ncs:ned-id/ncs:rpc" {
    container rpc-license-assign {
      tailf:ncs-device-type "netconf";
      tailf:display-when "/ncs:devices/ncs:device[ncs:name=current()/../../../ncs:member]/ncs:module[ncs:name='huawei-license']";
      tailf:action license-assign {
        tailf:actionpoint ncsproxy {
          tailf:internal;
        }
        description
          "Assign cloud license.";
        input {
          leaf item-name {
            type string {
              length "1..31";
            }
            description
              "License item.";
          }
          leaf item-num {
            type uint32;
            description
              "License number.";
          }
        }
      }
    }
  }
  augment "/ncs:devices/ncs:device/ncs:rpc" {
    container rpc-license-emergency {
      tailf:ncs-device-type "netconf";
      tailf:display-when "not(../../ncs:module) or ../../ncs:module[ncs:name='huawei-license']";
      tailf:action license-emergency {
        tailf:actionpoint ncsproxy {
          tailf:internal;
        }
        description
          "To activate license emergency mode.";
      }
    }
  }
  augment "/ncs:devices/ncs:device-group/ncs:ned-id/ncs:rpc" {
    container rpc-license-emergency {
      tailf:ncs-device-type "netconf";
      tailf:display-when "/ncs:devices/ncs:device[ncs:name=current()/../../../ncs:member]/ncs:module[ncs:name='huawei-license']";
      tailf:action license-emergency {
        tailf:actionpoint ncsproxy {
          tailf:internal;
        }
        description
          "To activate license emergency mode.";
      }
    }
  }
  augment "/ncs:devices/ncs:device/ncs:rpc" {
    container rpc-startup-paf {
      tailf:ncs-device-type "netconf";
      tailf:display-when "not(../../ncs:module) or ../../ncs:module[ncs:name='huawei-license']";
      tailf:action startup-paf {
        tailf:actionpoint ncsproxy {
          tailf:internal;
        }
        description
          "Configure an existing PAF file as the startup PAF file.";
        input {
          leaf filename {
            type string {
              length "5..48";
            }
            mandatory true;
            description
              "Name of a PAF file.";
          }
        }
      }
    }
  }
  augment "/ncs:devices/ncs:device-group/ncs:ned-id/ncs:rpc" {
    container rpc-startup-paf {
      tailf:ncs-device-type "netconf";
      tailf:display-when "/ncs:devices/ncs:device[ncs:name=current()/../../../ncs:member]/ncs:module[ncs:name='huawei-license']";
      tailf:action startup-paf {
        tailf:actionpoint ncsproxy {
          tailf:internal;
        }
        description
          "Configure an existing PAF file as the startup PAF file.";
        input {
          leaf filename {
            type string {
              length "5..48";
            }
            mandatory true;
            description
              "Name of a PAF file.";
          }
        }
      }
    }
  }
  augment "/ncs:devices/ncs:device/ncs:rpc" {
    container rpc-license-export {
      tailf:ncs-device-type "netconf";
      tailf:display-when "not(../../ncs:module) or ../../ncs:module[ncs:name='huawei-license']";
      tailf:action license-export {
        tailf:actionpoint ncsproxy {
          tailf:internal;
        }
        description
          "Export the license to a file.";
        input {
          leaf filename {
            type string {
              length "5..127";
            }
            description
              "The file name of exporting license.";
          }
        }
      }
    }
  }
  augment "/ncs:devices/ncs:device-group/ncs:ned-id/ncs:rpc" {
    container rpc-license-export {
      tailf:ncs-device-type "netconf";
      tailf:display-when "/ncs:devices/ncs:device[ncs:name=current()/../../../ncs:member]/ncs:module[ncs:name='huawei-license']";
      tailf:action license-export {
        tailf:actionpoint ncsproxy {
          tailf:internal;
        }
        description
          "Export the license to a file.";
        input {
          leaf filename {
            type string {
              length "5..127";
            }
            description
              "The file name of exporting license.";
          }
        }
      }
    }
  }
  augment "/ncs:devices/ncs:device/ncs:rpc" {
    container rpc-license-trial {
      tailf:ncs-device-type "netconf";
      tailf:display-when "not(../../ncs:module) or ../../ncs:module[ncs:name='huawei-license']";
      tailf:action license-trial {
        tailf:actionpoint ncsproxy {
          tailf:internal;
        }
        description
          "Enable or disable the trial of a specific control item.";
        input {
          leaf trial-switch {
            type boolean;
            mandatory true;
            description
              "Whether to enable or disable the trial function of a control item.";
          }
        }
      }
    }
  }
  augment "/ncs:devices/ncs:device-group/ncs:ned-id/ncs:rpc" {
    container rpc-license-trial {
      tailf:ncs-device-type "netconf";
      tailf:display-when "/ncs:devices/ncs:device[ncs:name=current()/../../../ncs:member]/ncs:module[ncs:name='huawei-license']";
      tailf:action license-trial {
        tailf:actionpoint ncsproxy {
          tailf:internal;
        }
        description
          "Enable or disable the trial of a specific control item.";
        input {
          leaf trial-switch {
            type boolean;
            mandatory true;
            description
              "Whether to enable or disable the trial function of a control item.";
          }
        }
      }
    }
  }
  augment "/ncs:devices/ncs:device/ncs:rpc" {
    container rpc-license-delete {
      tailf:ncs-device-type "netconf";
      tailf:display-when "not(../../ncs:module) or ../../ncs:module[ncs:name='huawei-license']";
      tailf:action license-delete {
        tailf:actionpoint ncsproxy {
          tailf:internal;
        }
        description
          "To delete a license file in $_license.";
        input {
          leaf filename {
            type string {
              length "1..127";
            }
            description
              "The name of a license file.";
          }
        }
      }
    }
  }
  augment "/ncs:devices/ncs:device-group/ncs:ned-id/ncs:rpc" {
    container rpc-license-delete {
      tailf:ncs-device-type "netconf";
      tailf:display-when "/ncs:devices/ncs:device[ncs:name=current()/../../../ncs:member]/ncs:module[ncs:name='huawei-license']";
      tailf:action license-delete {
        tailf:actionpoint ncsproxy {
          tailf:internal;
        }
        description
          "To delete a license file in $_license.";
        input {
          leaf filename {
            type string {
              length "1..127";
            }
            description
              "The name of a license file.";
          }
        }
      }
    }
  }
  augment "/ncs:devices/ncs:device/ncs:rpc" {
    container rpc-license-revoke-chassis {
      tailf:ncs-device-type "netconf";
      tailf:display-when "not(../../ncs:module) or ../../ncs:module[ncs:name='huawei-license']";
      tailf:action license-revoke-chassis {
        tailf:actionpoint ncsproxy {
          tailf:internal;
        }
        description
          "To revoke a license file by device ID.";
        input {
          leaf chassis-id {
            type string {
              length "1..31";
            }
            description
              "The device ID of revoke license action.";
          }
        }
      }
    }
  }
  augment "/ncs:devices/ncs:device-group/ncs:ned-id/ncs:rpc" {
    container rpc-license-revoke-chassis {
      tailf:ncs-device-type "netconf";
      tailf:display-when "/ncs:devices/ncs:device[ncs:name=current()/../../../ncs:member]/ncs:module[ncs:name='huawei-license']";
      tailf:action license-revoke-chassis {
        tailf:actionpoint ncsproxy {
          tailf:internal;
        }
        description
          "To revoke a license file by device ID.";
        input {
          leaf chassis-id {
            type string {
              length "1..31";
            }
            description
              "The device ID of revoke license action.";
          }
        }
      }
    }
  }
  augment "/ncs:devices/ncs:device/ncs:rpc" {
    container rpc-license-verify {
      tailf:ncs-device-type "netconf";
      tailf:display-when "not(../../ncs:module) or ../../ncs:module[ncs:name='huawei-license']";
      tailf:action license-verify {
        tailf:actionpoint ncsproxy {
          tailf:internal;
        }
        description
          "To verify a license file.";
        ext:node-ref "/lcs";
        input {
          leaf filename {
            type string {
              length "5..127";
            }
            description
              "The name of a license file.";
          }
        }
      }
    }
  }
  augment "/ncs:devices/ncs:device-group/ncs:ned-id/ncs:rpc" {
    container rpc-license-verify {
      tailf:ncs-device-type "netconf";
      tailf:display-when "/ncs:devices/ncs:device[ncs:name=current()/../../../ncs:member]/ncs:module[ncs:name='huawei-license']";
      tailf:action license-verify {
        tailf:actionpoint ncsproxy {
          tailf:internal;
        }
        description
          "To verify a license file.";
        ext:node-ref "/lcs";
        input {
          leaf filename {
            type string {
              length "5..127";
            }
            description
              "The name of a license file.";
          }
        }
      }
    }
  }
  augment "/ncs:devices/ncs:device/ncs:rpc" {
    container rpc-license-revoke {
      tailf:ncs-device-type "netconf";
      tailf:display-when "not(../../ncs:module) or ../../ncs:module[ncs:name='huawei-license']";
      tailf:action license-revoke {
        tailf:actionpoint ncsproxy {
          tailf:internal;
        }
        description
          "To revoke a license file.";
      }
    }
  }
  augment "/ncs:devices/ncs:device-group/ncs:ned-id/ncs:rpc" {
    container rpc-license-revoke {
      tailf:ncs-device-type "netconf";
      tailf:display-when "/ncs:devices/ncs:device[ncs:name=current()/../../../ncs:member]/ncs:module[ncs:name='huawei-license']";
      tailf:action license-revoke {
        tailf:actionpoint ncsproxy {
          tailf:internal;
        }
        description
          "To revoke a license file.";
      }
    }
  }
  augment "/ncs:devices/ncs:device/ncs:rpc" {
    container rpc-license-active {
      tailf:ncs-device-type "netconf";
      tailf:display-when "not(../../ncs:module) or ../../ncs:module[ncs:name='huawei-license']";
      tailf:action license-active {
        tailf:actionpoint ncsproxy {
          tailf:internal;
        }
        description
          "To active a license file.";
        input {
          leaf filename {
            type string {
              length "5..127";
            }
            description
              "The name of a license file.";
          }
        }
      }
    }
  }
  augment "/ncs:devices/ncs:device-group/ncs:ned-id/ncs:rpc" {
    container rpc-license-active {
      tailf:ncs-device-type "netconf";
      tailf:display-when "/ncs:devices/ncs:device[ncs:name=current()/../../../ncs:member]/ncs:module[ncs:name='huawei-license']";
      tailf:action license-active {
        tailf:actionpoint ncsproxy {
          tailf:internal;
        }
        description
          "To active a license file.";
        input {
          leaf filename {
            type string {
              length "5..127";
            }
            description
              "The name of a license file.";
          }
        }
      }
    }
  }
  augment "/ncs:devices/ncs:device/ncs:config" {
    container license {
      tailf:ncs-device-type "netconf";
      tailf:display-when "not(../../ncs:module) or ../../ncs:module[ncs:name='huawei-license']";
      description
        "Proof of permission granted.";
      // NCS drop config false container 'global-states'
      container license-items {
        description
          "List of all license items.";
        list license-item {
          ext:operation-exclude "create";
          ext:generated-by "system";
          key "name";
          description
            "Configure license item.";
          leaf name {
            type string {
              length "1..31";
            }
            description
              "License item name.";
          }
          // NCS drop config false leaf description
          // NCS drop config false leaf 'default-value'
          // NCS drop config false leaf 'maximum-value'
          // NCS drop config false leaf 'current-value'
          // NCS drop config false leaf 'used-value'
          // NCS drop config false leaf status
          // NCS drop config false leaf 'expired-date'
          // NCS drop config false leaf type
          // NCS drop config false leaf 'trial-state'
          // NCS drop config false leaf 'trial-remain-day'
          // NCS drop config false leaf 'trial-remain-times'
        }
      }
      // NCS drop config false container 'license-sale-items'
      // NCS drop config false container 'stack-sale-items'
      // NCS drop config false container 'spec-items'
      // NCS drop config false container 'license-files'
      // NCS drop config false container 'resource-usages'
      // NCS drop config false container 'resource-thresholds'
      container cloud-servers {
        description
          "List of cloud license servers.";
        list cloud-server {
          key "server-ip server-port";
          max-elements 1;
          description
            "Configure cloud license server.";
          leaf server-ip {
            type inet:ipv4-address-no-zone;
            description
              "The IP address of cloud license server.";
          }
          leaf server-port {
            type uint32;
            description
              "The port of cloud license server.";
          }
          // NCS drop config false leaf 'register-state'
          // NCS drop config false leaf 'policy-name'
        }
      }
    }
  }
  augment "/ncs:devices/ncs:device/ncs:live-status" {
    container license {
      tailf:ncs-device-type "netconf";
      tailf:display-when "not(../../ncs:module) or ../../ncs:module[ncs:name='huawei-license'] or (../../ncs:live-status-protocol[not(ncs:capability)]) or (../../ncs:live-status-protocol/ncs:capability/ncs:module[.='huawei-license'])";
      description
        "Proof of permission granted.";
      container global-states {
        description
          "List of the global license informations.";
        list global-state {
          key "chassis-id";
          description
            "Operational state of the global license information.";
          leaf chassis-id {
            type string {
              length "0..31";
            }
            description
              "The device ID of a license file.";
          }
          leaf active-filename {
            type string {
              length "5..127";
            }
            description
              "The name of a license file.";
          }
          leaf active-state {
            type live_ncs_state-type;
            description
              "To indicate the license activating state of the system, the value can be 'normal' or 'default'.";
          }
          leaf revoke-ticket {
            type string {
              length "1..135";
            }
            description
              "The revoket-ticket of a license file.";
          }
          leaf esn {
            type string {
              length "1..2047";
            }
            description
              "The License ESN.";
          }
          leaf license-mode {
            type live_ncs_mode-type;
            description
              "License mode.";
          }
        }
      }
      container license-items {
        description
          "List of all license items.";
        list license-item {
          ext:operation-exclude "create";
          ext:generated-by "system";
          key "name";
          description
            "Configure license item.";
          leaf name {
            type string {
              length "1..31";
            }
            description
              "License item name.";
          }
          leaf description {
            type string {
              length "1..255";
            }
            description
              "The description of a license item.";
          }
          leaf default-value {
            type uint32;
            description
              "The default value of a license item.";
          }
          leaf maximum-value {
            type uint32;
            description
              "The maximum value of a license item.";
          }
          leaf current-value {
            type uint32;
            description
              "The current value of a license item.";
          }
          leaf used-value {
            type uint32;
            description
              "The usage value of a license item.";
          }
          leaf status {
            type live_ncs_item-status-type;
            description
              "The status of a license item.";
          }
          leaf expired-date {
            type string {
              length "1..71";
            }
            description
              "The expired date of a license item.";
          }
          leaf type {
            type live_ncs_item-type;
            description
              "The type of a license item.";
          }
          leaf trial-state {
            type live_ncs_enable-status;
            description
              "Trial status of a control item.";
          }
          leaf trial-remain-day {
            type uint32;
            description
              "Remaining trial days of a license control item.";
          }
          leaf trial-remain-times {
            type uint32;
            description
              "Remaining trial times of a license control item.";
          }
        }
      }
      container license-sale-items {
        description
          "List of all license saleitems.";
        list license-sale-item {
          key "name";
          description
            "Operational state of license saleitem.";
          leaf name {
            type string {
              length "1..31";
            }
            description
              "License saleitem name.";
          }
          leaf description {
            type string {
              length "1..255";
            }
            description
              "The description of a license saleitem.";
          }
          leaf sale-value {
            type uint32;
            description
              "The sales value of a license saleitem.";
          }
          container sub-sale-items {
            description
              "List of all license sub saleitems.";
            list sub-sale-item {
              key "name";
              description
                "Operational state of license sub saleitem.";
              leaf name {
                type string {
                  length "1..31";
                }
                description
                  "License sub saleitem name.";
              }
              leaf description {
                type string {
                  length "1..255";
                }
                description
                  "The description of a license sub saleitem.";
              }
              leaf sale-value {
                type uint32;
                description
                  "The sales value of a license sub saleitem.";
              }
              container license-items {
                description
                  "List of all license items.";
                list license-item {
                  key "name";
                  description
                    "Operational state of license item.";
                  leaf name {
                    type string {
                      length "1..31";
                    }
                    description
                      "License item name.";
                  }
                  leaf description {
                    type string {
                      length "1..255";
                    }
                    description
                      "The description of a license item.";
                  }
                  leaf default-value {
                    type uint32;
                    description
                      "The default value of a license item.";
                  }
                  leaf maximum-value {
                    type uint32;
                    description
                      "The maximum value of a license item.";
                  }
                  leaf current-value {
                    type uint32;
                    description
                      "The current value of a license item.";
                  }
                  leaf used-value {
                    type uint32;
                    description
                      "The usage value of a license item.";
                  }
                  leaf status {
                    type live_ncs_item-status-type;
                    description
                      "The status of a license item.";
                  }
                  leaf expired-date {
                    type string {
                      length "1..71";
                    }
                    description
                      "The expired date of a license item.";
                  }
                  leaf type {
                    type live_ncs_item-type;
                    description
                      "The type of a license item.";
                  }
                  leaf trial-state {
                    type live_ncs_enable-status;
                    description
                      "Trial status of a control item.";
                  }
                  leaf trial-remain-day {
                    type uint32;
                    description
                      "Remaining trial days of a license control item.";
                  }
                  leaf trial-remain-times {
                    type uint32;
                    description
                      "Remaining trial times of a license control item.";
                  }
                }
              }
            }
          }
          container license-items {
            description
              "List of all license items.";
            list license-item {
              key "name";
              description
                "Operational state of license item.";
              leaf name {
                type string {
                  length "1..31";
                }
                description
                  "License item name.";
              }
              leaf description {
                type string {
                  length "1..255";
                }
                description
                  "The description of a license item.";
              }
              leaf default-value {
                type uint32;
                description
                  "The default value of a license item.";
              }
              leaf maximum-value {
                type uint32;
                description
                  "The maximum value of a license item.";
              }
              leaf current-value {
                type uint32;
                description
                  "The current value of a license item.";
              }
              leaf used-value {
                type uint32;
                description
                  "The usage value of a license item.";
              }
              leaf status {
                type live_ncs_item-status-type;
                description
                  "The status of a license item.";
              }
              leaf expired-date {
                type string {
                  length "1..71";
                }
                description
                  "The expired date of a license item.";
              }
              leaf type {
                type live_ncs_item-type;
                description
                  "The type of a license item.";
              }
              leaf trial-state {
                type live_ncs_enable-status;
                description
                  "Trial status of a control item.";
              }
              leaf trial-remain-day {
                type uint32;
                description
                  "Remaining trial days of a license control item.";
              }
              leaf trial-remain-times {
                type uint32;
                description
                  "Remaining trial times of a license control item.";
              }
            }
          }
        }
      }
      container stack-sale-items {
        description
          "List of all license sale items.";
        list stack-sale-item {
          key "chassis-id";
          description
            "Operational state of license sale item.";
          leaf chassis-id {
            type string {
              length "0..31";
            }
            description
              "The device ID of license sale item.";
          }
          container license-sale-items {
            description
              "List of all license saleitems.";
            list license-sale-item {
              key "name";
              description
                "Operational state of license saleitem.";
              leaf name {
                type string {
                  length "1..31";
                }
                description
                  "License saleitem name.";
              }
              leaf description {
                type string {
                  length "1..255";
                }
                description
                  "The description of a license saleitem.";
              }
              leaf sale-value {
                type uint32;
                description
                  "The sales value of a license saleitem.";
              }
              container license-items {
                description
                  "List of all license items.";
                list license-item {
                  key "name";
                  description
                    "Operational state of license item.";
                  leaf name {
                    type string {
                      length "1..31";
                    }
                    description
                      "License item name.";
                  }
                  leaf description {
                    type string {
                      length "1..255";
                    }
                    description
                      "The description of a license item.";
                  }
                  leaf default-value {
                    type uint32;
                    description
                      "The default value of a license item.";
                  }
                  leaf maximum-value {
                    type uint32;
                    description
                      "The maximum value of a license item.";
                  }
                  leaf current-value {
                    type uint32;
                    description
                      "The current value of a license item.";
                  }
                  leaf used-value {
                    type uint32;
                    description
                      "The usage value of a license item.";
                  }
                  leaf status {
                    type live_ncs_item-status-type;
                    description
                      "The status of a license item.";
                  }
                  leaf expired-date {
                    type string {
                      length "1..71";
                    }
                    description
                      "The expired date of a license item.";
                  }
                  leaf type {
                    type live_ncs_item-type;
                    description
                      "The type of a license item.";
                  }
                  leaf trial-state {
                    type live_ncs_enable-status;
                    description
                      "Trial status of a control item.";
                  }
                  leaf trial-remain-day {
                    type uint32;
                    description
                      "Remaining trial days of a license control item.";
                  }
                  leaf trial-remain-times {
                    type uint32;
                    description
                      "Remaining trial times of a license control item.";
                  }
                }
              }
            }
          }
        }
      }
      container spec-items {
        description
          "List of all specific license items.";
        list spec-item {
          key "name";
          description
            "Operational state of specific license item.";
          leaf name {
            type string {
              length "0..63";
            }
            description
              "The name of a specific item.";
          }
          leaf description {
            type string {
              length "0..127";
            }
            description
              "Description of the specification.";
          }
          leaf current-value {
            type uint32;
            description
              "The value of a specific item.";
          }
          leaf type {
            type live_ncs_spec-type;
            description
              "The type of a specific item.";
          }
          leaf default-value {
            type uint32;
            description
              "The specification default value.";
          }
          leaf minimum-value {
            type uint32;
            description
              "The specification minimum value.";
          }
          leaf maximum-value {
            type uint32;
            description
              "The specification maximum value.";
          }
        }
      }
      container license-files {
        description
          "List of all information of a license file.";
        list license-file {
          key "chassis-id filename";
          description
            "Operational state of the information of a license file.";
          leaf chassis-id {
            type string {
              length "0..31";
            }
            description
              "The device ID of a license file.";
          }
          leaf filename {
            type string {
              length "5..127";
            }
            description
              "The name of a license file.";
          }
          leaf filesize {
            type uint32;
            description
              "The size of a license file.";
          }
          container general {
            description
              "Operational state of the general information of a license file.";
            leaf serial-number {
              type string {
                length "0..63";
              }
              description
                "The serial number of a license file.";
            }
            leaf creator {
              type string {
                length "0..63";
              }
              description
                "The creator of a license file.";
            }
            leaf created-time {
              type yang:date-and-time;
              description
                "The created time of a license file.";
            }
            leaf country {
              type string {
                length "0..63";
              }
              description
                "The country information of a license file.";
            }
            leaf customer {
              type string {
                length "0..63";
              }
              description
                "The customer information of a license file.";
            }
            leaf office {
              type string {
                length "0..63";
              }
              description
                "The office information of a license file.";
            }
            leaf file-expired-date {
              type pub-type:live_ncs_date;
              description
                "The expired date of a license file.";
            }
          }
          container features {
            description
              "List of all the feature information of a license file.";
            list feature {
              key "name";
              description
                "Operational state of the feature information of a license file.";
              leaf name {
                type string {
                  length "0..63";
                }
                description
                  "The feature information name of a license file.";
              }
              leaf product {
                type string {
                  length "0..63";
                }
                description
                  "The product information of a license file.";
              }
              leaf esn {
                type string {
                  length "0..2055";
                }
                description
                  "The ESN of a license file.";
              }
              leaf auth-type {
                type live_ncs_auth-type;
                description
                  "The authorizing type of a license file.";
              }
              leaf running-deadline {
                type pub-type:live_ncs_date;
                description
                  "The running deadline of a license file.";
              }
              leaf trial-days {
                type uint32;
                description
                  "List of the trial days of a license file.";
              }
              leaf software-deadline {
                type pub-type:live_ncs_date;
                description
                  "The software deadline of a license file.";
              }
              leaf hardware-deadline {
                type pub-type:live_ncs_date;
                description
                  "The hardware deadline of a license file.";
              }
              leaf upgrate-deadline {
                type pub-type:live_ncs_date;
                description
                  "The upgrate deadline of a license file.";
              }
              container feature-items {
                description
                  "List of all feature items of a license file.";
                list feature-item {
                  key "name";
                  description
                    "Operational state of feature item of a license file.";
                  leaf name {
                    type string {
                      length "0..63";
                    }
                    description
                      "Feature item name of a license file.";
                  }
                  leaf value {
                    type uint32;
                    description
                      "Feature item value of a license file.";
                  }
                }
              }
            }
          }
        }
      }
      container resource-usages {
        description
          "List of all license resource usages.";
        list resource-usage {
          key "name";
          description
            "Operational state of license resource usage.";
          leaf name {
            type string {
              length "0..31";
            }
            description
              "The name of resource item.";
          }
          leaf usage {
            type uint32;
            description
              "The usage of resource item.";
          }
          leaf active-value {
            type uint32;
            description
              "The active value of resource item.";
          }
        }
      }
      container resource-thresholds {
        description
          "List of license resource usage thresholds.";
        list resource-threshold {
          key "name";
          description
            "Operational state of license resource usage threshold.";
          leaf name {
            type string {
              length "0..31";
            }
            description
              "Name of a license resource control item.";
          }
          leaf threshold {
            type uint32 {
              range "50..95";
            }
            description
              "Usage threshold of a license control resource item.";
          }
          leaf configurable-switch {
            type uint32 {
              range "0..1";
            }
            // NCS drop default statement
            description
              "Configurable flag of a license resource item.";
          }
          leaf description {
            type string {
              length "0..255";
            }
            description
              "Description of a license resource control item.";
          }
        }
      }
      container cloud-servers {
        description
          "List of cloud license servers.";
        list cloud-server {
          key "server-ip server-port";
          // NCS drop max-elements statement
          description
            "Configure cloud license server.";
          leaf server-ip {
            type inet:ipv4-address-no-zone;
            description
              "The IP address of cloud license server.";
          }
          leaf server-port {
            type uint32;
            description
              "The port of cloud license server.";
          }
          leaf register-state {
            type live_ncs_register-state;
            description
              "The register state with cloud license server.";
          }
          leaf policy-name {
            type string {
              length "1..255";
            }
            description
              "The policy name.";
          }
        }
      }
    }
  }
  augment "/ncs:devices/ncs:template/ncs:ned-id/ncs:config" {
    container license {
      description
        "Proof of permission granted.";
      // NCS drop config false container 'global-states'
      container license-items {
        description
          "List of all license items.";
        list license-item {
          // NCS patched for predictable order
          ordered-by user;
          ext:operation-exclude "create";
          ext:generated-by "system";
          key "name";
          description
            "Configure license item.";
          leaf name {
            type string;
            description
              "License item name.";
          }
          // NCS drop config false leaf description
          // NCS drop config false leaf 'default-value'
          // NCS drop config false leaf 'maximum-value'
          // NCS drop config false leaf 'current-value'
          // NCS drop config false leaf 'used-value'
          // NCS drop config false leaf status
          // NCS drop config false leaf 'expired-date'
          // NCS drop config false leaf type
          // NCS drop config false leaf 'trial-state'
          // NCS drop config false leaf 'trial-remain-day'
          // NCS drop config false leaf 'trial-remain-times'
        }
      }
      // NCS drop config false container 'license-sale-items'
      // NCS drop config false container 'stack-sale-items'
      // NCS drop config false container 'spec-items'
      // NCS drop config false container 'license-files'
      // NCS drop config false container 'resource-usages'
      // NCS drop config false container 'resource-thresholds'
      container cloud-servers {
        description
          "List of cloud license servers.";
        list cloud-server {
          // NCS patched for predictable order
          ordered-by user;
          key "server-ip server-port";
          // NCS drop max-elements statement
          description
            "Configure cloud license server.";
          leaf server-ip {
            type string;
            description
              "The IP address of cloud license server.";
          }
          leaf server-port {
            type string;
            description
              "The port of cloud license server.";
          }
          // NCS drop config false leaf 'register-state'
          // NCS drop config false leaf 'policy-name'
        }
      }
    }
  }
}
