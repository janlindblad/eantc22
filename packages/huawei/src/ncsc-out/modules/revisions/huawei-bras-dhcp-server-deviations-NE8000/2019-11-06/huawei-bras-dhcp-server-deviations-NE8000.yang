module huawei-bras-dhcp-server-deviations-NE8000 {
  // Generated by yanger -t ncs
  tailf:mount-id "huawei-nc-1.0:huawei-nc-1.0";
  tailf:ncs-device-type "netconf";

  namespace "urn:huawei:yang:huawei-bras-dhcp-server-deviations-NE8000";
  prefix bras-dhcp-server-devs-NE8000;

  import huawei-bras-dhcp-server {
    prefix bras-dhcp-server;
  }
  import huawei-rbs {
    prefix rbs;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "This module defines deviation statements for huawei-bras-dhcp-server module.";

  revision 2019-11-06 {
    description
      "Initial revision.";
    reference "Huawei private.";
  }

  deviation "/ncs:devices/ncs:template/ncs:ned-id/ncs:config/bras-dhcp-server:bras-dhcp-server/bras-dhcp-server:dhcp-server-groups/bras-dhcp-server:dhcp-server-group/bras-dhcp-server:remote-backup-service-name" {
    deviate replace {
      type string;
    }
  }
  deviation "/ncs:devices/ncs:device/ncs:live-status/bras-dhcp-server:bras-dhcp-server/bras-dhcp-server:dhcp-server-groups/bras-dhcp-server:dhcp-server-group/bras-dhcp-server:remote-backup-service-name" {
    deviate replace {
      type leafref {
        path "/ncs:devices/ncs:device/ncs:live-status/rbs:rbs/rbs:services/rbs:service/rbs:name" {
          tailf:xpath-root 3;
        }
      }
    }
  }
  deviation "/ncs:devices/ncs:device/ncs:config/bras-dhcp-server:bras-dhcp-server/bras-dhcp-server:dhcp-server-groups/bras-dhcp-server:dhcp-server-group/bras-dhcp-server:remote-backup-service-name" {
    deviate replace {
      type leafref {
        path "/ncs:devices/ncs:device/ncs:config/rbs:rbs/rbs:services/rbs:service/rbs:name" {
          tailf:xpath-root 3;
        }
      }
    }
  }
}
