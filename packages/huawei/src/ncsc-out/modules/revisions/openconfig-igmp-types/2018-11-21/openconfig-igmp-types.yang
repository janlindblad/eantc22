module openconfig-igmp-types {
  // Generated by yanger -t ncs
  tailf:mount-id "huawei-nc-1.0:huawei-nc-1.0";
  tailf:ncs-device-type "netconf";

  yang-version 1;
  namespace "http://openconfig.net/yang/igmp/types";
  prefix oc-igmp-types;

  import openconfig-extensions {
    prefix oc-ext;
  }
  import tailf-common {
    prefix tailf;
  }
  import tailf-ncs {
    prefix ncs;
  }

  organization
    "OpenConfig working group";
  contact
    "OpenConfig working group
     www.openconfig.net";
  description
    "This module defines types related to the IGMP protocol model.";
  oc-ext:openconfig-version "0.1.1";

  revision 2018-11-21 {
    description
      "Add OpenConfig module metadata extensions.";
    reference "0.1.1";
  }
  revision 2018-02-19 {
    description
      "Initial revision.";
    reference "0.1.0";
  }
  oc-ext:regexp-posix;
  oc-ext:catalog-organization "openconfig";
  oc-ext:origin "openconfig";

  typedef ncs_template_igmp-version {
    type string;
    description
      "IGMP Version.";
    reference "v1 = RFC1112, v2 = RFC2236, v3 = RFC3376";
  }

  typedef ncs_template_igmp-interval-type {
    type string;
    units "seconds";
    description
      "Interval at which the router sends the IGMP query message toward
       the upstream neighbor.";
    reference "RFC3376 8.2 Page 40";
  }

  typedef ncs_rpc_notif_igmp-version {
    type uint8 {
      range "1..3";
    }
    description
      "IGMP Version.";
    reference "v1 = RFC1112, v2 = RFC2236, v3 = RFC3376";
  }

  typedef ncs_rpc_notif_igmp-interval-type {
    type uint16 {
      range "1..1024";
    }
    units "seconds";
    description
      "Interval at which the router sends the IGMP query message toward
       the upstream neighbor.";
    reference "RFC3376 8.2 Page 40";
  }

  typedef live_ncs_igmp-version {
    type uint8 {
      range "1..3";
    }
    description
      "IGMP Version.";
    reference "v1 = RFC1112, v2 = RFC2236, v3 = RFC3376";
  }

  typedef live_ncs_igmp-interval-type {
    type uint16 {
      range "1..1024";
    }
    units "seconds";
    description
      "Interval at which the router sends the IGMP query message toward
       the upstream neighbor.";
    reference "RFC3376 8.2 Page 40";
  }

  typedef igmp-version {
    type uint8 {
      range "1..3";
    }
    description
      "IGMP Version.";
    reference "v1 = RFC1112, v2 = RFC2236, v3 = RFC3376";
  }

  typedef igmp-interval-type {
    type uint16 {
      range "1..1024";
    }
    units "seconds";
    description
      "Interval at which the router sends the IGMP query message toward
       the upstream neighbor.";
    reference "RFC3376 8.2 Page 40";
  }
}
