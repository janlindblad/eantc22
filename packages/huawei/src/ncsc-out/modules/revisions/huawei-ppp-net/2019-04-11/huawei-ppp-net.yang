module huawei-ppp-net {
  // Generated by yanger -t ncs
  tailf:mount-id "huawei-nc-1.0:huawei-nc-1.0";
  tailf:ncs-device-type "netconf";

  namespace "urn:huawei:yang:huawei-ppp-net";
  prefix ppp-net;

  import huawei-extension {
    prefix ext;
  }
  import huawei-ifm {
    prefix ifm;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "PPP net.";

  revision 2019-04-11 {
    description
      "Initial revision.";
    reference "Huawei private.";
  }
  ext:task-name "ppp";

  typedef ncs_template_ppp-damp-level-type {
    type string;
    description
      "PPP damp level type is light/middle/heavy/manual.";
  }

  typedef ncs_rpc_notif_ppp-damp-level-type {
    type enumeration {
      enum "light" {
        value 0;
        description
          "Light weight.";
      }
      enum "middle" {
        value 1;
        description
          "Middle weight.";
      }
      enum "heavy" {
        value 2;
        description
          "Heavy weight.";
      }
      enum "manual" {
        value 3;
        description
          "Manually configure the parameters.";
      }
    }
    description
      "PPP damp level type is light/middle/heavy/manual.";
  }

  typedef live_ncs_ppp-damp-level-type {
    type enumeration {
      enum "light" {
        value 0;
        description
          "Light weight.";
      }
      enum "middle" {
        value 1;
        description
          "Middle weight.";
      }
      enum "heavy" {
        value 2;
        description
          "Heavy weight.";
      }
      enum "manual" {
        value 3;
        description
          "Manually configure the parameters.";
      }
    }
    description
      "PPP damp level type is light/middle/heavy/manual.";
  }

  typedef ppp-damp-level-type {
    type enumeration {
      enum "light" {
        value 0;
        description
          "Light weight.";
      }
      enum "middle" {
        value 1;
        description
          "Middle weight.";
      }
      enum "heavy" {
        value 2;
        description
          "Heavy weight.";
      }
      enum "manual" {
        value 3;
        description
          "Manually configure the parameters.";
      }
    }
    description
      "PPP damp level type is light/middle/heavy/manual.";
  }

  augment "/ncs:devices/ncs:device/ncs:config" {
    container ppp-net {
      tailf:ncs-device-type "netconf";
      tailf:display-when "not(../../ncs:module) or ../../ncs:module[ncs:name='huawei-ppp-net']";
      description
        "PPP net.";
      container ppp-dampening {
        presence "PPP protocol status damping enable.";
        description
          "Enable/disable type of PPP damp. If dampen-level is set to manual, the settings of the other parameters need to meet the following requirement: suppress-value/1000 <= (reuse-value/1000) * 2^ (max-suppress-time/half-life-period).";
        ext:generated-by "system" {
          ext:can-be-deleted;
          description
            "The PPP dampening whose level is light is generated by system automatically.";
        }
        leaf dampen-level {
          type ppp-damp-level-type;
          default "light";
          description
            "PPP protocol status damping level.";
        }
        leaf half-life-period {
          when "../dampen-level='manual'" {
            tailf:xpath-root 3;
          }
          type uint8 {
            range "1..60";
          }
          units "s";
          mandatory true;
          description
            "PPP protocol status damping half life time (seconds)";
        }
        leaf suppress-value {
          when "../dampen-level='manual'" {
            tailf:xpath-root 3;
          }
          type uint16 {
            range "1..20000";
          }
          must '../suppress-value >= ../reuse-value' {
            tailf:xpath-root 3;
          }
          mandatory true;
          description
            "1000 times of PPP protocol status damping suppress threshold.";
        }
        leaf reuse-value {
          when "../dampen-level='manual'" {
            tailf:xpath-root 3;
          }
          type uint16 {
            range "1..20000";
          }
          must '../suppress-value >= ../reuse-value' {
            tailf:xpath-root 3;
          }
          mandatory true;
          description
            "1000 times of PPP protocol status damping reuse threshold.";
        }
        leaf max-suppress-time {
          when "../dampen-level='manual'" {
            tailf:xpath-root 3;
          }
          type uint8 {
            range "1..255";
          }
          units "s";
          mandatory true;
          description
            "PPP protocol status damping max suppress time.";
        }
      }
    }
  }
  augment "/ncs:devices/ncs:device/ncs:live-status" {
    container ppp-net {
      tailf:ncs-device-type "netconf";
      tailf:display-when "not(../../ncs:module) or ../../ncs:module[ncs:name='huawei-ppp-net'] or (../../ncs:live-status-protocol[not(ncs:capability)]) or (../../ncs:live-status-protocol/ncs:capability/ncs:module[.='huawei-ppp-net'])";
      description
        "PPP net.";
      container ppp-dampening {
        presence "PPP protocol status damping enable.";
        description
          "Enable/disable type of PPP damp. If dampen-level is set to manual, the settings of the other parameters need to meet the following requirement: suppress-value/1000 <= (reuse-value/1000) * 2^ (max-suppress-time/half-life-period).";
        ext:generated-by "system" {
          ext:can-be-deleted;
          description
            "The PPP dampening whose level is light is generated by system automatically.";
        }
        leaf dampen-level {
          type live_ncs_ppp-damp-level-type;
          // NCS drop default statement
          description
            "PPP protocol status damping level.";
        }
        leaf half-life-period {
          // NCS drop when statement
          type uint8 {
            range "1..60";
          }
          units "s";
          // NCS drop mandatory statement
          description
            "PPP protocol status damping half life time (seconds)";
        }
        leaf suppress-value {
          // NCS drop when statement
          type uint16 {
            range "1..20000";
          }
          // NCS drop must statement
          // NCS drop mandatory statement
          description
            "1000 times of PPP protocol status damping suppress threshold.";
        }
        leaf reuse-value {
          // NCS drop when statement
          type uint16 {
            range "1..20000";
          }
          // NCS drop must statement
          // NCS drop mandatory statement
          description
            "1000 times of PPP protocol status damping reuse threshold.";
        }
        leaf max-suppress-time {
          // NCS drop when statement
          type uint8 {
            range "1..255";
          }
          units "s";
          // NCS drop mandatory statement
          description
            "PPP protocol status damping max suppress time.";
        }
      }
    }
  }
  augment "/ncs:devices/ncs:template/ncs:ned-id/ncs:config" {
    container ppp-net {
      description
        "PPP net.";
      container ppp-dampening {
        presence "PPP protocol status damping enable.";
        description
          "Enable/disable type of PPP damp. If dampen-level is set to manual, the settings of the other parameters need to meet the following requirement: suppress-value/1000 <= (reuse-value/1000) * 2^ (max-suppress-time/half-life-period).";
        ext:generated-by "system" {
          ext:can-be-deleted;
          description
            "The PPP dampening whose level is light is generated by system automatically.";
        }
        leaf dampen-level {
          type ncs_template_ppp-damp-level-type;
          // NCS drop default statement
          description
            "PPP protocol status damping level.";
        }
        leaf half-life-period {
          // NCS drop when statement
          type string;
          units "s";
          // NCS drop mandatory statement
          description
            "PPP protocol status damping half life time (seconds)";
        }
        leaf suppress-value {
          // NCS drop when statement
          type string;
          // NCS drop must statement
          // NCS drop mandatory statement
          description
            "1000 times of PPP protocol status damping suppress threshold.";
        }
        leaf reuse-value {
          // NCS drop when statement
          type string;
          // NCS drop must statement
          // NCS drop mandatory statement
          description
            "1000 times of PPP protocol status damping reuse threshold.";
        }
        leaf max-suppress-time {
          // NCS drop when statement
          type string;
          units "s";
          // NCS drop mandatory statement
          description
            "PPP protocol status damping max suppress time.";
        }
      }
    }
  }
  augment "/ncs:devices/ncs:template/ncs:ned-id/ncs:config/ifm:ifm/ifm:interfaces/ifm:interface" {
    description
      "PPP configuration of interface.";
    container ppp-net {
      description
        "Configure PPP configuration of interface.";
      container ppp {
        // NCS drop when statement
        description
          "Configure PPP of interface.";
        container interface-link {
          description
            "Configure PPP polling interval.";
          leaf time-interval {
            type string;
            units "s";
            // NCS drop must statement
            // NCS drop default statement
            description
              "Polling interval.";
          }
        }
      }
    }
  }
  augment "/ncs:devices/ncs:device/ncs:live-status/ifm:ifm/ifm:interfaces/ifm:interface" {
    description
      "PPP configuration of interface.";
    container ppp-net {
      tailf:ncs-device-type "netconf";
      tailf:display-when "not(../../../../../ncs:module) or ../../../../../ncs:module[ncs:name='huawei-ppp-net'] or (../../../../../ncs:live-status-protocol[not(ncs:capability)]) or (../../../../../ncs:live-status-protocol/ncs:capability/ncs:module[.='huawei-ppp-net'])";
      description
        "Configure PPP configuration of interface.";
      container ppp {
        // NCS drop when statement
        description
          "Configure PPP of interface.";
        container interface-link {
          description
            "Configure PPP polling interval.";
          leaf time-interval {
            type uint32 {
              range "0..32767";
            }
            units "s";
            // NCS drop must statement
            // NCS drop default statement
            description
              "Polling interval.";
          }
        }
      }
    }
  }
  augment "/ncs:devices/ncs:device/ncs:config/ifm:ifm/ifm:interfaces/ifm:interface" {
    description
      "PPP configuration of interface.";
    container ppp-net {
      tailf:ncs-device-type "netconf";
      tailf:display-when "not(../../../../../ncs:module) or ../../../../../ncs:module[ncs:name='huawei-ppp-net']";
      description
        "Configure PPP configuration of interface.";
      container ppp {
        when "../../ifm:link-protocol='ppp'" {
          tailf:xpath-root 3;
        }
        description
          "Configure PPP of interface.";
        container interface-link {
          description
            "Configure PPP polling interval.";
          leaf time-interval {
            type uint32 {
              range "0..32767";
            }
            units "s";
            must "../../../../ifm:type != 'Pos-Trunk' and ../../../../ifm:type != 'Mp-group' and ../../../../ifm:type != 'Global-Mp-Group'" {
              tailf:xpath-root 3;
            }
            default "10";
            description
              "Polling interval.";
          }
        }
      }
    }
  }
}
