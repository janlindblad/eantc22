module huawei-bras-cu-agent-deviations-NE8000 {
  // Generated by yanger -t ncs
  tailf:mount-id "huawei-nc-1.0:huawei-nc-1.0";
  tailf:ncs-device-type "netconf";

  namespace "urn:huawei:yang:huawei-bras-cu-agent-deviations-NE8000";
  prefix bras-cu-agent-devs-NE8000;

  import huawei-bras-cu-agent {
    prefix bras-cu-agent;
  }
  import huawei-ifm {
    prefix ifm;
  }
  import huawei-rbs {
    prefix rbs;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "This module defines deviation statements for huawei-bras-cu-agent module.";

  revision 2019-11-06 {
    description
      "Initial revision.";
    reference "Huawei private.";
  }

  deviation "/ncs:devices/ncs:template/ncs:ned-id/ncs:config/ifm:ifm/ifm:interfaces/ifm:interface/bras-cu-agent:cu-agent/bras-cu-agent:cu-multicast-rbp/bras-cu-agent:name" {
    deviate replace {
      type string;
    }
  }
  deviation "/ncs:devices/ncs:device/ncs:live-status/ifm:ifm/ifm:interfaces/ifm:interface/bras-cu-agent:cu-agent/bras-cu-agent:cu-multicast-rbp/bras-cu-agent:name" {
    deviate replace {
      type leafref {
        path "/ncs:devices/ncs:device/ncs:live-status/rbs:rbs/rbs:profiles/rbs:profile/rbs:name" {
          tailf:xpath-root 3;
        }
      }
    }
  }
  deviation "/ncs:devices/ncs:device/ncs:config/ifm:ifm/ifm:interfaces/ifm:interface/bras-cu-agent:cu-agent/bras-cu-agent:cu-multicast-rbp/bras-cu-agent:name" {
    deviate replace {
      type leafref {
        path "/ncs:devices/ncs:device/ncs:config/rbs:rbs/rbs:profiles/rbs:profile/rbs:name" {
          tailf:xpath-root 3;
        }
      }
    }
  }
}
