module huawei-if-ip {
  // Generated by yanger -t ncs
  tailf:mount-id "huawei-nc-1.0:huawei-nc-1.0";
  tailf:ncs-device-type "netconf";

  namespace "urn:huawei:yang:huawei-if-ip";
  prefix if-ip;

  import ietf-inet-types {
    prefix inet;
  }
  import huawei-ifm {
    prefix ifm;
  }
  import huawei-network-instance {
    prefix ni;
  }
  import huawei-extension {
    prefix ext;
  }
  import huawei-l3vpn {
    prefix l3vpn;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "This module contains a collection of YANG definitions for
     configuring IP implementations.
     Copyright (C) 2019 Huawei Technologies Co., Ltd. All rights reserved.";

  revision 2020-06-30 {
    description
      "Add units attribute.";
    reference "Huawei private.";
  }
  revision 2020-02-07 {
    description
      "The modifications in the code are synchronized to the YANG file.";
    reference "Huawei private.";
  }
  revision 2019-04-10 {
    description
      "Initial revision.";
    reference "Huawei private.";
  }
  ext:task-name "interface-mgr";

  typedef ncs_template_ipv4-address-config-type {
    type string;
    description
      "IPv4 address type.";
  }

  typedef ncs_template_ipv4-address-state-type {
    type string;
    description
      "IPv4 address type.";
  }

  typedef ncs_template_ipv4-netmask {
    type string;
    description
      "IPv4 mask support mask format.";
  }

  typedef ncs_template_negotiation-type {
    type string;
    description
      "Negotiation address type.";
  }

  typedef ncs_template_ipv6-address-config-type {
    type string;
    description
      "IPv6 address type.";
  }

  typedef ncs_template_ipv6-address-state-type {
    type string;
    description
      "IPv6 address type.";
  }

  typedef ncs_template_ipv6-address-algorithm-type {
    type string;
    description
      "IPv6 address algorithm type.";
  }

  typedef ncs_template_ipv6-status-type {
    type string;
    description
      "Status of an address.";
  }

  typedef ncs_rpc_notif_ipv4-address-config-type {
    type enumeration {
      enum "main" {
        value 1;
        description
          "Primary address of an interface.";
      }
      enum "sub" {
        value 32;
        description
          "Secondary address of an interface.";
      }
    }
    description
      "IPv4 address type.";
  }

  typedef ncs_rpc_notif_ipv4-address-state-type {
    type enumeration {
      enum "main" {
        value 1;
        description
          "Primary address of an interface.";
      }
      enum "sub" {
        value 32;
        description
          "Secondary address of an interface.";
      }
      enum "neg" {
        value 4;
        description
          "Negotiated address of an interface.";
      }
      enum "unnumber" {
        value 2;
        description
          "Unnumbered address of an interface.";
      }
    }
    description
      "IPv4 address type.";
  }

  typedef ncs_rpc_notif_ipv4-netmask {
    type string {
      length "9..15";
      pattern '((([1-9]?[0-9]|1[0-9][0-9]|2[0-4][0-9]|25[0-5])\.){3}([1-9]?[0-9]|1[0-9][0-9]|2[0-4][0-9]|25[0-5]))';
    }
    description
      "IPv4 mask support mask format.";
  }

  typedef ncs_rpc_notif_negotiation-type {
    type enumeration {
      enum "ppp-negotiate" {
        value 0;
        description
          "PPP negotiation type.";
      }
    }
    description
      "Negotiation address type.";
  }

  typedef ncs_rpc_notif_ipv6-address-config-type {
    type enumeration {
      enum "global" {
        value 1;
        description
          "Global unicast address.";
      }
      enum "link-local" {
        value 2;
        description
          "Link local address.";
      }
      enum "anycast" {
        value 6;
        description
          "Anycast address.";
      }
    }
    description
      "IPv6 address type.";
  }

  typedef ncs_rpc_notif_ipv6-address-state-type {
    type enumeration {
      enum "global" {
        value 1;
        description
          "Global unicast address.";
      }
      enum "link-local" {
        value 2;
        description
          "Link local address.";
      }
      enum "auto-link-local" {
        value 3;
        description
          "Auto link local address.";
      }
      enum "anycast" {
        value 6;
        description
          "Anycast address.";
      }
    }
    description
      "IPv6 address type.";
  }

  typedef ncs_rpc_notif_ipv6-address-algorithm-type {
    type enumeration {
      enum "none" {
        value 0;
        description
          "None.";
      }
      enum "cga" {
        value 1;
        description
          "CGA.";
      }
      enum "eui64" {
        value 2;
        description
          "EUI 64.";
      }
    }
    description
      "IPv6 address algorithm type.";
  }

  typedef ncs_rpc_notif_ipv6-status-type {
    type enumeration {
      enum "preferred" {
        value 1;
        description
          "This is a valid address that can appear as the destination or source address of a packet.";
      }
      enum "inaccessible" {
        value 4;
        description
          "The address is not accessible because the interface to which this address is assigned is not operational.";
      }
      enum "unknown" {
        value 5;
        description
          "The status cannot be determined for some reason.";
      }
      enum "tentative" {
        value 6;
        description
          "The uniqueness of the address on the link is being verified. Addresses in this state should not be used for general communication and should only be used to determine the uniqueness of the address.";
      }
      enum "duplicate" {
        value 7;
        description
          "The address has been determined to be non-unique on the link and so must not be used.";
      }
    }
    description
      "Status of an address.";
  }

  typedef live_ncs_ipv4-address-config-type {
    type enumeration {
      enum "main" {
        value 1;
        description
          "Primary address of an interface.";
      }
      enum "sub" {
        value 32;
        description
          "Secondary address of an interface.";
      }
    }
    description
      "IPv4 address type.";
  }

  typedef live_ncs_ipv4-address-state-type {
    type enumeration {
      enum "main" {
        value 1;
        description
          "Primary address of an interface.";
      }
      enum "sub" {
        value 32;
        description
          "Secondary address of an interface.";
      }
      enum "neg" {
        value 4;
        description
          "Negotiated address of an interface.";
      }
      enum "unnumber" {
        value 2;
        description
          "Unnumbered address of an interface.";
      }
    }
    description
      "IPv4 address type.";
  }

  typedef live_ncs_ipv4-netmask {
    type string {
      length "9..15";
      pattern '((([1-9]?[0-9]|1[0-9][0-9]|2[0-4][0-9]|25[0-5])\.){3}([1-9]?[0-9]|1[0-9][0-9]|2[0-4][0-9]|25[0-5]))';
    }
    description
      "IPv4 mask support mask format.";
  }

  typedef live_ncs_negotiation-type {
    type enumeration {
      enum "ppp-negotiate" {
        value 0;
        description
          "PPP negotiation type.";
      }
    }
    description
      "Negotiation address type.";
  }

  typedef live_ncs_ipv6-address-config-type {
    type enumeration {
      enum "global" {
        value 1;
        description
          "Global unicast address.";
      }
      enum "link-local" {
        value 2;
        description
          "Link local address.";
      }
      enum "anycast" {
        value 6;
        description
          "Anycast address.";
      }
    }
    description
      "IPv6 address type.";
  }

  typedef live_ncs_ipv6-address-state-type {
    type enumeration {
      enum "global" {
        value 1;
        description
          "Global unicast address.";
      }
      enum "link-local" {
        value 2;
        description
          "Link local address.";
      }
      enum "auto-link-local" {
        value 3;
        description
          "Auto link local address.";
      }
      enum "anycast" {
        value 6;
        description
          "Anycast address.";
      }
    }
    description
      "IPv6 address type.";
  }

  typedef live_ncs_ipv6-address-algorithm-type {
    type enumeration {
      enum "none" {
        value 0;
        description
          "None.";
      }
      enum "cga" {
        value 1;
        description
          "CGA.";
      }
      enum "eui64" {
        value 2;
        description
          "EUI 64.";
      }
    }
    description
      "IPv6 address algorithm type.";
  }

  typedef live_ncs_ipv6-status-type {
    type enumeration {
      enum "preferred" {
        value 1;
        description
          "This is a valid address that can appear as the destination or source address of a packet.";
      }
      enum "inaccessible" {
        value 4;
        description
          "The address is not accessible because the interface to which this address is assigned is not operational.";
      }
      enum "unknown" {
        value 5;
        description
          "The status cannot be determined for some reason.";
      }
      enum "tentative" {
        value 6;
        description
          "The uniqueness of the address on the link is being verified. Addresses in this state should not be used for general communication and should only be used to determine the uniqueness of the address.";
      }
      enum "duplicate" {
        value 7;
        description
          "The address has been determined to be non-unique on the link and so must not be used.";
      }
    }
    description
      "Status of an address.";
  }

  typedef ipv4-address-config-type {
    type enumeration {
      enum "main" {
        value 1;
        description
          "Primary address of an interface.";
      }
      enum "sub" {
        value 32;
        description
          "Secondary address of an interface.";
      }
    }
    description
      "IPv4 address type.";
  }

  typedef ipv4-address-state-type {
    type enumeration {
      enum "main" {
        value 1;
        description
          "Primary address of an interface.";
      }
      enum "sub" {
        value 32;
        description
          "Secondary address of an interface.";
      }
      enum "neg" {
        value 4;
        description
          "Negotiated address of an interface.";
      }
      enum "unnumber" {
        value 2;
        description
          "Unnumbered address of an interface.";
      }
    }
    description
      "IPv4 address type.";
  }

  typedef ipv4-netmask {
    type string {
      length "9..15";
      pattern '((([1-9]?[0-9]|1[0-9][0-9]|2[0-4][0-9]|25[0-5])\.){3}([1-9]?[0-9]|1[0-9][0-9]|2[0-4][0-9]|25[0-5]))';
    }
    description
      "IPv4 mask support mask format.";
  }

  typedef negotiation-type {
    type enumeration {
      enum "ppp-negotiate" {
        value 0;
        description
          "PPP negotiation type.";
      }
    }
    description
      "Negotiation address type.";
  }

  typedef ipv6-address-config-type {
    type enumeration {
      enum "global" {
        value 1;
        description
          "Global unicast address.";
      }
      enum "link-local" {
        value 2;
        description
          "Link local address.";
      }
      enum "anycast" {
        value 6;
        description
          "Anycast address.";
      }
    }
    description
      "IPv6 address type.";
  }

  typedef ipv6-address-state-type {
    type enumeration {
      enum "global" {
        value 1;
        description
          "Global unicast address.";
      }
      enum "link-local" {
        value 2;
        description
          "Link local address.";
      }
      enum "auto-link-local" {
        value 3;
        description
          "Auto link local address.";
      }
      enum "anycast" {
        value 6;
        description
          "Anycast address.";
      }
    }
    description
      "IPv6 address type.";
  }

  typedef ipv6-address-algorithm-type {
    type enumeration {
      enum "none" {
        value 0;
        description
          "None.";
      }
      enum "cga" {
        value 1;
        description
          "CGA.";
      }
      enum "eui64" {
        value 2;
        description
          "EUI 64.";
      }
    }
    description
      "IPv6 address algorithm type.";
  }

  typedef ipv6-status-type {
    type enumeration {
      enum "preferred" {
        value 1;
        description
          "This is a valid address that can appear as the destination or source address of a packet.";
      }
      enum "inaccessible" {
        value 4;
        description
          "The address is not accessible because the interface to which this address is assigned is not operational.";
      }
      enum "unknown" {
        value 5;
        description
          "The status cannot be determined for some reason.";
      }
      enum "tentative" {
        value 6;
        description
          "The uniqueness of the address on the link is being verified. Addresses in this state should not be used for general communication and should only be used to determine the uniqueness of the address.";
      }
      enum "duplicate" {
        value 7;
        description
          "The address has been determined to be non-unique on the link and so must not be used.";
      }
    }
    description
      "Status of an address.";
  }

  augment "/ncs:devices/ncs:template/ncs:ned-id/ncs:config/ni:network-instance/ni:instances/ni:instance" {
    description
      "Policies for selecting source and destination IPv6 addresses and parameters for configuring IP on interfaces.";
    container ipv4-ifs {
      description
        "List of IPv4 configurations.";
      list ipv4-if {
        // NCS patched for predictable order
        ordered-by user;
        key "name";
        description
          "Configure IPv4. Capabilities supported by this node vary according to interface types.";
        leaf name {
          type string;
          // NCS drop must statement
          description
            "Interface name. The formats of interface names are defined based on interface types and device types, for example, the Loopback interface: Loopback0, and the Ethernet interface: Ethernet 0/3/0/7.";
        }
        choice address {
          // NCS drop mandatory statement
          description
            "The IPv4 address can be specified as negotiated or unnumbered or ordinarily address.";
          case config-address {
            description
              "Config IPv4 address.";
            container addresses {
              // NCS drop must statement
              description
                "List of IPv4 addresses. The IPv4 address of the DCN interface cannot be created, modified, or deleted.";
              list address {
                // NCS patched for predictable order
                ordered-by user;
                key "ip";
                description
                  "Configure an IPv4 address to the interface.";
                leaf ip {
                  type string;
                  // NCS drop must statement
                  description
                    "IPv4 address.";
                }
                leaf netmask {
                  type ncs_template_ipv4-netmask;
                  // NCS drop mandatory statement
                  description
                    "IPv4 address mask.";
                }
                leaf type {
                  type ncs_template_ipv4-address-config-type;
                  // NCS drop mandatory statement
                  description
                    "IPv4 address type.";
                }
              }
            }
          }
          case unnumbered-address {
            description
              "Unnumbered address.";
            container unnumbered-if {
              description
                "Configure unnumbered interface. The address borrowing relationship of the DCN interface cannot be created, modified, or deleted.";
              leaf name {
                type string;
                // NCS drop must statement
                description
                  "Name of an unnumbered interface.";
              }
            }
          }
        }
      }
    }
    // NCS drop config false container 'ipv4-if-states'
    container ipv6-ifs {
      description
        "List of IPv6 configurations.";
      list ipv6-if {
        // NCS patched for predictable order
        ordered-by user;
        key "name";
        description
          "Configure IPv6. Capabilities supported by this node vary according to interface types.";
        leaf name {
          type string;
          // NCS drop must statement
          description
            "Interface name. The formats of interface names are defined based on interface types and device types, for example, the Loopback interface: Loopback0, and the Ethernet interface: Ethernet 0/3/0/7.";
        }
        leaf mtu6 {
          type string;
          units "Byte";
          ext:dynamic-default;
          description
            "IPv6 maximum transmission unit of an interface.
             Special explanation:
             Range: The server may restrict the allowed values for this leaf, depending on the interface's type.";
        }
        leaf spread-mtu-flag {
          type string;
          // NCS drop default statement
          description
            "Enable/disable the function of spreading the IPv6 MTU of main interface to subinterface.";
        }
        leaf auto-link-local {
          type string;
          // NCS drop must statement
          // NCS drop default statement
          description
            "Enable/disable an interface with the auto linklocal address function.";
        }
        container addresses {
          description
            "List of IPv6 addresses.";
          list address {
            // NCS patched for predictable order
            ordered-by user;
            key "ip";
            description
              "Configure an IPv6 address to the interface.";
            leaf ip {
              type string;
              // NCS drop must statement
              description
                "IPv6 address.";
            }
            leaf prefix-length {
              type string;
              // NCS drop mandatory statement
              description
                "Length of the IPv6 address prefix.";
            }
            leaf type {
              type ncs_template_ipv6-address-config-type;
              // NCS drop mandatory statement
              description
                "IPv6 address type.";
            }
            leaf algorithm-type {
              type ncs_template_ipv6-address-algorithm-type;
              // NCS drop must statement
              // NCS drop default statement
              description
                "Address algorithm type.";
            }
          }
        }
      }
    }
    // NCS drop config false container 'ipv6-if-states'
  }
  augment "/ncs:devices/ncs:device/ncs:live-status/ni:network-instance/ni:instances/ni:instance" {
    description
      "Policies for selecting source and destination IPv6 addresses and parameters for configuring IP on interfaces.";
    container ipv4-ifs {
      tailf:ncs-device-type "netconf";
      tailf:display-when "not(../../../../../ncs:module) or ../../../../../ncs:module[ncs:name='huawei-if-ip'] or (../../../../../ncs:live-status-protocol[not(ncs:capability)]) or (../../../../../ncs:live-status-protocol/ncs:capability/ncs:module[.='huawei-if-ip'])";
      description
        "List of IPv4 configurations.";
      list ipv4-if {
        key "name";
        description
          "Configure IPv4. Capabilities supported by this node vary according to interface types.";
        leaf name {
          type leafref {
            path "/ncs:devices/ncs:device/ncs:live-status/ifm:ifm/ifm:interfaces/ifm:interface/ifm:name" {
              tailf:xpath-root 3;
            }
          }
          // NCS drop must statement
          description
            "Interface name. The formats of interface names are defined based on interface types and device types, for example, the Loopback interface: Loopback0, and the Ethernet interface: Ethernet 0/3/0/7.";
        }
        choice address {
          // NCS drop mandatory statement
          description
            "The IPv4 address can be specified as negotiated or unnumbered or ordinarily address.";
          case config-address {
            description
              "Config IPv4 address.";
            container addresses {
              // NCS drop must statement
              description
                "List of IPv4 addresses. The IPv4 address of the DCN interface cannot be created, modified, or deleted.";
              list address {
                key "ip";
                description
                  "Configure an IPv4 address to the interface.";
                leaf ip {
                  type inet:ipv4-address-no-zone;
                  // NCS drop must statement
                  description
                    "IPv4 address.";
                }
                leaf netmask {
                  type live_ncs_ipv4-netmask;
                  // NCS drop mandatory statement
                  description
                    "IPv4 address mask.";
                }
                leaf type {
                  type live_ncs_ipv4-address-config-type;
                  // NCS drop mandatory statement
                  description
                    "IPv4 address type.";
                }
              }
            }
          }
          case unnumbered-address {
            description
              "Unnumbered address.";
            container unnumbered-if {
              description
                "Configure unnumbered interface. The address borrowing relationship of the DCN interface cannot be created, modified, or deleted.";
              leaf name {
                type leafref {
                  path "/ncs:devices/ncs:device/ncs:live-status/ifm:ifm/ifm:interfaces/ifm:interface/ifm:name" {
                    tailf:xpath-root 3;
                  }
                }
                // NCS drop must statement
                description
                  "Name of an unnumbered interface.";
              }
            }
          }
        }
      }
    }
    container ipv4-if-states {
      tailf:ncs-device-type "netconf";
      tailf:display-when "not(../../../../../ncs:module) or ../../../../../ncs:module[ncs:name='huawei-if-ip'] or (../../../../../ncs:live-status-protocol[not(ncs:capability)]) or (../../../../../ncs:live-status-protocol/ncs:capability/ncs:module[.='huawei-if-ip'])";
      description
        "List of IPv4 address state.";
      list ipv4-if-state {
        key "name";
        description
          "Operational state of IPv4 addresses.";
        leaf name {
          type leafref {
            path "/ncs:devices/ncs:device/ncs:live-status/ifm:ifm/ifm:interfaces/ifm:interface/ifm:name" {
              tailf:xpath-root 3;
            }
          }
          description
            "Interface name. The formats of interface names are defined based on interface types and device types, for example, the Loopback interface: Loopback0, and the Ethernet interface: Ethernet 0/3/0/7.";
        }
        container addresses {
          description
            "List of IPv4 addresses.";
          list address {
            key "ip";
            description
              "Operational state of IPv4 addresses.";
            leaf ip {
              type inet:ipv4-address-no-zone;
              description
                "IPv4 address.";
            }
            leaf netmask {
              type live_ncs_ipv4-netmask;
              description
                "IPv4 address mask.";
            }
            leaf type {
              type live_ncs_ipv4-address-state-type;
              description
                "IPv4 address type.";
            }
          }
        }
      }
    }
    container ipv6-ifs {
      tailf:ncs-device-type "netconf";
      tailf:display-when "not(../../../../../ncs:module) or ../../../../../ncs:module[ncs:name='huawei-if-ip'] or (../../../../../ncs:live-status-protocol[not(ncs:capability)]) or (../../../../../ncs:live-status-protocol/ncs:capability/ncs:module[.='huawei-if-ip'])";
      description
        "List of IPv6 configurations.";
      list ipv6-if {
        key "name";
        description
          "Configure IPv6. Capabilities supported by this node vary according to interface types.";
        leaf name {
          type leafref {
            path "/ncs:devices/ncs:device/ncs:live-status/ifm:ifm/ifm:interfaces/ifm:interface/ifm:name" {
              tailf:xpath-root 3;
            }
          }
          // NCS drop must statement
          description
            "Interface name. The formats of interface names are defined based on interface types and device types, for example, the Loopback interface: Loopback0, and the Ethernet interface: Ethernet 0/3/0/7.";
        }
        leaf mtu6 {
          type uint32 {
            range "0..50000";
          }
          units "Byte";
          ext:dynamic-default;
          description
            "IPv6 maximum transmission unit of an interface.
             Special explanation:
             Range: The server may restrict the allowed values for this leaf, depending on the interface's type.";
        }
        leaf spread-mtu-flag {
          type boolean;
          // NCS drop default statement
          description
            "Enable/disable the function of spreading the IPv6 MTU of main interface to subinterface.";
        }
        leaf auto-link-local {
          type boolean;
          // NCS drop must statement
          // NCS drop default statement
          description
            "Enable/disable an interface with the auto linklocal address function.";
        }
        container addresses {
          description
            "List of IPv6 addresses.";
          list address {
            key "ip";
            description
              "Configure an IPv6 address to the interface.";
            leaf ip {
              type inet:ipv6-address-no-zone;
              // NCS drop must statement
              description
                "IPv6 address.";
            }
            leaf prefix-length {
              type uint32 {
                range "1..128";
              }
              // NCS drop mandatory statement
              description
                "Length of the IPv6 address prefix.";
            }
            leaf type {
              type live_ncs_ipv6-address-config-type;
              // NCS drop mandatory statement
              description
                "IPv6 address type.";
            }
            leaf algorithm-type {
              type live_ncs_ipv6-address-algorithm-type;
              // NCS drop must statement
              // NCS drop default statement
              description
                "Address algorithm type.";
            }
          }
        }
      }
    }
    container ipv6-if-states {
      tailf:ncs-device-type "netconf";
      tailf:display-when "not(../../../../../ncs:module) or ../../../../../ncs:module[ncs:name='huawei-if-ip'] or (../../../../../ncs:live-status-protocol[not(ncs:capability)]) or (../../../../../ncs:live-status-protocol/ncs:capability/ncs:module[.='huawei-if-ip'])";
      description
        "List of IPv6 address state.";
      list ipv6-if-state {
        key "name";
        description
          "Operational state of IPv6 addresses.";
        leaf name {
          type leafref {
            path "/ncs:devices/ncs:device/ncs:live-status/ifm:ifm/ifm:interfaces/ifm:interface/ifm:name" {
              tailf:xpath-root 3;
            }
          }
          description
            "Interface name. The formats of interface names are defined based on interface types and device types, for example, the Loopback interface: Loopback0, and the Ethernet interface: Ethernet 0/3/0/7.";
        }
        container addresses {
          description
            "List of IPv6 addresses.";
          list address {
            key "ip";
            description
              "Operational state of IPv6 addresses.";
            leaf ip {
              type inet:ipv6-address-no-zone;
              description
                "IPv6 address.";
            }
            leaf prefix-length {
              type uint32 {
                range "1..128";
              }
              description
                "Length of the IPv6 address prefix.";
            }
            leaf type {
              type live_ncs_ipv6-address-state-type;
              description
                "IPv6 address type.";
            }
            leaf algorithm-type {
              type live_ncs_ipv6-address-algorithm-type;
              description
                "Address algorithm type.";
            }
            leaf collision-count {
              type uint32 {
                range "0..3";
              }
              description
                "Number of IPv6 address collisions.";
            }
            leaf is-block {
              type boolean;
              description
                "IPv6 address is blocked or not.";
            }
            leaf status {
              type live_ncs_ipv6-status-type;
              description
                "IPv6 address status.";
            }
          }
        }
      }
    }
  }
  augment "/ncs:devices/ncs:device/ncs:config/ni:network-instance/ni:instances/ni:instance" {
    description
      "Policies for selecting source and destination IPv6 addresses and parameters for configuring IP on interfaces.";
    container ipv4-ifs {
      tailf:ncs-device-type "netconf";
      tailf:display-when "not(../../../../../ncs:module) or ../../../../../ncs:module[ncs:name='huawei-if-ip']";
      description
        "List of IPv4 configurations.";
      list ipv4-if {
        key "name";
        description
          "Configure IPv4. Capabilities supported by this node vary according to interface types.";
        leaf name {
          type leafref {
            path "/ncs:devices/ncs:device/ncs:config/ifm:ifm/ifm:interfaces/ifm:interface/ifm:name" {
              tailf:xpath-root 3;
            }
          }
          must '../../../ni:name=/ifm:ifm/ifm:interfaces/ifm:interface[ifm:name=current()]/ifm:vrf-name' {
            tailf:xpath-root 3;
          }
          description
            "Interface name. The formats of interface names are defined based on interface types and device types, for example, the Loopback interface: Loopback0, and the Ethernet interface: Ethernet 0/3/0/7.";
        }
        choice address {
          mandatory true;
          description
            "The IPv4 address can be specified as negotiated or unnumbered or ordinarily address.";
          case config-address {
            description
              "Config IPv4 address.";
            container addresses {
              must "count(address)=0 or count(address[type='main'])=1" {
                tailf:xpath-root 3;
              }
              description
                "List of IPv4 addresses. The IPv4 address of the DCN interface cannot be created, modified, or deleted.";
              list address {
                key "ip";
                description
                  "Configure an IPv4 address to the interface.";
                leaf ip {
                  type inet:ipv4-address-no-zone;
                  must "../../../../../l3vpn:afs/l3vpn:af[l3vpn:type='ipv4-unicast']" {
                    tailf:xpath-root 3;
                  }
                  description
                    "IPv4 address.";
                }
                leaf netmask {
                  type ipv4-netmask;
                  mandatory true;
                  description
                    "IPv4 address mask.";
                }
                leaf type {
                  type ipv4-address-config-type;
                  mandatory true;
                  description
                    "IPv4 address type.";
                }
              }
            }
          }
          case unnumbered-address {
            description
              "Unnumbered address.";
            container unnumbered-if {
              description
                "Configure unnumbered interface. The address borrowing relationship of the DCN interface cannot be created, modified, or deleted.";
              leaf name {
                type leafref {
                  path "/ncs:devices/ncs:device/ncs:config/ifm:ifm/ifm:interfaces/ifm:interface/ifm:name" {
                    tailf:xpath-root 3;
                  }
                }
                must "../../if-ip:name!=../name and ../../../../l3vpn:afs/l3vpn:af[l3vpn:type='ipv4-unicast'] and /ifm:ifm/ifm:interfaces/ifm:interface[ifm:name=current()]/ifm:vrf-name=/ifm:ifm/ifm:interfaces/ifm:interface[ifm:name=current()/../../if-ip:name]/ifm:vrf-name" {
                  tailf:xpath-root 3;
                }
                description
                  "Name of an unnumbered interface.";
              }
            }
          }
        }
      }
    }
    // NCS drop config false container 'ipv4-if-states'
    container ipv6-ifs {
      tailf:ncs-device-type "netconf";
      tailf:display-when "not(../../../../../ncs:module) or ../../../../../ncs:module[ncs:name='huawei-if-ip']";
      description
        "List of IPv6 configurations.";
      list ipv6-if {
        key "name";
        description
          "Configure IPv6. Capabilities supported by this node vary according to interface types.";
        leaf name {
          type leafref {
            path "/ncs:devices/ncs:device/ncs:config/ifm:ifm/ifm:interfaces/ifm:interface/ifm:name" {
              tailf:xpath-root 3;
            }
          }
          must '../../../ni:name=/ifm:ifm/ifm:interfaces/ifm:interface[ifm:name=current()]/ifm:vrf-name' {
            tailf:xpath-root 3;
          }
          description
            "Interface name. The formats of interface names are defined based on interface types and device types, for example, the Loopback interface: Loopback0, and the Ethernet interface: Ethernet 0/3/0/7.";
        }
        leaf mtu6 {
          type uint32 {
            range "0..50000";
          }
          units "Byte";
          ext:dynamic-default;
          description
            "IPv6 maximum transmission unit of an interface.
             Special explanation:
             Range: The server may restrict the allowed values for this leaf, depending on the interface's type.";
        }
        leaf spread-mtu-flag {
          type boolean;
          default "false";
          description
            "Enable/disable the function of spreading the IPv6 MTU of main interface to subinterface.";
        }
        leaf auto-link-local {
          type boolean;
          must "../auto-link-local = 'false' or (../auto-link-local = 'true' and ../../../l3vpn:afs/l3vpn:af[l3vpn:type='ipv6-unicast'])" {
            tailf:xpath-root 3;
          }
          default "false";
          description
            "Enable/disable an interface with the auto linklocal address function.";
        }
        container addresses {
          description
            "List of IPv6 addresses.";
          list address {
            key "ip";
            description
              "Configure an IPv6 address to the interface.";
            leaf ip {
              type inet:ipv6-address-no-zone;
              must "../../../../../l3vpn:afs/l3vpn:af[l3vpn:type='ipv6-unicast']" {
                tailf:xpath-root 3;
              }
              description
                "IPv6 address.";
            }
            leaf prefix-length {
              type uint32 {
                range "1..128";
              }
              mandatory true;
              description
                "Length of the IPv6 address prefix.";
            }
            leaf type {
              type ipv6-address-config-type;
              mandatory true;
              description
                "IPv6 address type.";
            }
            leaf algorithm-type {
              type ipv6-address-algorithm-type;
              must "(../type='global' and (../algorithm-type='none' or ../algorithm-type='cga' or ../algorithm-type='eui64') ) or (../type='link-local' and (../algorithm-type='none' or ../algorithm-type='cga') ) or (../type='anycast' and ../algorithm-type='none')" {
                tailf:xpath-root 3;
              }
              default "none";
              description
                "Address algorithm type.";
            }
          }
        }
      }
    }
    // NCS drop config false container 'ipv6-if-states'
  }
}
