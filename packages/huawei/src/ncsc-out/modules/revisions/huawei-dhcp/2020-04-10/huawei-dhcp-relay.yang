submodule huawei-dhcp-relay {
  // Generated by yanger -t ncs
  tailf:mount-id "huawei-nc-1.0:huawei-nc-1.0";

  yang-version 1;
  belongs-to huawei-dhcp {
    prefix dhcp;
  }

  import huawei-ifm {
    prefix ifm;
  }
  import ietf-inet-types {
    prefix inet;
  }
  import huawei-network-instance {
    prefix ni;
  }
  import huawei-l3vpn {
    prefix l3vpn;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "This module contains a collection of YANG definitions for managing DHCP relay.";

  revision 2020-03-15 {
    description
      "Modify description.";
    reference "Huawei private.";
  }
  revision 2020-02-25 {
    description
      "Add the node of link-selection-address.";
    reference "Huawei private.";
  }
  revision 2019-12-25 {
    description
      "Initial revision.";
    reference "Huawei private.";
  }

  typedef ncs_template_dhcp-relay-reply-type {
    type string;
    description
      "The type of relay reply.";
  }

  typedef ncs_template_dhcp-opt82-sub6-format {
    type string;
    description
      "The type of DHCP option82 suboption6 format.";
  }

  typedef ncs_template_dhcp-opt82-vendor-sub-option-format {
    type string;
    description
      "The type of DHCP option82 vendor suboption format.";
  }

  typedef ncs_rpc_notif_dhcp-relay-reply-type {
    type enumeration {
      enum "broadcast-always" {
        value 1;
        description
          "Always broadcast the reply.";
      }
    }
    description
      "The type of relay reply.";
  }

  typedef ncs_rpc_notif_dhcp-opt82-sub6-format {
    type enumeration {
      enum "self-define" {
        value 1;
        description
          "DHCP option82 self-define format.";
      }
    }
    description
      "The type of DHCP option82 suboption6 format.";
  }

  typedef ncs_rpc_notif_dhcp-opt82-vendor-sub-option-format {
    type enumeration {
      enum "source-ip-address" {
        value 0;
        description
          "Source IP address.";
      }
    }
    description
      "The type of DHCP option82 vendor suboption format.";
  }

  typedef live_ncs_dhcp-relay-reply-type {
    type enumeration {
      enum "broadcast-always" {
        value 1;
        description
          "Always broadcast the reply.";
      }
    }
    description
      "The type of relay reply.";
  }

  typedef live_ncs_dhcp-opt82-sub6-format {
    type enumeration {
      enum "self-define" {
        value 1;
        description
          "DHCP option82 self-define format.";
      }
    }
    description
      "The type of DHCP option82 suboption6 format.";
  }

  typedef live_ncs_dhcp-opt82-vendor-sub-option-format {
    type enumeration {
      enum "source-ip-address" {
        value 0;
        description
          "Source IP address.";
      }
    }
    description
      "The type of DHCP option82 vendor suboption format.";
  }

  typedef dhcp-relay-reply-type {
    type enumeration {
      enum "broadcast-always" {
        value 1;
        description
          "Always broadcast the reply.";
      }
    }
    description
      "The type of relay reply.";
  }

  typedef dhcp-opt82-sub6-format {
    type enumeration {
      enum "self-define" {
        value 1;
        description
          "DHCP option82 self-define format.";
      }
    }
    description
      "The type of DHCP option82 suboption6 format.";
  }

  typedef dhcp-opt82-vendor-sub-option-format {
    type enumeration {
      enum "source-ip-address" {
        value 0;
        description
          "Source IP address.";
      }
    }
    description
      "The type of DHCP option82 vendor suboption format.";
  }

  grouping ncs_template_dhcp-relay-type {
    description
      "DHCP relay.";
    container global {
      description
        "Configure DHCP relay global attributes.";
      leaf user-detect-interval {
        type string;
        units "min";
        // NCS drop default statement
        description
          "DHCP relay ARP user-detect interval.";
      }
      leaf user-autosave-flag {
        type string;
        // NCS drop default statement
        description
          "Enable/disable a DHCP relay agent to store user entries.";
      }
      leaf user-store-interval {
        type string;
        units "s";
        // NCS drop default statement
        description
          "DHCP relay unnumbered table write-delay.";
      }
      leaf distribute-flag {
        type string;
        // NCS drop default statement
        description
          "Enable/disable DHCP relay distribute flag.";
      }
      leaf opt82-inner-vlan-insert-flag {
        type string;
        // NCS drop default statement
        description
          "Enable/disable DHCP option82 inner-VLAN change flag.";
      }
      container option {
        description
          "Configure the information instance of DHCP packet option code.";
        leaf option-code {
          type string;
          description
            "Option code.";
        }
        leaf sub-option {
          // NCS drop when statement
          type string;
          description
            "Sub-option code.";
        }
      }
      container source-ip {
        description
          "Configure DHCP relay global source IP attributes.";
        leaf source-ip-address {
          type string;
          description
            "Relay source address.";
        }
        leaf vpn-name {
          // NCS drop when statement
          type string;
          // NCS drop must statement
          // NCS drop default statement
          description
            "VPN name.";
        }
      }
    }
  }

  grouping ncs_rpc_notif_dhcp-relay-type {
    description
      "DHCP relay.";
    container global {
      description
        "Configure DHCP relay global attributes.";
      leaf user-detect-interval {
        type uint16 {
          range "0..60";
        }
        units "min";
        default "20";
        description
          "DHCP relay ARP user-detect interval.";
      }
      leaf user-autosave-flag {
        type boolean;
        default "false";
        description
          "Enable/disable a DHCP relay agent to store user entries.";
      }
      leaf user-store-interval {
        type uint32 {
          range "300..86400";
        }
        units "s";
        default "300";
        description
          "DHCP relay unnumbered table write-delay.";
      }
      leaf distribute-flag {
        type boolean;
        default "false";
        description
          "Enable/disable DHCP relay distribute flag.";
      }
      leaf opt82-inner-vlan-insert-flag {
        type boolean;
        default "false";
        description
          "Enable/disable DHCP option82 inner-VLAN change flag.";
      }
      container option {
        description
          "Configure the information instance of DHCP packet option code.";
        leaf option-code {
          type uint8 {
            range "1..255";
          }
          description
            "Option code.";
        }
        leaf sub-option {
          when '../option-code' {
            tailf:xpath-root 3;
          }
          type uint8 {
            range "1..255";
          }
          description
            "Sub-option code.";
        }
      }
      container source-ip {
        description
          "Configure DHCP relay global source IP attributes.";
        leaf source-ip-address {
          type inet:ipv4-address-no-zone;
          description
            "Relay source address.";
        }
        leaf vpn-name {
          when '../source-ip-address' {
            tailf:xpath-root 3;
          }
          type string;
          must "/ni:network-instance/ni:instances/ni:instance[ni:name=current()]/l3vpn:afs/l3vpn:af[l3vpn:type='ipv4-unicast']" {
            tailf:xpath-root 3;
          }
          default "_public_";
          description
            "VPN name.";
        }
      }
    }
  }

  grouping live_ncs_dhcp-relay-type {
    description
      "DHCP relay.";
    container global {
      description
        "Configure DHCP relay global attributes.";
      leaf user-detect-interval {
        type uint16 {
          range "0..60";
        }
        units "min";
        // NCS drop default statement
        description
          "DHCP relay ARP user-detect interval.";
      }
      leaf user-autosave-flag {
        type boolean;
        // NCS drop default statement
        description
          "Enable/disable a DHCP relay agent to store user entries.";
      }
      leaf user-store-interval {
        type uint32 {
          range "300..86400";
        }
        units "s";
        // NCS drop default statement
        description
          "DHCP relay unnumbered table write-delay.";
      }
      leaf distribute-flag {
        type boolean;
        // NCS drop default statement
        description
          "Enable/disable DHCP relay distribute flag.";
      }
      leaf opt82-inner-vlan-insert-flag {
        type boolean;
        // NCS drop default statement
        description
          "Enable/disable DHCP option82 inner-VLAN change flag.";
      }
      container option {
        description
          "Configure the information instance of DHCP packet option code.";
        leaf option-code {
          type uint8 {
            range "1..255";
          }
          description
            "Option code.";
        }
        leaf sub-option {
          // NCS drop when statement
          type uint8 {
            range "1..255";
          }
          description
            "Sub-option code.";
        }
      }
      container source-ip {
        description
          "Configure DHCP relay global source IP attributes.";
        leaf source-ip-address {
          type inet:ipv4-address-no-zone;
          description
            "Relay source address.";
        }
        leaf vpn-name {
          // NCS drop when statement
          type leafref {
            path "/ncs:devices/ncs:device/ncs:live-status/ni:network-instance/ni:instances/ni:instance/ni:name" {
              tailf:xpath-root 3;
            }
          }
          // NCS drop must statement
          // NCS drop default statement
          description
            "VPN name.";
        }
      }
    }
  }

  grouping dhcp-relay-type {
    description
      "DHCP relay.";
    container global {
      description
        "Configure DHCP relay global attributes.";
      leaf user-detect-interval {
        type uint16 {
          range "0..60";
        }
        units "min";
        default "20";
        description
          "DHCP relay ARP user-detect interval.";
      }
      leaf user-autosave-flag {
        type boolean;
        default "false";
        description
          "Enable/disable a DHCP relay agent to store user entries.";
      }
      leaf user-store-interval {
        type uint32 {
          range "300..86400";
        }
        units "s";
        default "300";
        description
          "DHCP relay unnumbered table write-delay.";
      }
      leaf distribute-flag {
        type boolean;
        default "false";
        description
          "Enable/disable DHCP relay distribute flag.";
      }
      leaf opt82-inner-vlan-insert-flag {
        type boolean;
        default "false";
        description
          "Enable/disable DHCP option82 inner-VLAN change flag.";
      }
      container option {
        description
          "Configure the information instance of DHCP packet option code.";
        leaf option-code {
          type uint8 {
            range "1..255";
          }
          description
            "Option code.";
        }
        leaf sub-option {
          when '../option-code' {
            tailf:xpath-root 3;
          }
          type uint8 {
            range "1..255";
          }
          description
            "Sub-option code.";
        }
      }
      container source-ip {
        description
          "Configure DHCP relay global source IP attributes.";
        leaf source-ip-address {
          type inet:ipv4-address-no-zone;
          description
            "Relay source address.";
        }
        leaf vpn-name {
          when '../source-ip-address' {
            tailf:xpath-root 3;
          }
          type leafref {
            path "/ncs:devices/ncs:device/ncs:config/ni:network-instance/ni:instances/ni:instance/ni:name" {
              tailf:xpath-root 3;
            }
          }
          must "/ni:network-instance/ni:instances/ni:instance[ni:name=current()]/l3vpn:afs/l3vpn:af[l3vpn:type='ipv4-unicast']" {
            tailf:xpath-root 3;
          }
          default "_public_";
          description
            "VPN name.";
        }
      }
    }
  }

  augment "/ncs:devices/ncs:template/ncs:ned-id/ncs:config/ifm:ifm/ifm:interfaces/ifm:interface" {
    description
      "Extend interface attribute.";
    container dhcp-relay-attribute {
      description
        "Configure DHCP relay attributes on an interface.";
      leaf enable {
        type string;
        // NCS drop default statement
        description
          "Enable/disable DHCP relay.";
      }
      leaf reply-packet-policy {
        type ncs_template_dhcp-relay-reply-type;
        description
          "Reply packets policy.";
      }
      container option82 {
        // NCS drop must statement
        description
          "Configure DHCP relay option82 on an interface.";
        leaf link-selection-enable {
          type string;
          // NCS drop default statement
          description
            "Enable/disable to insert link selection information.";
        }
        leaf link-selection-address {
          type string;
          description
            "Link selection sub-option IP address.";
        }
        leaf vendor-specific-enable {
          // NCS drop when statement
          type string;
          // NCS drop default statement
          description
            "Enable/disable to insert suboption9 of option82.";
        }
        leaf subscriber-id-enable {
          type string;
          // NCS drop default statement
          description
            "Enable/disable to insert subscriber ID.";
        }
        leaf subscriber-id-mode {
          // NCS drop when statement
          type ncs_template_dhcp-opt82-sub6-format;
          // NCS drop default statement
          description
            "Subscriber ID mode.";
        }
        leaf subscriber-id-self-define-text {
          // NCS drop when statement
          type string;
          description
            "Configure a DHCP option82 self-defined string for subscriber ID.";
        }
      }
      container server-addresses {
        description
          "List of configuring server addresses on interfaces.";
        list server-address {
          // NCS patched for predictable order
          ordered-by user;
          // NCS drop must statement
          key "address vendor option-code vendor-class";
          description
            "Configure a server address on an interface.";
          leaf address {
            type string;
            description
              "Server address.";
          }
          leaf vendor {
            type string;
            description
              "Enable/disable to carry a vendor identifier.";
          }
          leaf option-code {
            type string;
            description
              "Option code, 0 means NULL.";
          }
          leaf vendor-class {
            type string;
            description
              "Vendor identifier.";
          }
        }
      }
      container gateway-addresses {
        description
          "List of configuring a gateway address list on an interface.";
        list gateway-address {
          // NCS patched for predictable order
          ordered-by user;
          // NCS drop must statement
          key "vendor option-code vendor-class";
          description
            "Configure a gateway address instance on an interface.";
          leaf vendor {
            type string;
            description
              "Enable/disable to carry vendor identifier.";
          }
          leaf option-code {
            type string;
            description
              "Option code, 0 means NULL.";
          }
          leaf vendor-class {
            type string;
            description
              "Vendor identifier.";
          }
          leaf ip-address {
            type string;
            // NCS drop mandatory statement
            description
              "Gateway address.";
          }
        }
      }
      container relay-source-address {
        // NCS drop must statement
        presence "Enable/disable the functions of DHCP relay source address.";
        description
          "Configure DHCP relay source address.";
        leaf vpn-name {
          type string;
          // NCS drop must statement
          // NCS drop mandatory statement
          description
            "VPN name specified in the source address of a relay interface, the '_public_' of vpn-name means public network.";
        }
        leaf source-address {
          type string;
          // NCS drop mandatory statement
          description
            "Source address.";
        }
      }
      container relay-source-option-addresses {
        description
          "List of configuring source IP addresses based on option.";
        list relay-source-option-address {
          // NCS patched for predictable order
          ordered-by user;
          // NCS drop must statement
          // NCS drop must statement
          key "vendor option-code vendor-class";
          description
            "Configure a source IP address based on option.";
          leaf vendor {
            type string;
            description
              "Enable/disable to carry a vendor identifier.";
          }
          leaf option-code {
            type string;
            description
              "Option code, 0 means NULL.";
          }
          leaf vendor-class {
            type string;
            description
              "Vendor identifier.";
          }
          leaf source-address {
            type string;
            // NCS drop mandatory statement
            description
              "Source address.";
          }
        }
      }
      container opt82-vendor-specifics {
        // NCS drop when statement
        description
          "List of option82 vendor-specific instance.";
        list opt82-vendor-specific {
          // NCS patched for predictable order
          ordered-by user;
          key "sub-option-number";
          // NCS drop max-elements statement
          description
            "Configure an option82 vendor-specific instance. Only one record can be configured.";
          leaf sub-option-number {
            type string;
            description
              "Suboption of option82.";
          }
          leaf sub-option-format {
            type ncs_template_dhcp-opt82-vendor-sub-option-format;
            // NCS drop mandatory statement
            description
              "Suboption format.";
          }
          leaf ip-address {
            type string;
            // NCS drop mandatory statement
            description
              "Source IPv4 address of forward package.";
          }
        }
      }
    }
  }
  augment "/ncs:devices/ncs:device/ncs:live-status/ifm:ifm/ifm:interfaces/ifm:interface" {
    description
      "Extend interface attribute.";
    container dhcp-relay-attribute {
      tailf:ncs-device-type "netconf";
      tailf:display-when "not(../../../../../ncs:module) or ../../../../../ncs:module[ncs:name='huawei-dhcp'] or (../../../../../ncs:live-status-protocol[not(ncs:capability)]) or (../../../../../ncs:live-status-protocol/ncs:capability/ncs:module[.='huawei-dhcp'])";
      description
        "Configure DHCP relay attributes on an interface.";
      leaf enable {
        type boolean;
        // NCS drop default statement
        description
          "Enable/disable DHCP relay.";
      }
      leaf reply-packet-policy {
        type live_ncs_dhcp-relay-reply-type;
        description
          "Reply packets policy.";
      }
      container option82 {
        // NCS drop must statement
        description
          "Configure DHCP relay option82 on an interface.";
        leaf link-selection-enable {
          type boolean;
          // NCS drop default statement
          description
            "Enable/disable to insert link selection information.";
        }
        leaf link-selection-address {
          type inet:ipv4-address-no-zone;
          description
            "Link selection sub-option IP address.";
        }
        leaf vendor-specific-enable {
          // NCS drop when statement
          type boolean;
          // NCS drop default statement
          description
            "Enable/disable to insert suboption9 of option82.";
        }
        leaf subscriber-id-enable {
          type boolean;
          // NCS drop default statement
          description
            "Enable/disable to insert subscriber ID.";
        }
        leaf subscriber-id-mode {
          // NCS drop when statement
          type live_ncs_dhcp-opt82-sub6-format;
          // NCS drop default statement
          description
            "Subscriber ID mode.";
        }
        leaf subscriber-id-self-define-text {
          // NCS drop when statement
          type string {
            length "1..251";
            pattern '([^\t]{1,})';
          }
          description
            "Configure a DHCP option82 self-defined string for subscriber ID.";
        }
      }
      container server-addresses {
        description
          "List of configuring server addresses on interfaces.";
        list server-address {
          // NCS drop must statement
          key "address vendor option-code vendor-class";
          description
            "Configure a server address on an interface.";
          leaf address {
            type inet:ipv4-address-no-zone;
            description
              "Server address.";
          }
          leaf vendor {
            type boolean;
            description
              "Enable/disable to carry a vendor identifier.";
          }
          leaf option-code {
            type uint8 {
              range "0..254";
            }
            description
              "Option code, 0 means NULL.";
          }
          leaf vendor-class {
            type string {
              length "1..128";
              pattern '([^\t]{1,})';
            }
            description
              "Vendor identifier.";
          }
        }
      }
      container gateway-addresses {
        description
          "List of configuring a gateway address list on an interface.";
        list gateway-address {
          // NCS drop must statement
          key "vendor option-code vendor-class";
          description
            "Configure a gateway address instance on an interface.";
          leaf vendor {
            type boolean;
            description
              "Enable/disable to carry vendor identifier.";
          }
          leaf option-code {
            type uint8 {
              range "0..254";
            }
            description
              "Option code, 0 means NULL.";
          }
          leaf vendor-class {
            type string {
              length "1..128";
              pattern '([^\t]{1,})';
            }
            description
              "Vendor identifier.";
          }
          leaf ip-address {
            type inet:ipv4-address-no-zone;
            // NCS drop mandatory statement
            description
              "Gateway address.";
          }
        }
      }
      container relay-source-address {
        // NCS drop must statement
        presence "Enable/disable the functions of DHCP relay source address.";
        description
          "Configure DHCP relay source address.";
        leaf vpn-name {
          type leafref {
            path "/ncs:devices/ncs:device/ncs:live-status/ni:network-instance/ni:instances/ni:instance/ni:name" {
              tailf:xpath-root 3;
            }
          }
          // NCS drop must statement
          // NCS drop mandatory statement
          description
            "VPN name specified in the source address of a relay interface, the '_public_' of vpn-name means public network.";
        }
        leaf source-address {
          type inet:ipv4-address-no-zone;
          // NCS drop mandatory statement
          description
            "Source address.";
        }
      }
      container relay-source-option-addresses {
        description
          "List of configuring source IP addresses based on option.";
        list relay-source-option-address {
          // NCS drop must statement
          // NCS drop must statement
          key "vendor option-code vendor-class";
          description
            "Configure a source IP address based on option.";
          leaf vendor {
            type boolean;
            description
              "Enable/disable to carry a vendor identifier.";
          }
          leaf option-code {
            type uint8 {
              range "0..254";
            }
            description
              "Option code, 0 means NULL.";
          }
          leaf vendor-class {
            type string {
              length "1..128";
              pattern '([^\t]{1,})';
            }
            description
              "Vendor identifier.";
          }
          leaf source-address {
            type inet:ipv4-address-no-zone;
            // NCS drop mandatory statement
            description
              "Source address.";
          }
        }
      }
      container opt82-vendor-specifics {
        // NCS drop when statement
        description
          "List of option82 vendor-specific instance.";
        list opt82-vendor-specific {
          key "sub-option-number";
          // NCS drop max-elements statement
          description
            "Configure an option82 vendor-specific instance. Only one record can be configured.";
          leaf sub-option-number {
            type uint32 {
              range "1..255";
            }
            description
              "Suboption of option82.";
          }
          leaf sub-option-format {
            type live_ncs_dhcp-opt82-vendor-sub-option-format;
            // NCS drop mandatory statement
            description
              "Suboption format.";
          }
          leaf ip-address {
            type inet:ipv4-address-no-zone;
            // NCS drop mandatory statement
            description
              "Source IPv4 address of forward package.";
          }
        }
      }
    }
  }
  augment "/ncs:devices/ncs:device/ncs:config/ifm:ifm/ifm:interfaces/ifm:interface" {
    description
      "Extend interface attribute.";
    container dhcp-relay-attribute {
      tailf:ncs-device-type "netconf";
      tailf:display-when "not(../../../../../ncs:module) or ../../../../../ncs:module[ncs:name='huawei-dhcp']";
      description
        "Configure DHCP relay attributes on an interface.";
      leaf enable {
        type boolean;
        default "false";
        description
          "Enable/disable DHCP relay.";
      }
      leaf reply-packet-policy {
        type dhcp-relay-reply-type;
        description
          "Reply packets policy.";
      }
      container option82 {
        must "(subscriber-id-enable='true' and subscriber-id-mode='self-define' and subscriber-id-self-define-text) or (subscriber-id-enable='false')" {
          tailf:xpath-root 3;
        }
        description
          "Configure DHCP relay option82 on an interface.";
        leaf link-selection-enable {
          type boolean;
          default "false";
          description
            "Enable/disable to insert link selection information.";
        }
        leaf link-selection-address {
          type inet:ipv4-address-no-zone;
          description
            "Link selection sub-option IP address.";
        }
        leaf vendor-specific-enable {
          when "(../../../ifm:type='Vbdif') or (../../../ifm:type='Global-VE' and ../../../ifm:class='sub-interface') or (../../../ifm:type='Virtual-Ethernet' and ../../../ifm:class='sub-interface')" {
            tailf:xpath-root 3;
          }
          type boolean;
          default "false";
          description
            "Enable/disable to insert suboption9 of option82.";
        }
        leaf subscriber-id-enable {
          type boolean;
          default "false";
          description
            "Enable/disable to insert subscriber ID.";
        }
        leaf subscriber-id-mode {
          when "../subscriber-id-enable='true'" {
            tailf:xpath-root 3;
          }
          type dhcp-opt82-sub6-format;
          default "self-define";
          description
            "Subscriber ID mode.";
        }
        leaf subscriber-id-self-define-text {
          when "../subscriber-id-enable='true' and ../subscriber-id-mode='self-define'" {
            tailf:xpath-root 3;
          }
          type string {
            length "1..251";
            pattern '([^\t]{1,})';
          }
          description
            "Configure a DHCP option82 self-defined string for subscriber ID.";
        }
      }
      container server-addresses {
        description
          "List of configuring server addresses on interfaces.";
        list server-address {
          must "(vendor='false' and vendor-class='-') or (vendor='true' and option-code=60)" {
            tailf:xpath-root 3;
          }
          key "address vendor option-code vendor-class";
          description
            "Configure a server address on an interface.";
          leaf address {
            type inet:ipv4-address-no-zone;
            description
              "Server address.";
          }
          leaf vendor {
            type boolean;
            description
              "Enable/disable to carry a vendor identifier.";
          }
          leaf option-code {
            type uint8 {
              range "0..254";
            }
            description
              "Option code, 0 means NULL.";
          }
          leaf vendor-class {
            type string {
              length "1..128";
              pattern '([^\t]{1,})';
            }
            description
              "Vendor identifier.";
          }
        }
      }
      container gateway-addresses {
        description
          "List of configuring a gateway address list on an interface.";
        list gateway-address {
          must "(vendor='false' and vendor-class='-') or (vendor='true' and option-code=60)" {
            tailf:xpath-root 3;
          }
          key "vendor option-code vendor-class";
          description
            "Configure a gateway address instance on an interface.";
          leaf vendor {
            type boolean;
            description
              "Enable/disable to carry vendor identifier.";
          }
          leaf option-code {
            type uint8 {
              range "0..254";
            }
            description
              "Option code, 0 means NULL.";
          }
          leaf vendor-class {
            type string {
              length "1..128";
              pattern '([^\t]{1,})';
            }
            description
              "Vendor identifier.";
          }
          leaf ip-address {
            type inet:ipv4-address-no-zone;
            mandatory true;
            description
              "Gateway address.";
          }
        }
      }
      container relay-source-address {
        must 'not(../relay-source-option-addresses/relay-source-option-address)' {
          tailf:xpath-root 3;
        }
        presence "Enable/disable the functions of DHCP relay source address.";
        description
          "Configure DHCP relay source address.";
        leaf vpn-name {
          type leafref {
            path "/ncs:devices/ncs:device/ncs:config/ni:network-instance/ni:instances/ni:instance/ni:name" {
              tailf:xpath-root 3;
            }
          }
          must "/ni:network-instance/ni:instances/ni:instance[ni:name=current()]/l3vpn:afs/l3vpn:af[l3vpn:type='ipv4-unicast']" {
            tailf:xpath-root 3;
          }
          mandatory true;
          description
            "VPN name specified in the source address of a relay interface, the '_public_' of vpn-name means public network.";
        }
        leaf source-address {
          type inet:ipv4-address-no-zone;
          mandatory true;
          description
            "Source address.";
        }
      }
      container relay-source-option-addresses {
        description
          "List of configuring source IP addresses based on option.";
        list relay-source-option-address {
          must 'not(../../relay-source-address)' {
            tailf:xpath-root 3;
          }
          must "(vendor='false' and vendor-class='-') or (vendor='true' and option-code=60)" {
            tailf:xpath-root 3;
          }
          key "vendor option-code vendor-class";
          description
            "Configure a source IP address based on option.";
          leaf vendor {
            type boolean;
            description
              "Enable/disable to carry a vendor identifier.";
          }
          leaf option-code {
            type uint8 {
              range "0..254";
            }
            description
              "Option code, 0 means NULL.";
          }
          leaf vendor-class {
            type string {
              length "1..128";
              pattern '([^\t]{1,})';
            }
            description
              "Vendor identifier.";
          }
          leaf source-address {
            type inet:ipv4-address-no-zone;
            mandatory true;
            description
              "Source address.";
          }
        }
      }
      container opt82-vendor-specifics {
        when "(../../ifm:type='Vbdif') or (../../ifm:type='Global-VE' and ../../ifm:class='sub-interface') or (../../ifm:type='Virtual-Ethernet' and ../../ifm:class='sub-interface')" {
          tailf:xpath-root 3;
        }
        description
          "List of option82 vendor-specific instance.";
        list opt82-vendor-specific {
          key "sub-option-number";
          max-elements 1;
          description
            "Configure an option82 vendor-specific instance. Only one record can be configured.";
          leaf sub-option-number {
            type uint32 {
              range "1..255";
            }
            description
              "Suboption of option82.";
          }
          leaf sub-option-format {
            type dhcp-opt82-vendor-sub-option-format;
            mandatory true;
            description
              "Suboption format.";
          }
          leaf ip-address {
            type inet:ipv4-address-no-zone;
            mandatory true;
            description
              "Source IPv4 address of forward package.";
          }
        }
      }
    }
  }
}
