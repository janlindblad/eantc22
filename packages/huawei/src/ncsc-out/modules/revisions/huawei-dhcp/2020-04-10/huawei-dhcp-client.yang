submodule huawei-dhcp-client {
  // Generated by yanger -t ncs
  tailf:mount-id "huawei-nc-1.0:huawei-nc-1.0";

  yang-version 1;
  belongs-to huawei-dhcp {
    prefix dhcp;
  }

  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "This module contains a collection of YANG definitions for managing DHCP client.";

  revision 2019-12-22 {
    description
      "Initial revision.";
    reference "Huawei private.";
  }

  typedef ncs_template_client-state {
    type string;
    description
      "The type of client-state.";
  }

  typedef ncs_rpc_notif_client-state {
    type enumeration {
      enum "init" {
        value 0;
        description
          "Init state.";
      }
      enum "selecting" {
        value 1;
        description
          "Selecting state.";
      }
      enum "requesting" {
        value 2;
        description
          "Requesting state.";
      }
      enum "bound" {
        value 3;
        description
          "Bound state.";
      }
      enum "renewing" {
        value 4;
        description
          "Renewing state.";
      }
      enum "rebinding" {
        value 5;
        description
          "Rebinding state.";
      }
    }
    description
      "The type of client-state.";
  }

  typedef live_ncs_client-state {
    type enumeration {
      enum "init" {
        value 0;
        description
          "Init state.";
      }
      enum "selecting" {
        value 1;
        description
          "Selecting state.";
      }
      enum "requesting" {
        value 2;
        description
          "Requesting state.";
      }
      enum "bound" {
        value 3;
        description
          "Bound state.";
      }
      enum "renewing" {
        value 4;
        description
          "Renewing state.";
      }
      enum "rebinding" {
        value 5;
        description
          "Rebinding state.";
      }
    }
    description
      "The type of client-state.";
  }

  typedef client-state {
    type enumeration {
      enum "init" {
        value 0;
        description
          "Init state.";
      }
      enum "selecting" {
        value 1;
        description
          "Selecting state.";
      }
      enum "requesting" {
        value 2;
        description
          "Requesting state.";
      }
      enum "bound" {
        value 3;
        description
          "Bound state.";
      }
      enum "renewing" {
        value 4;
        description
          "Renewing state.";
      }
      enum "rebinding" {
        value 5;
        description
          "Rebinding state.";
      }
    }
    description
      "The type of client-state.";
  }

  grouping ncs_template_dhcp-client-type {
    description
      "Configure DHCP client attributes.";
    container global {
      description
        "Configure DHCP client global attributes.";
      leaf option60 {
        type string;
        description
          "The value of DHCP client global option60.";
      }
      leaf unicast-flag {
        type empty;
        description
          "DHCP client unicast flag.";
      }
    }
  }

  grouping ncs_rpc_notif_dhcp-client-type {
    description
      "Configure DHCP client attributes.";
    container global {
      description
        "Configure DHCP client global attributes.";
      leaf option60 {
        type string {
          length "1..128";
          pattern '([^\t]{1,})';
        }
        description
          "The value of DHCP client global option60.";
      }
      leaf unicast-flag {
        type empty;
        description
          "DHCP client unicast flag.";
      }
    }
  }

  grouping live_ncs_dhcp-client-type {
    description
      "Configure DHCP client attributes.";
    container global {
      description
        "Configure DHCP client global attributes.";
      leaf option60 {
        type string {
          length "1..128";
          pattern '([^\t]{1,})';
        }
        description
          "The value of DHCP client global option60.";
      }
      leaf unicast-flag {
        type empty;
        description
          "DHCP client unicast flag.";
      }
    }
  }

  grouping dhcp-client-type {
    description
      "Configure DHCP client attributes.";
    container global {
      description
        "Configure DHCP client global attributes.";
      leaf option60 {
        type string {
          length "1..128";
          pattern '([^\t]{1,})';
        }
        description
          "The value of DHCP client global option60.";
      }
      leaf unicast-flag {
        type empty;
        description
          "DHCP client unicast flag.";
      }
    }
  }
}
