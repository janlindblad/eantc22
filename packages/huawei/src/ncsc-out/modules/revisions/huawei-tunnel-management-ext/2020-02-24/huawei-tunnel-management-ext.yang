module huawei-tunnel-management-ext {
  // Generated by yanger -t ncs
  tailf:mount-id "huawei-nc-1.0:huawei-nc-1.0";
  tailf:ncs-device-type "netconf";

  yang-version 1;
  namespace "urn:huawei:yang:huawei-tunnel-management-ext";
  prefix tnlm-ext;

  import huawei-extension {
    prefix ext;
  }
  import huawei-tunnel-management {
    prefix tnlm;
  }
  import huawei-network-instance {
    prefix ni;
  }
  import huawei-srpolicy {
    prefix srpolicy;
  }
  import huawei-segment-routing {
    prefix sr;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Tunnel management, including management on tunnel policies and tunnel selectors.";

  revision 2020-02-24 {
    description
      "Initial revision.";
    reference "Huawei private.";
  }
  ext:task-name "tunnel";

  augment "/ncs:devices/ncs:template/ncs:ned-id/ncs:config/tnlm:tunnel-management/tnlm:tunnel-policys/tnlm:tunnel-policy/tnlm:ipv4-set/tnlm:policy-type/tnlm:binding/tnlm:nexthops/tnlm:nexthop" {
    description
      "Augment the huawei-tunnel-management-ext model to add tunnel-policy configuration.";
    leaf group-id {
      // NCS drop when statement
      type string;
      description
        "SR TE policy group ID.";
    }
  }
  augment "/ncs:devices/ncs:device/ncs:live-status/tnlm:tunnel-management/tnlm:tunnel-policys/tnlm:tunnel-policy/tnlm:ipv4-set/tnlm:policy-type/tnlm:binding/tnlm:nexthops/tnlm:nexthop" {
    description
      "Augment the huawei-tunnel-management-ext model to add tunnel-policy configuration.";
    leaf group-id {
      tailf:ncs-device-type "netconf";
      tailf:display-when "not(../../../../../../../../../../ncs:module) or ../../../../../../../../../../ncs:module[ncs:name='huawei-tunnel-management-ext'] or (../../../../../../../../../../ncs:live-status-protocol[not(ncs:capability)]) or (../../../../../../../../../../ncs:live-status-protocol/ncs:capability/ncs:module[.='huawei-tunnel-management-ext'])";
      // NCS drop when statement
      type leafref {
        path "/ncs:devices/ncs:device/ncs:live-status/ni:network-instance/ni:instances/ni:instance/sr:segment-routing/srpolicy:srpolicy/srpolicy:policy-groups/srpolicy:policy-group/srpolicy:index" {
          tailf:xpath-root 3;
        }
      }
      description
        "SR TE policy group ID.";
    }
  }
  augment "/ncs:devices/ncs:device/ncs:config/tnlm:tunnel-management/tnlm:tunnel-policys/tnlm:tunnel-policy/tnlm:ipv4-set/tnlm:policy-type/tnlm:binding/tnlm:nexthops/tnlm:nexthop" {
    description
      "Augment the huawei-tunnel-management-ext model to add tunnel-policy configuration.";
    leaf group-id {
      tailf:ncs-device-type "netconf";
      tailf:display-when "not(../../../../../../../../../../ncs:module) or ../../../../../../../../../../ncs:module[ncs:name='huawei-tunnel-management-ext']";
      when "../tnlm:bind-type='sr-te-policy-group'" {
        tailf:xpath-root 3;
      }
      type leafref {
        path "/ncs:devices/ncs:device/ncs:config/ni:network-instance/ni:instances/ni:instance/sr:segment-routing/srpolicy:srpolicy/srpolicy:policy-groups/srpolicy:policy-group/srpolicy:index" {
          tailf:xpath-root 3;
        }
      }
      description
        "SR TE policy group ID.";
    }
  }
}
