module huawei-mac-flapping {
  // Generated by yanger -t ncs
  tailf:mount-id "huawei-nc-1.0:huawei-nc-1.0";
  tailf:ncs-device-type "netconf";

  namespace "urn:huawei:yang:huawei-mac-flapping";
  prefix mac-flapping;

  import huawei-ifm {
    prefix ifm;
  }
  import huawei-ethernet {
    prefix ethernet;
  }
  import huawei-bd {
    prefix bd;
  }
  import huawei-vlan {
    prefix vlan;
  }
  import huawei-l2vpn {
    prefix l2vpn;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "MAC flapping-based loop detection.";

  revision 2020-03-09 {
    description
      "Modify description.";
    reference "Huawei private.";
  }
  revision 2019-04-23 {
    description
      "Initial revision.";
    reference "Huawei private.";
  }
  ext:task-name "mflp";

  typedef ncs_template_alarm-enable {
    type string;
    description
      "Alarm enable.";
  }

  typedef ncs_template_mflp-enable {
    type string;
    description
      "MFLP enable type.";
  }

  typedef ncs_rpc_notif_alarm-enable {
    type enumeration {
      enum "block" {
        value 1;
        description
          "Disable the loop detection alarm function.";
      }
      enum "alarm" {
        value 2;
        description
          "Enable the loop detection alarm function.";
      }
    }
    description
      "Alarm enable.";
  }

  typedef ncs_rpc_notif_mflp-enable {
    type enumeration {
      enum "disable" {
        value 1;
        description
          "Disable type.";
      }
      enum "enable" {
        value 2;
        description
          "Enable type.";
      }
    }
    description
      "MFLP enable type.";
  }

  typedef live_ncs_alarm-enable {
    type enumeration {
      enum "block" {
        value 1;
        description
          "Disable the loop detection alarm function.";
      }
      enum "alarm" {
        value 2;
        description
          "Enable the loop detection alarm function.";
      }
    }
    description
      "Alarm enable.";
  }

  typedef live_ncs_mflp-enable {
    type enumeration {
      enum "disable" {
        value 1;
        description
          "Disable type.";
      }
      enum "enable" {
        value 2;
        description
          "Enable type.";
      }
    }
    description
      "MFLP enable type.";
  }

  typedef alarm-enable {
    type enumeration {
      enum "block" {
        value 1;
        description
          "Disable the loop detection alarm function.";
      }
      enum "alarm" {
        value 2;
        description
          "Enable the loop detection alarm function.";
      }
    }
    description
      "Alarm enable.";
  }

  typedef mflp-enable {
    type enumeration {
      enum "disable" {
        value 1;
        description
          "Disable type.";
      }
      enum "enable" {
        value 2;
        description
          "Enable type.";
      }
    }
    description
      "MFLP enable type.";
  }

  grouping ncs_template_group-mac-flapping {
    description
      "Configuration of MAC flapping.";
    container mac-flapping {
      description
        "Configure MAC flapping.";
      container loop-detect {
        presence "Loop detect configuration.";
        description
          "Configure VSI MAC flapping entry.";
        leaf loop-times {
          type string;
          // NCS drop mandatory statement
          description
            "Number of MAC address flappings.";
        }
        leaf detect-cycle {
          type string;
          units "s";
          // NCS drop mandatory statement
          description
            "Detection cycle.";
        }
        leaf cycles {
          type string;
          // NCS drop mandatory statement
          description
            "Number of cycles.";
        }
        leaf action {
          type ncs_template_alarm-enable;
          // NCS drop mandatory statement
          description
            "Action taken after a loop occurs. The action can be reporting an alarm or blocking an interface.";
        }
        leaf retry-times {
          // NCS drop when statement
          type string;
          // NCS drop must statement
          description
            "Retry times.";
        }
        leaf block-time {
          // NCS drop when statement
          type string;
          units "s";
          // NCS drop must statement
          description
            "Blocking time.";
        }
      }
      container precise-block {
        presence "precise-block";
        description
          "Configure precise blocking policy table.";
      }
    }
  }

  grouping ncs_rpc_notif_group-mac-flapping {
    description
      "Configuration of MAC flapping.";
    container mac-flapping {
      description
        "Configure MAC flapping.";
      container loop-detect {
        presence "Loop detect configuration.";
        description
          "Configure VSI MAC flapping entry.";
        leaf loop-times {
          type uint32 {
            range "3..1000";
          }
          mandatory true;
          description
            "Number of MAC address flappings.";
        }
        leaf detect-cycle {
          type uint32 {
            range "3..30";
          }
          units "s";
          mandatory true;
          description
            "Detection cycle.";
        }
        leaf cycles {
          type uint32 {
            range "1..15";
          }
          mandatory true;
          description
            "Number of cycles.";
        }
        leaf action {
          type ncs_rpc_notif_alarm-enable;
          mandatory true;
          description
            "Action taken after a loop occurs. The action can be reporting an alarm or blocking an interface.";
        }
        leaf retry-times {
          when "../action='block'" {
            tailf:xpath-root 3;
          }
          type uint32 {
            range "0..5";
          }
          must '(../retry-times and ../block-time) or (not(../retry-times) and not(../block-time))' {
            tailf:xpath-root 3;
          }
          description
            "Retry times.";
        }
        leaf block-time {
          when "../action='block'" {
            tailf:xpath-root 3;
          }
          type uint32 {
            range "10..65535";
          }
          units "s";
          must '(../retry-times and ../block-time) or (not(../retry-times) and not(../block-time))' {
            tailf:xpath-root 3;
          }
          description
            "Blocking time.";
        }
      }
      container precise-block {
        presence "precise-block";
        description
          "Configure precise blocking policy table.";
      }
    }
  }

  grouping live_ncs_group-mac-flapping {
    description
      "Configuration of MAC flapping.";
    container mac-flapping {
      description
        "Configure MAC flapping.";
      container loop-detect {
        presence "Loop detect configuration.";
        description
          "Configure VSI MAC flapping entry.";
        leaf loop-times {
          type uint32 {
            range "3..1000";
          }
          // NCS drop mandatory statement
          description
            "Number of MAC address flappings.";
        }
        leaf detect-cycle {
          type uint32 {
            range "3..30";
          }
          units "s";
          // NCS drop mandatory statement
          description
            "Detection cycle.";
        }
        leaf cycles {
          type uint32 {
            range "1..15";
          }
          // NCS drop mandatory statement
          description
            "Number of cycles.";
        }
        leaf action {
          type live_ncs_alarm-enable;
          // NCS drop mandatory statement
          description
            "Action taken after a loop occurs. The action can be reporting an alarm or blocking an interface.";
        }
        leaf retry-times {
          // NCS drop when statement
          type uint32 {
            range "0..5";
          }
          // NCS drop must statement
          description
            "Retry times.";
        }
        leaf block-time {
          // NCS drop when statement
          type uint32 {
            range "10..65535";
          }
          units "s";
          // NCS drop must statement
          description
            "Blocking time.";
        }
      }
      container precise-block {
        presence "precise-block";
        description
          "Configure precise blocking policy table.";
      }
    }
  }

  grouping group-mac-flapping {
    description
      "Configuration of MAC flapping.";
    container mac-flapping {
      description
        "Configure MAC flapping.";
      container loop-detect {
        presence "Loop detect configuration.";
        description
          "Configure VSI MAC flapping entry.";
        leaf loop-times {
          type uint32 {
            range "3..1000";
          }
          mandatory true;
          description
            "Number of MAC address flappings.";
        }
        leaf detect-cycle {
          type uint32 {
            range "3..30";
          }
          units "s";
          mandatory true;
          description
            "Detection cycle.";
        }
        leaf cycles {
          type uint32 {
            range "1..15";
          }
          mandatory true;
          description
            "Number of cycles.";
        }
        leaf action {
          type alarm-enable;
          mandatory true;
          description
            "Action taken after a loop occurs. The action can be reporting an alarm or blocking an interface.";
        }
        leaf retry-times {
          when "../action='block'" {
            tailf:xpath-root 3;
          }
          type uint32 {
            range "0..5";
          }
          must '(../retry-times and ../block-time) or (not(../retry-times) and not(../block-time))' {
            tailf:xpath-root 3;
          }
          description
            "Retry times.";
        }
        leaf block-time {
          when "../action='block'" {
            tailf:xpath-root 3;
          }
          type uint32 {
            range "10..65535";
          }
          units "s";
          must '(../retry-times and ../block-time) or (not(../retry-times) and not(../block-time))' {
            tailf:xpath-root 3;
          }
          description
            "Blocking time.";
        }
      }
      container precise-block {
        presence "precise-block";
        description
          "Configure precise blocking policy table.";
      }
    }
  }

  augment "/ncs:devices/ncs:device/ncs:config" {
    container mac-flapping {
      tailf:ncs-device-type "netconf";
      tailf:display-when "not(../../ncs:module) or ../../ncs:module[ncs:name='huawei-mac-flapping']";
      description
        "MAC flapping-based loop detection.";
      container global-attribute {
        description
          "Configure global attribute of MFLP.";
        leaf precise-block-policy {
          type mflp-enable;
          default "disable";
          description
            "Global blocking policy.";
        }
        leaf generate-time {
          type uint32 {
            range "60..2000000";
          }
          units "s";
          default "600";
          description
            "Trust interface generation time.";
        }
        leaf assist-stp {
          type mflp-enable;
          default "disable";
          description
            "MAC flapping assist flag.";
        }
        leaf traffic-suppression {
          type mflp-enable;
          default "enable";
          description
            "Global traffic suppress state.";
        }
        leaf traffic-suppression-threshold {
          type uint16 {
            range "10..50";
          }
          units "%";
          default "10";
          description
            "Traffic suppress threshold.";
        }
      }
    }
  }
  augment "/ncs:devices/ncs:device/ncs:live-status" {
    container mac-flapping {
      tailf:ncs-device-type "netconf";
      tailf:display-when "not(../../ncs:module) or ../../ncs:module[ncs:name='huawei-mac-flapping'] or (../../ncs:live-status-protocol[not(ncs:capability)]) or (../../ncs:live-status-protocol/ncs:capability/ncs:module[.='huawei-mac-flapping'])";
      description
        "MAC flapping-based loop detection.";
      container global-attribute {
        description
          "Configure global attribute of MFLP.";
        leaf precise-block-policy {
          type live_ncs_mflp-enable;
          // NCS drop default statement
          description
            "Global blocking policy.";
        }
        leaf generate-time {
          type uint32 {
            range "60..2000000";
          }
          units "s";
          // NCS drop default statement
          description
            "Trust interface generation time.";
        }
        leaf assist-stp {
          type live_ncs_mflp-enable;
          // NCS drop default statement
          description
            "MAC flapping assist flag.";
        }
        leaf traffic-suppression {
          type live_ncs_mflp-enable;
          // NCS drop default statement
          description
            "Global traffic suppress state.";
        }
        leaf traffic-suppression-threshold {
          type uint16 {
            range "10..50";
          }
          units "%";
          // NCS drop default statement
          description
            "Traffic suppress threshold.";
        }
      }
    }
  }
  augment "/ncs:devices/ncs:template/ncs:ned-id/ncs:config" {
    container mac-flapping {
      description
        "MAC flapping-based loop detection.";
      container global-attribute {
        description
          "Configure global attribute of MFLP.";
        leaf precise-block-policy {
          type ncs_template_mflp-enable;
          // NCS drop default statement
          description
            "Global blocking policy.";
        }
        leaf generate-time {
          type string;
          units "s";
          // NCS drop default statement
          description
            "Trust interface generation time.";
        }
        leaf assist-stp {
          type ncs_template_mflp-enable;
          // NCS drop default statement
          description
            "MAC flapping assist flag.";
        }
        leaf traffic-suppression {
          type ncs_template_mflp-enable;
          // NCS drop default statement
          description
            "Global traffic suppress state.";
        }
        leaf traffic-suppression-threshold {
          type string;
          units "%";
          // NCS drop default statement
          description
            "Traffic suppress threshold.";
        }
      }
    }
  }
  augment "/ncs:devices/ncs:template/ncs:ned-id/ncs:config/l2vpn:l2vpn/l2vpn:instances/l2vpn:instance/l2vpn:vpls" {
    description
      "MAC flapping patameters on VSI.";
    // NCS expand uses statement
    container mac-flapping {
      description
        "Configure MAC flapping.";
      container loop-detect {
        presence "Loop detect configuration.";
        description
          "Configure VSI MAC flapping entry.";
        leaf loop-times {
          type string;
          // NCS drop mandatory statement
          description
            "Number of MAC address flappings.";
        }
        leaf detect-cycle {
          type string;
          units "s";
          // NCS drop mandatory statement
          description
            "Detection cycle.";
        }
        leaf cycles {
          type string;
          // NCS drop mandatory statement
          description
            "Number of cycles.";
        }
        leaf action {
          type ncs_template_alarm-enable;
          // NCS drop mandatory statement
          description
            "Action taken after a loop occurs. The action can be reporting an alarm or blocking an interface.";
        }
        leaf retry-times {
          // NCS drop when statement
          type string;
          // NCS drop must statement
          description
            "Retry times.";
        }
        leaf block-time {
          // NCS drop when statement
          type string;
          units "s";
          // NCS drop must statement
          description
            "Blocking time.";
        }
      }
      container precise-block {
        presence "precise-block";
        description
          "Configure precise blocking policy table.";
        // NCS drop must statement
      }
    }
  }
  augment "/ncs:devices/ncs:device/ncs:live-status/l2vpn:l2vpn/l2vpn:instances/l2vpn:instance/l2vpn:vpls" {
    description
      "MAC flapping patameters on VSI.";
    // NCS expand uses statement
    container mac-flapping {
      description
        "Configure MAC flapping.";
      container loop-detect {
        presence "Loop detect configuration.";
        description
          "Configure VSI MAC flapping entry.";
        leaf loop-times {
          type uint32 {
            range "3..1000";
          }
          // NCS drop mandatory statement
          description
            "Number of MAC address flappings.";
        }
        leaf detect-cycle {
          type uint32 {
            range "3..30";
          }
          units "s";
          // NCS drop mandatory statement
          description
            "Detection cycle.";
        }
        leaf cycles {
          type uint32 {
            range "1..15";
          }
          // NCS drop mandatory statement
          description
            "Number of cycles.";
        }
        leaf action {
          type live_ncs_alarm-enable;
          // NCS drop mandatory statement
          description
            "Action taken after a loop occurs. The action can be reporting an alarm or blocking an interface.";
        }
        leaf retry-times {
          // NCS drop when statement
          type uint32 {
            range "0..5";
          }
          // NCS drop must statement
          description
            "Retry times.";
        }
        leaf block-time {
          // NCS drop when statement
          type uint32 {
            range "10..65535";
          }
          units "s";
          // NCS drop must statement
          description
            "Blocking time.";
        }
      }
      container precise-block {
        presence "precise-block";
        description
          "Configure precise blocking policy table.";
        // NCS drop must statement
      }
    }
  }
  augment "/ncs:devices/ncs:device/ncs:config/l2vpn:l2vpn/l2vpn:instances/l2vpn:instance/l2vpn:vpls" {
    description
      "MAC flapping patameters on VSI.";
    // NCS expand uses statement
    container mac-flapping {
      description
        "Configure MAC flapping.";
      container loop-detect {
        presence "Loop detect configuration.";
        description
          "Configure VSI MAC flapping entry.";
        leaf loop-times {
          type uint32 {
            range "3..1000";
          }
          mandatory true;
          description
            "Number of MAC address flappings.";
        }
        leaf detect-cycle {
          type uint32 {
            range "3..30";
          }
          units "s";
          mandatory true;
          description
            "Detection cycle.";
        }
        leaf cycles {
          type uint32 {
            range "1..15";
          }
          mandatory true;
          description
            "Number of cycles.";
        }
        leaf action {
          type alarm-enable;
          mandatory true;
          description
            "Action taken after a loop occurs. The action can be reporting an alarm or blocking an interface.";
        }
        leaf retry-times {
          when "../action='block'" {
            tailf:xpath-root 3;
          }
          type uint32 {
            range "0..5";
          }
          must '(../retry-times and ../block-time) or (not(../retry-times) and not(../block-time))' {
            tailf:xpath-root 3;
          }
          description
            "Retry times.";
        }
        leaf block-time {
          when "../action='block'" {
            tailf:xpath-root 3;
          }
          type uint32 {
            range "10..65535";
          }
          units "s";
          must '(../retry-times and ../block-time) or (not(../retry-times) and not(../block-time))' {
            tailf:xpath-root 3;
          }
          description
            "Blocking time.";
        }
      }
      container precise-block {
        presence "precise-block";
        description
          "Configure precise blocking policy table.";
        must "../../l2vpn:work-mode='normal'" {
          tailf:xpath-root 3;
        }
      }
    }
  }
  augment "/ncs:devices/ncs:template/ncs:ned-id/ncs:config/bd:bd/bd:instances/bd:instance" {
    description
      "MAC flapping patameters on BD.";
    // NCS expand uses statement
    container mac-flapping {
      description
        "Configure MAC flapping.";
      container loop-detect {
        presence "Loop detect configuration.";
        leaf loop-times {
          type string;
          // NCS drop mandatory statement
          description
            "Number of MAC address flappings.";
        }
        leaf detect-cycle {
          type string;
          units "s";
          // NCS drop mandatory statement
          description
            "Detection cycle.";
        }
        leaf cycles {
          type string;
          // NCS drop mandatory statement
          description
            "Number of cycles.";
        }
        leaf action {
          type ncs_template_alarm-enable;
          // NCS drop mandatory statement
          description
            "Action taken after a loop occurs. The action can be reporting an alarm or blocking an interface.";
        }
        leaf retry-times {
          // NCS drop when statement
          type string;
          // NCS drop must statement
          description
            "Retry times.";
        }
        leaf block-time {
          // NCS drop when statement
          type string;
          units "s";
          // NCS drop must statement
          description
            "Blocking time.";
        }
        description
          "Configure BD MAC flapping entry.";
      }
      container precise-block {
        presence "precise-block";
        description
          "Configure precise blocking policy table.";
      }
    }
  }
  augment "/ncs:devices/ncs:device/ncs:live-status/bd:bd/bd:instances/bd:instance" {
    description
      "MAC flapping patameters on BD.";
    // NCS expand uses statement
    container mac-flapping {
      description
        "Configure MAC flapping.";
      container loop-detect {
        presence "Loop detect configuration.";
        leaf loop-times {
          type uint32 {
            range "3..1000";
          }
          // NCS drop mandatory statement
          description
            "Number of MAC address flappings.";
        }
        leaf detect-cycle {
          type uint32 {
            range "3..30";
          }
          units "s";
          // NCS drop mandatory statement
          description
            "Detection cycle.";
        }
        leaf cycles {
          type uint32 {
            range "1..15";
          }
          // NCS drop mandatory statement
          description
            "Number of cycles.";
        }
        leaf action {
          type live_ncs_alarm-enable;
          // NCS drop mandatory statement
          description
            "Action taken after a loop occurs. The action can be reporting an alarm or blocking an interface.";
        }
        leaf retry-times {
          // NCS drop when statement
          type uint32 {
            range "0..5";
          }
          // NCS drop must statement
          description
            "Retry times.";
        }
        leaf block-time {
          // NCS drop when statement
          type uint32 {
            range "10..65535";
          }
          units "s";
          // NCS drop must statement
          description
            "Blocking time.";
        }
        description
          "Configure BD MAC flapping entry.";
      }
      container precise-block {
        presence "precise-block";
        description
          "Configure precise blocking policy table.";
      }
    }
  }
  augment "/ncs:devices/ncs:device/ncs:config/bd:bd/bd:instances/bd:instance" {
    description
      "MAC flapping patameters on BD.";
    // NCS expand uses statement
    container mac-flapping {
      description
        "Configure MAC flapping.";
      container loop-detect {
        presence "Loop detect configuration.";
        leaf loop-times {
          type uint32 {
            range "3..1000";
          }
          mandatory true;
          description
            "Number of MAC address flappings.";
        }
        leaf detect-cycle {
          type uint32 {
            range "3..30";
          }
          units "s";
          mandatory true;
          description
            "Detection cycle.";
        }
        leaf cycles {
          type uint32 {
            range "1..15";
          }
          mandatory true;
          description
            "Number of cycles.";
        }
        leaf action {
          type alarm-enable;
          mandatory true;
          description
            "Action taken after a loop occurs. The action can be reporting an alarm or blocking an interface.";
        }
        leaf retry-times {
          when "../action='block'" {
            tailf:xpath-root 3;
          }
          type uint32 {
            range "0..5";
          }
          must '(../retry-times and ../block-time) or (not(../retry-times) and not(../block-time))' {
            tailf:xpath-root 3;
          }
          description
            "Retry times.";
        }
        leaf block-time {
          when "../action='block'" {
            tailf:xpath-root 3;
          }
          type uint32 {
            range "10..65535";
          }
          units "s";
          must '(../retry-times and ../block-time) or (not(../retry-times) and not(../block-time))' {
            tailf:xpath-root 3;
          }
          description
            "Blocking time.";
        }
        description
          "Configure BD MAC flapping entry.";
      }
      container precise-block {
        presence "precise-block";
        description
          "Configure precise blocking policy table.";
      }
    }
  }
  augment "/ncs:devices/ncs:template/ncs:ned-id/ncs:config/vlan:vlan/vlan:vlans/vlan:vlan" {
    description
      "MAC flapping patameters on VLAN.";
    // NCS expand uses statement
    container mac-flapping {
      description
        "Configure MAC flapping.";
      container loop-detect {
        presence "Loop detect configuration.";
        leaf loop-times {
          type string;
          // NCS drop mandatory statement
          description
            "Number of MAC address flappings.";
        }
        leaf detect-cycle {
          type string;
          units "s";
          // NCS drop mandatory statement
          description
            "Detection cycle.";
        }
        leaf cycles {
          type string;
          // NCS drop mandatory statement
          description
            "Number of cycles.";
        }
        leaf action {
          type ncs_template_alarm-enable;
          // NCS drop mandatory statement
          description
            "Action taken after a loop occurs. The action can be reporting an alarm or blocking an interface.";
        }
        leaf retry-times {
          // NCS drop when statement
          type string;
          // NCS drop must statement
          description
            "Retry times.";
        }
        leaf block-time {
          // NCS drop when statement
          type string;
          units "s";
          // NCS drop must statement
          description
            "Blocking time.";
        }
        description
          "Configure VLAN MAC flapping entry.";
      }
      container precise-block {
        presence "precise-block";
        description
          "Configure precise blocking policy table.";
      }
    }
  }
  augment "/ncs:devices/ncs:device/ncs:live-status/vlan:vlan/vlan:vlans/vlan:vlan" {
    description
      "MAC flapping patameters on VLAN.";
    // NCS expand uses statement
    container mac-flapping {
      description
        "Configure MAC flapping.";
      container loop-detect {
        presence "Loop detect configuration.";
        leaf loop-times {
          type uint32 {
            range "3..1000";
          }
          // NCS drop mandatory statement
          description
            "Number of MAC address flappings.";
        }
        leaf detect-cycle {
          type uint32 {
            range "3..30";
          }
          units "s";
          // NCS drop mandatory statement
          description
            "Detection cycle.";
        }
        leaf cycles {
          type uint32 {
            range "1..15";
          }
          // NCS drop mandatory statement
          description
            "Number of cycles.";
        }
        leaf action {
          type live_ncs_alarm-enable;
          // NCS drop mandatory statement
          description
            "Action taken after a loop occurs. The action can be reporting an alarm or blocking an interface.";
        }
        leaf retry-times {
          // NCS drop when statement
          type uint32 {
            range "0..5";
          }
          // NCS drop must statement
          description
            "Retry times.";
        }
        leaf block-time {
          // NCS drop when statement
          type uint32 {
            range "10..65535";
          }
          units "s";
          // NCS drop must statement
          description
            "Blocking time.";
        }
        description
          "Configure VLAN MAC flapping entry.";
      }
      container precise-block {
        presence "precise-block";
        description
          "Configure precise blocking policy table.";
      }
    }
  }
  augment "/ncs:devices/ncs:device/ncs:config/vlan:vlan/vlan:vlans/vlan:vlan" {
    description
      "MAC flapping patameters on VLAN.";
    // NCS expand uses statement
    container mac-flapping {
      description
        "Configure MAC flapping.";
      container loop-detect {
        presence "Loop detect configuration.";
        leaf loop-times {
          type uint32 {
            range "3..1000";
          }
          mandatory true;
          description
            "Number of MAC address flappings.";
        }
        leaf detect-cycle {
          type uint32 {
            range "3..30";
          }
          units "s";
          mandatory true;
          description
            "Detection cycle.";
        }
        leaf cycles {
          type uint32 {
            range "1..15";
          }
          mandatory true;
          description
            "Number of cycles.";
        }
        leaf action {
          type alarm-enable;
          mandatory true;
          description
            "Action taken after a loop occurs. The action can be reporting an alarm or blocking an interface.";
        }
        leaf retry-times {
          when "../action='block'" {
            tailf:xpath-root 3;
          }
          type uint32 {
            range "0..5";
          }
          must '(../retry-times and ../block-time) or (not(../retry-times) and not(../block-time))' {
            tailf:xpath-root 3;
          }
          description
            "Retry times.";
        }
        leaf block-time {
          when "../action='block'" {
            tailf:xpath-root 3;
          }
          type uint32 {
            range "10..65535";
          }
          units "s";
          must '(../retry-times and ../block-time) or (not(../retry-times) and not(../block-time))' {
            tailf:xpath-root 3;
          }
          description
            "Blocking time.";
        }
        description
          "Configure VLAN MAC flapping entry.";
      }
      container precise-block {
        presence "precise-block";
        description
          "Configure precise blocking policy table.";
      }
    }
  }
  augment "/ncs:devices/ncs:template/ncs:ned-id/ncs:config/ifm:ifm/ifm:interfaces/ifm:interface/ethernet:ethernet/ethernet:main-interface" {
    description
      "MAC flapping patameters on the interface.";
    container mflp-mac-shift {
      presence "mflp mac shift";
      description
        "Configure MAC flapping-based loop detection association on an interface.";
    }
  }
  augment "/ncs:devices/ncs:device/ncs:live-status/ifm:ifm/ifm:interfaces/ifm:interface/ethernet:ethernet/ethernet:main-interface" {
    description
      "MAC flapping patameters on the interface.";
    container mflp-mac-shift {
      tailf:ncs-device-type "netconf";
      tailf:display-when "not(../../../../../../../ncs:module) or ../../../../../../../ncs:module[ncs:name='huawei-mac-flapping'] or (../../../../../../../ncs:live-status-protocol[not(ncs:capability)]) or (../../../../../../../ncs:live-status-protocol/ncs:capability/ncs:module[.='huawei-mac-flapping'])";
      presence "mflp mac shift";
      description
        "Configure MAC flapping-based loop detection association on an interface.";
    }
  }
  augment "/ncs:devices/ncs:device/ncs:config/ifm:ifm/ifm:interfaces/ifm:interface/ethernet:ethernet/ethernet:main-interface" {
    description
      "MAC flapping patameters on the interface.";
    container mflp-mac-shift {
      tailf:ncs-device-type "netconf";
      tailf:display-when "not(../../../../../../../ncs:module) or ../../../../../../../ncs:module[ncs:name='huawei-mac-flapping']";
      presence "mflp mac shift";
      description
        "Configure MAC flapping-based loop detection association on an interface.";
    }
  }
}
