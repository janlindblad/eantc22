module huawei-bfd-static-mpls-te {
  // Generated by yanger -t ncs
  tailf:mount-id "huawei-nc-1.0:huawei-nc-1.0";
  tailf:ncs-device-type "netconf";

  yang-version 1;
  namespace "urn:huawei:yang:huawei-bfd-static-mpls-te";
  prefix bfd-static-mpls-te;

  import huawei-bfd {
    prefix bfd;
  }
  import huawei-ifm {
    prefix ifm;
  }
  import huawei-tunnel-management {
    prefix tnlm;
  }
  import huawei-mpls-te {
    prefix mpls-te;
  }
  import ietf-inet-types {
    prefix inet;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Bidirectional Forwarding Detection (BFD) is a detection mechanism used uniformly on the entire network. BFD is used to rapidly detect and monitor the connectivity of links or IP routes on a network.";

  revision 2020-05-30 {
    description
      "Modify the range of reverse-tunnel-id nodes.";
    reference "Huawei private.";
  }
  revision 2020-03-13 {
    description
      "Modify description.";
    reference "Huawei private.";
  }
  revision 2019-12-30 {
    description
      "Units correct.";
    reference "Huawei private.";
  }
  revision 2019-11-25 {
    description
      "Add sr-bit-err-det-static-te-lsp.";
    reference "Huawei private.";
  }
  revision 2019-06-25 {
    description
      "Initial revision.";
    reference "Huawei private.";
  }
  ext:task-name "bfd";

  augment "/ncs:devices/ncs:template/ncs:ned-id/ncs:config/bfd:bfd/bfd:sessions/bfd:session/bfd:session-type/bfd:static/bfd:static-session-link-type" {
    description
      "Configure BFD for MPLS TE.";
    case te-lsp {
      description
        "List of BFD static session configurations for TE-LSP.";
      leaf min-tx-interval-static-te-lsp {
        // NCS drop when statement
        type string;
        units "ms";
        // NCS drop default statement
        description
          "Minimum interval between sending packets.";
      }
      leaf min-rx-interval-static-te-lsp {
        // NCS drop when statement
        type string;
        units "ms";
        // NCS drop default statement
        description
          "Minimum interval between receiving packets.";
      }
      leaf min-echo-rx-interval-static-te-lsp {
        // NCS drop when statement
        type string;
        units "ms";
        // NCS drop default statement
        description
          "Minimum interval between receiving one-arm echo session packets.";
      }
      leaf local-discriminator-static-te-lsp {
        // NCS drop when statement
        type string;
        description
          "Local discriminator of a BFD session. Note that the local discriminator must correspond to the remote discriminator on the peer of the BFD session.";
      }
      leaf remote-discriminator-static-te-lsp {
        // NCS drop when statement
        type string;
        description
          "Remote discriminator of a BFD session. Note that the remote discriminator must correspond to the local discriminator on the peer of the BFD session.";
      }
      leaf tunnel-name-static-te-lsp {
        type string;
        // NCS drop must statement
        // NCS drop mandatory statement
        description
          "Name of a RSVP TE tunnel.";
      }
      leaf te-backup-lsp-static-te-lsp {
        type string;
        // NCS drop default statement
        description
          "Enable/disable the LSP to be the primary LSP in a tunnel.";
      }
      leaf one-arm-echo-static-te-lsp {
        type string;
        // NCS drop default statement
        description
          "Enable/disable echo session in one-arm mode, one-arm-echo must be configured for one-arm session type.";
      }
      leaf is-group-static-te-lsp {
        type string;
        // NCS drop default statement
        description
          "Enable/disable Session Group.";
      }
      leaf process-pst-static-te-lsp {
        type string;
        // NCS drop default statement
        description
          "Enable/disable to update the PST when the status of a BFD session changes. On each interface, only one BFD session can be set for this parameter.";
      }
      leaf sr-bit-err-det-static-te-lsp {
        type string;
        // NCS drop default statement
        description
          "Enable/disable bit error dectection only used for SR-TE LSP.";
      }
    }
    case te-tunnel {
      description
        "List of BFD static session configurations for TE-tunnel.";
      leaf min-tx-interval-static-te-tunnel {
        // NCS drop when statement
        type string;
        units "ms";
        // NCS drop default statement
        description
          "Minimum interval between sending packets, which is set for a BFD session.";
      }
      leaf min-rx-interval-static-te-tunnel {
        // NCS drop when statement
        type string;
        units "ms";
        // NCS drop default statement
        description
          "Minimum interval between receiving packets, which is set for a BFD session.";
      }
      leaf min-echo-rx-interval-static-te-tunnel {
        // NCS drop when statement
        type string;
        units "ms";
        // NCS drop default statement
        description
          "Minimum interval between receiving one-arm echo session packets.";
      }
      leaf local-discriminator-static-te-tunnel {
        // NCS drop when statement
        type string;
        description
          "Local discriminator of a BFD session. Note that the local discriminator must correspond to the remote discriminator on the peer of the BFD session.";
      }
      leaf remote-discriminator-static-te-tunnel {
        // NCS drop when statement
        type string;
        description
          "Remote discriminator of a BFD session. Note that the remote discriminator must correspond to the local discriminator on the peer of the BFD session.";
      }
      leaf tunnel-name-static-te-tunnel {
        type string;
        // NCS drop must statement
        // NCS drop mandatory statement
        description
          "Name of a TE tunnel.";
      }
      leaf one-arm-echo-static-te-tunnel {
        type string;
        // NCS drop default statement
        description
          "Enable/disable echo session in one-arm mode, one-arm-echo must be configured for one-arm session type.";
      }
      leaf select-board-slot-static-te-tunnel {
        type string;
        description
          "ID of the slot for forcible board selection.";
      }
      leaf is-group-static-te-tunnel {
        type string;
        // NCS drop default statement
        description
          "Enable/disable session group.";
      }
      leaf process-pst-static-te-tunnel {
        type string;
        // NCS drop default statement
        description
          "Enable/disable to update the PST when the status of a BFD session changes. On each interface, only one BFD session can be set for this parameter.";
      }
    }
  }
  augment "/ncs:devices/ncs:device/ncs:live-status/bfd:bfd/bfd:sessions/bfd:session/bfd:session-type/bfd:static/bfd:static-session-link-type" {
    description
      "Configure BFD for MPLS TE.";
    case te-lsp {
      description
        "List of BFD static session configurations for TE-LSP.";
      leaf min-tx-interval-static-te-lsp {
        // NCS drop when statement
        type uint32 {
          range "3..20000";
        }
        units "ms";
        // NCS drop default statement
        description
          "Minimum interval between sending packets.";
      }
      leaf min-rx-interval-static-te-lsp {
        // NCS drop when statement
        type uint32 {
          range "3..20000";
        }
        units "ms";
        // NCS drop default statement
        description
          "Minimum interval between receiving packets.";
      }
      leaf min-echo-rx-interval-static-te-lsp {
        // NCS drop when statement
        type uint32 {
          range "3..20000";
        }
        units "ms";
        // NCS drop default statement
        description
          "Minimum interval between receiving one-arm echo session packets.";
      }
      leaf local-discriminator-static-te-lsp {
        // NCS drop when statement
        type uint32 {
          range "1..16384";
        }
        description
          "Local discriminator of a BFD session. Note that the local discriminator must correspond to the remote discriminator on the peer of the BFD session.";
      }
      leaf remote-discriminator-static-te-lsp {
        // NCS drop when statement
        type uint32 {
          range "1..4294967295";
        }
        description
          "Remote discriminator of a BFD session. Note that the remote discriminator must correspond to the local discriminator on the peer of the BFD session.";
      }
      leaf tunnel-name-static-te-lsp {
        type leafref {
          path "/ncs:devices/ncs:device/ncs:live-status/ifm:ifm/ifm:interfaces/ifm:interface/ifm:name" {
            tailf:xpath-root 3;
          }
        }
        // NCS drop must statement
        // NCS drop mandatory statement
        description
          "Name of a RSVP TE tunnel.";
      }
      leaf te-backup-lsp-static-te-lsp {
        type boolean;
        // NCS drop default statement
        description
          "Enable/disable the LSP to be the primary LSP in a tunnel.";
      }
      leaf one-arm-echo-static-te-lsp {
        type boolean;
        // NCS drop default statement
        description
          "Enable/disable echo session in one-arm mode, one-arm-echo must be configured for one-arm session type.";
      }
      leaf is-group-static-te-lsp {
        type boolean;
        // NCS drop default statement
        description
          "Enable/disable Session Group.";
      }
      leaf process-pst-static-te-lsp {
        type boolean;
        // NCS drop default statement
        description
          "Enable/disable to update the PST when the status of a BFD session changes. On each interface, only one BFD session can be set for this parameter.";
      }
      leaf sr-bit-err-det-static-te-lsp {
        type boolean;
        // NCS drop default statement
        description
          "Enable/disable bit error dectection only used for SR-TE LSP.";
      }
    }
    case te-tunnel {
      description
        "List of BFD static session configurations for TE-tunnel.";
      leaf min-tx-interval-static-te-tunnel {
        // NCS drop when statement
        type uint32 {
          range "3..20000";
        }
        units "ms";
        // NCS drop default statement
        description
          "Minimum interval between sending packets, which is set for a BFD session.";
      }
      leaf min-rx-interval-static-te-tunnel {
        // NCS drop when statement
        type uint32 {
          range "3..20000";
        }
        units "ms";
        // NCS drop default statement
        description
          "Minimum interval between receiving packets, which is set for a BFD session.";
      }
      leaf min-echo-rx-interval-static-te-tunnel {
        // NCS drop when statement
        type uint32 {
          range "3..20000";
        }
        units "ms";
        // NCS drop default statement
        description
          "Minimum interval between receiving one-arm echo session packets.";
      }
      leaf local-discriminator-static-te-tunnel {
        // NCS drop when statement
        type uint32 {
          range "1..16384";
        }
        description
          "Local discriminator of a BFD session. Note that the local discriminator must correspond to the remote discriminator on the peer of the BFD session.";
      }
      leaf remote-discriminator-static-te-tunnel {
        // NCS drop when statement
        type uint32 {
          range "1..4294967295";
        }
        description
          "Remote discriminator of a BFD session. Note that the remote discriminator must correspond to the local discriminator on the peer of the BFD session.";
      }
      leaf tunnel-name-static-te-tunnel {
        type leafref {
          path "/ncs:devices/ncs:device/ncs:live-status/ifm:ifm/ifm:interfaces/ifm:interface/ifm:name" {
            tailf:xpath-root 3;
          }
        }
        // NCS drop must statement
        // NCS drop mandatory statement
        description
          "Name of a TE tunnel.";
      }
      leaf one-arm-echo-static-te-tunnel {
        type boolean;
        // NCS drop default statement
        description
          "Enable/disable echo session in one-arm mode, one-arm-echo must be configured for one-arm session type.";
      }
      leaf select-board-slot-static-te-tunnel {
        type string {
          length "1..31";
        }
        description
          "ID of the slot for forcible board selection.";
      }
      leaf is-group-static-te-tunnel {
        type boolean;
        // NCS drop default statement
        description
          "Enable/disable session group.";
      }
      leaf process-pst-static-te-tunnel {
        type boolean;
        // NCS drop default statement
        description
          "Enable/disable to update the PST when the status of a BFD session changes. On each interface, only one BFD session can be set for this parameter.";
      }
    }
  }
  augment "/ncs:devices/ncs:device/ncs:config/bfd:bfd/bfd:sessions/bfd:session/bfd:session-type/bfd:static/bfd:static-session-link-type" {
    description
      "Configure BFD for MPLS TE.";
    case te-lsp {
      description
        "List of BFD static session configurations for TE-LSP.";
      leaf min-tx-interval-static-te-lsp {
        when "../one-arm-echo-static-te-lsp='false'" {
          tailf:xpath-root 3;
        }
        type uint32 {
          range "3..20000";
        }
        units "ms";
        default "10";
        description
          "Minimum interval between sending packets.";
      }
      leaf min-rx-interval-static-te-lsp {
        when "../one-arm-echo-static-te-lsp='false'" {
          tailf:xpath-root 3;
        }
        type uint32 {
          range "3..20000";
        }
        units "ms";
        default "10";
        description
          "Minimum interval between receiving packets.";
      }
      leaf min-echo-rx-interval-static-te-lsp {
        when "../one-arm-echo-static-te-lsp='true'" {
          tailf:xpath-root 3;
        }
        type uint32 {
          range "3..20000";
        }
        units "ms";
        default "10";
        description
          "Minimum interval between receiving one-arm echo session packets.";
      }
      leaf local-discriminator-static-te-lsp {
        when "not(../is-group-static-te-lsp='true')" {
          tailf:xpath-root 3;
        }
        type uint32 {
          range "1..16384";
        }
        description
          "Local discriminator of a BFD session. Note that the local discriminator must correspond to the remote discriminator on the peer of the BFD session.";
      }
      leaf remote-discriminator-static-te-lsp {
        when "not(../is-group-static-te-lsp='true' or ../one-arm-echo-static-te-lsp='true')" {
          tailf:xpath-root 3;
        }
        type uint32 {
          range "1..4294967295";
        }
        description
          "Remote discriminator of a BFD session. Note that the remote discriminator must correspond to the local discriminator on the peer of the BFD session.";
      }
      leaf tunnel-name-static-te-lsp {
        type leafref {
          path "/ncs:devices/ncs:device/ncs:config/ifm:ifm/ifm:interfaces/ifm:interface/ifm:name" {
            tailf:xpath-root 3;
          }
        }
        must '/ifm:ifm/ifm:interfaces/ifm:interface[ifm:name = current()]/tnlm:tunnel-protocol/mpls-te:te-tunnel' {
          tailf:xpath-root 3;
        }
        mandatory true;
        description
          "Name of a RSVP TE tunnel.";
      }
      leaf te-backup-lsp-static-te-lsp {
        type boolean;
        default "false";
        description
          "Enable/disable the LSP to be the primary LSP in a tunnel.";
      }
      leaf one-arm-echo-static-te-lsp {
        type boolean;
        default "false";
        description
          "Enable/disable echo session in one-arm mode, one-arm-echo must be configured for one-arm session type.";
      }
      leaf is-group-static-te-lsp {
        type boolean;
        default "false";
        description
          "Enable/disable Session Group.";
      }
      leaf process-pst-static-te-lsp {
        type boolean;
        default "false";
        description
          "Enable/disable to update the PST when the status of a BFD session changes. On each interface, only one BFD session can be set for this parameter.";
      }
      leaf sr-bit-err-det-static-te-lsp {
        type boolean;
        default "false";
        description
          "Enable/disable bit error dectection only used for SR-TE LSP.";
      }
    }
    case te-tunnel {
      description
        "List of BFD static session configurations for TE-tunnel.";
      leaf min-tx-interval-static-te-tunnel {
        when "../one-arm-echo-static-te-tunnel='false'" {
          tailf:xpath-root 3;
        }
        type uint32 {
          range "3..20000";
        }
        units "ms";
        default "10";
        description
          "Minimum interval between sending packets, which is set for a BFD session.";
      }
      leaf min-rx-interval-static-te-tunnel {
        when "../one-arm-echo-static-te-tunnel='false'" {
          tailf:xpath-root 3;
        }
        type uint32 {
          range "3..20000";
        }
        units "ms";
        default "10";
        description
          "Minimum interval between receiving packets, which is set for a BFD session.";
      }
      leaf min-echo-rx-interval-static-te-tunnel {
        when "../one-arm-echo-static-te-tunnel='true'" {
          tailf:xpath-root 3;
        }
        type uint32 {
          range "3..20000";
        }
        units "ms";
        default "10";
        description
          "Minimum interval between receiving one-arm echo session packets.";
      }
      leaf local-discriminator-static-te-tunnel {
        when "not(../is-group-static-te-tunnel='true')" {
          tailf:xpath-root 3;
        }
        type uint32 {
          range "1..16384";
        }
        description
          "Local discriminator of a BFD session. Note that the local discriminator must correspond to the remote discriminator on the peer of the BFD session.";
      }
      leaf remote-discriminator-static-te-tunnel {
        when "not(../is-group-static-te-tunnel='true' or ../one-arm-echo-static-te-tunnel='true')" {
          tailf:xpath-root 3;
        }
        type uint32 {
          range "1..4294967295";
        }
        description
          "Remote discriminator of a BFD session. Note that the remote discriminator must correspond to the local discriminator on the peer of the BFD session.";
      }
      leaf tunnel-name-static-te-tunnel {
        type leafref {
          path "/ncs:devices/ncs:device/ncs:config/ifm:ifm/ifm:interfaces/ifm:interface/ifm:name" {
            tailf:xpath-root 3;
          }
        }
        must '/ifm:ifm/ifm:interfaces/ifm:interface[ifm:name = current()]/tnlm:tunnel-protocol/mpls-te:te-tunnel' {
          tailf:xpath-root 3;
        }
        mandatory true;
        description
          "Name of a TE tunnel.";
      }
      leaf one-arm-echo-static-te-tunnel {
        type boolean;
        default "false";
        description
          "Enable/disable echo session in one-arm mode, one-arm-echo must be configured for one-arm session type.";
      }
      leaf select-board-slot-static-te-tunnel {
        type string {
          length "1..31";
        }
        description
          "ID of the slot for forcible board selection.";
      }
      leaf is-group-static-te-tunnel {
        type boolean;
        default "false";
        description
          "Enable/disable session group.";
      }
      leaf process-pst-static-te-tunnel {
        type boolean;
        default "false";
        description
          "Enable/disable to update the PST when the status of a BFD session changes. On each interface, only one BFD session can be set for this parameter.";
      }
    }
  }
  augment "/ncs:devices/ncs:template/ncs:ned-id/ncs:config/bfd:bfd/bfd:sessions/bfd:session/bfd:session-type/bfd:auto/bfd:auto-session-link-type" {
    description
      "Configure BFD for MPLS TE.";
    case te-lsp {
      description
        "List of BFD auto session configurations for TE-LSP.";
      leaf min-tx-interval-auto-te-lsp {
        type string;
        units "ms";
        // NCS drop default statement
        description
          "Minimum interval between sending packets, which is set for a BFD session.";
      }
      leaf min-rx-interval-auto-te-lsp {
        type string;
        units "ms";
        // NCS drop default statement
        description
          "Minimum interval between receiving packets, which is set for a BFD session.";
      }
      leaf tunnel-name-auto-te-lsp {
        type string;
        // NCS drop must statement
        // NCS drop mandatory statement
        description
          "Name of a RSVP TE tunnel.";
      }
      leaf te-backup-lsp-auto-te-lsp {
        type string;
        // NCS drop default statement
        description
          "Enable/disable the LSP to be the primary LSP in a tunnel. By default, the LSP is the primary LSP. This parameter is available when the type of the detected link is TE LSP.";
      }
      leaf reverse-lsr-id-auto-te-lsp {
        type string;
        // NCS drop mandatory statement
        description
          "Reverse LSR ID.";
      }
      leaf reverse-tunnel-id-auto-te-lsp {
        type string;
        // NCS drop mandatory statement
        description
          "Reverse tunnel ID.";
      }
      leaf process-pst-auto-te-lsp {
        type string;
        // NCS drop default statement
        description
          "Enable/disable to update the PST when the status of a BFD session changes. On each interface, only one BFD session can be set for this parameter.";
      }
    }
    case te-tunnel {
      description
        "List of BFD auto session configurations for TE-tunnel.";
      leaf min-tx-interval-auto-te-tunnel {
        type string;
        units "ms";
        // NCS drop default statement
        description
          "Minimum interval between sending packets, which is set for a BFD session.";
      }
      leaf min-rx-interval-auto-te-tunnel {
        type string;
        units "ms";
        // NCS drop default statement
        description
          "Minimum interval between receiving packets, which is set for a BFD session.";
      }
      leaf tunnel-name-auto-te-tunnel {
        type string;
        // NCS drop must statement
        // NCS drop mandatory statement
        description
          "Name of a RSVP TE tunnel.";
      }
      leaf reverse-lsr-id-auto-te-tunnel {
        type string;
        // NCS drop mandatory statement
        description
          "Reverse LSR ID.";
      }
      leaf reverse-tunnel-id-auto-te-tunnel {
        type string;
        // NCS drop mandatory statement
        description
          "Reverse tunnel ID.";
      }
      leaf process-pst-auto-te-tunnel {
        type string;
        // NCS drop default statement
        description
          "Enable/disable to update the PST when the status of a BFD session changes. On each interface, only one BFD session can be set for this parameter.";
      }
    }
  }
  augment "/ncs:devices/ncs:device/ncs:live-status/bfd:bfd/bfd:sessions/bfd:session/bfd:session-type/bfd:auto/bfd:auto-session-link-type" {
    description
      "Configure BFD for MPLS TE.";
    case te-lsp {
      description
        "List of BFD auto session configurations for TE-LSP.";
      leaf min-tx-interval-auto-te-lsp {
        type uint32 {
          range "3..20000";
        }
        units "ms";
        // NCS drop default statement
        description
          "Minimum interval between sending packets, which is set for a BFD session.";
      }
      leaf min-rx-interval-auto-te-lsp {
        type uint32 {
          range "3..20000";
        }
        units "ms";
        // NCS drop default statement
        description
          "Minimum interval between receiving packets, which is set for a BFD session.";
      }
      leaf tunnel-name-auto-te-lsp {
        type leafref {
          path "/ncs:devices/ncs:device/ncs:live-status/ifm:ifm/ifm:interfaces/ifm:interface/ifm:name" {
            tailf:xpath-root 3;
          }
        }
        // NCS drop must statement
        // NCS drop mandatory statement
        description
          "Name of a RSVP TE tunnel.";
      }
      leaf te-backup-lsp-auto-te-lsp {
        type boolean;
        // NCS drop default statement
        description
          "Enable/disable the LSP to be the primary LSP in a tunnel. By default, the LSP is the primary LSP. This parameter is available when the type of the detected link is TE LSP.";
      }
      leaf reverse-lsr-id-auto-te-lsp {
        type inet:ipv4-address-no-zone;
        // NCS drop mandatory statement
        description
          "Reverse LSR ID.";
      }
      leaf reverse-tunnel-id-auto-te-lsp {
        type uint32 {
          range "1..4294967295";
        }
        // NCS drop mandatory statement
        description
          "Reverse tunnel ID.";
      }
      leaf process-pst-auto-te-lsp {
        type boolean;
        // NCS drop default statement
        description
          "Enable/disable to update the PST when the status of a BFD session changes. On each interface, only one BFD session can be set for this parameter.";
      }
    }
    case te-tunnel {
      description
        "List of BFD auto session configurations for TE-tunnel.";
      leaf min-tx-interval-auto-te-tunnel {
        type uint32 {
          range "3..20000";
        }
        units "ms";
        // NCS drop default statement
        description
          "Minimum interval between sending packets, which is set for a BFD session.";
      }
      leaf min-rx-interval-auto-te-tunnel {
        type uint32 {
          range "3..20000";
        }
        units "ms";
        // NCS drop default statement
        description
          "Minimum interval between receiving packets, which is set for a BFD session.";
      }
      leaf tunnel-name-auto-te-tunnel {
        type leafref {
          path "/ncs:devices/ncs:device/ncs:live-status/ifm:ifm/ifm:interfaces/ifm:interface/ifm:name" {
            tailf:xpath-root 3;
          }
        }
        // NCS drop must statement
        // NCS drop mandatory statement
        description
          "Name of a RSVP TE tunnel.";
      }
      leaf reverse-lsr-id-auto-te-tunnel {
        type inet:ipv4-address-no-zone;
        // NCS drop mandatory statement
        description
          "Reverse LSR ID.";
      }
      leaf reverse-tunnel-id-auto-te-tunnel {
        type uint32 {
          range "1..4294967295";
        }
        // NCS drop mandatory statement
        description
          "Reverse tunnel ID.";
      }
      leaf process-pst-auto-te-tunnel {
        type boolean;
        // NCS drop default statement
        description
          "Enable/disable to update the PST when the status of a BFD session changes. On each interface, only one BFD session can be set for this parameter.";
      }
    }
  }
  augment "/ncs:devices/ncs:device/ncs:config/bfd:bfd/bfd:sessions/bfd:session/bfd:session-type/bfd:auto/bfd:auto-session-link-type" {
    description
      "Configure BFD for MPLS TE.";
    case te-lsp {
      description
        "List of BFD auto session configurations for TE-LSP.";
      leaf min-tx-interval-auto-te-lsp {
        type uint32 {
          range "3..20000";
        }
        units "ms";
        default "10";
        description
          "Minimum interval between sending packets, which is set for a BFD session.";
      }
      leaf min-rx-interval-auto-te-lsp {
        type uint32 {
          range "3..20000";
        }
        units "ms";
        default "10";
        description
          "Minimum interval between receiving packets, which is set for a BFD session.";
      }
      leaf tunnel-name-auto-te-lsp {
        type leafref {
          path "/ncs:devices/ncs:device/ncs:config/ifm:ifm/ifm:interfaces/ifm:interface/ifm:name" {
            tailf:xpath-root 3;
          }
        }
        must '/ifm:ifm/ifm:interfaces/ifm:interface[ifm:name = current()]/tnlm:tunnel-protocol/mpls-te:te-tunnel' {
          tailf:xpath-root 3;
        }
        mandatory true;
        description
          "Name of a RSVP TE tunnel.";
      }
      leaf te-backup-lsp-auto-te-lsp {
        type boolean;
        default "false";
        description
          "Enable/disable the LSP to be the primary LSP in a tunnel. By default, the LSP is the primary LSP. This parameter is available when the type of the detected link is TE LSP.";
      }
      leaf reverse-lsr-id-auto-te-lsp {
        type inet:ipv4-address-no-zone;
        mandatory true;
        description
          "Reverse LSR ID.";
      }
      leaf reverse-tunnel-id-auto-te-lsp {
        type uint32 {
          range "1..4294967295";
        }
        mandatory true;
        description
          "Reverse tunnel ID.";
      }
      leaf process-pst-auto-te-lsp {
        type boolean;
        default "false";
        description
          "Enable/disable to update the PST when the status of a BFD session changes. On each interface, only one BFD session can be set for this parameter.";
      }
    }
    case te-tunnel {
      description
        "List of BFD auto session configurations for TE-tunnel.";
      leaf min-tx-interval-auto-te-tunnel {
        type uint32 {
          range "3..20000";
        }
        units "ms";
        default "10";
        description
          "Minimum interval between sending packets, which is set for a BFD session.";
      }
      leaf min-rx-interval-auto-te-tunnel {
        type uint32 {
          range "3..20000";
        }
        units "ms";
        default "10";
        description
          "Minimum interval between receiving packets, which is set for a BFD session.";
      }
      leaf tunnel-name-auto-te-tunnel {
        type leafref {
          path "/ncs:devices/ncs:device/ncs:config/ifm:ifm/ifm:interfaces/ifm:interface/ifm:name" {
            tailf:xpath-root 3;
          }
        }
        must '/ifm:ifm/ifm:interfaces/ifm:interface[ifm:name = current()]/tnlm:tunnel-protocol/mpls-te:te-tunnel' {
          tailf:xpath-root 3;
        }
        mandatory true;
        description
          "Name of a RSVP TE tunnel.";
      }
      leaf reverse-lsr-id-auto-te-tunnel {
        type inet:ipv4-address-no-zone;
        mandatory true;
        description
          "Reverse LSR ID.";
      }
      leaf reverse-tunnel-id-auto-te-tunnel {
        type uint32 {
          range "1..4294967295";
        }
        mandatory true;
        description
          "Reverse tunnel ID.";
      }
      leaf process-pst-auto-te-tunnel {
        type boolean;
        default "false";
        description
          "Enable/disable to update the PST when the status of a BFD session changes. On each interface, only one BFD session can be set for this parameter.";
      }
    }
  }
  augment "/ncs:devices/ncs:template/ncs:ned-id/ncs:config/bfd:bfd/bfd:sessions/bfd:session" {
    description
      "Configure BFD group for MPLS TE.";
    container mpls-te-groups {
      // NCS drop when statement
      description
        "List of BFD sub-session.";
      list mpls-te-group {
        // NCS patched for predictable order
        ordered-by user;
        key "sub-local-discriminator";
        description
          "Configure BFD sub-session.";
        leaf sub-local-discriminator {
          type string;
          description
            "Local discriminator of a BFD session. When the BFD session is created in static auto-negotiation mode, you do not need to set this parameter. Note that the local discriminator must correspond to the remote discriminator on the peer of the BFD session. That is, the value of the local discriminator must be the same as the value of the remote discriminator.";
        }
        leaf sub-remote-discriminator {
          type string;
          // NCS drop mandatory statement
          description
            "Remote discriminator of a BFD session. When the BFD session is created in static auto-negotiation mode, you do not need to set this parameter. Note that the remote discriminator must correspond to the local discriminator on the peer of the BFD session. That is, the value of the remote discriminator must be the same as the value of the local discriminator.";
        }
        leaf sub-select-slot-id {
          type string;
          // NCS drop mandatory statement
          description
            "ID of the slot for forcible board selection.";
        }
      }
    }
  }
  augment "/ncs:devices/ncs:device/ncs:live-status/bfd:bfd/bfd:sessions/bfd:session" {
    description
      "Configure BFD group for MPLS TE.";
    container mpls-te-groups {
      tailf:ncs-device-type "netconf";
      tailf:display-when "not(../../../../../ncs:module) or ../../../../../ncs:module[ncs:name='huawei-bfd-static-mpls-te'] or (../../../../../ncs:live-status-protocol[not(ncs:capability)]) or (../../../../../ncs:live-status-protocol/ncs:capability/ncs:module[.='huawei-bfd-static-mpls-te'])";
      // NCS drop when statement
      description
        "List of BFD sub-session.";
      list mpls-te-group {
        key "sub-local-discriminator";
        description
          "Configure BFD sub-session.";
        leaf sub-local-discriminator {
          type uint32 {
            range "1..16384";
          }
          description
            "Local discriminator of a BFD session. When the BFD session is created in static auto-negotiation mode, you do not need to set this parameter. Note that the local discriminator must correspond to the remote discriminator on the peer of the BFD session. That is, the value of the local discriminator must be the same as the value of the remote discriminator.";
        }
        leaf sub-remote-discriminator {
          type uint32 {
            range "1..4294967295";
          }
          // NCS drop mandatory statement
          description
            "Remote discriminator of a BFD session. When the BFD session is created in static auto-negotiation mode, you do not need to set this parameter. Note that the remote discriminator must correspond to the local discriminator on the peer of the BFD session. That is, the value of the remote discriminator must be the same as the value of the local discriminator.";
        }
        leaf sub-select-slot-id {
          type string {
            length "1..19";
          }
          // NCS drop mandatory statement
          description
            "ID of the slot for forcible board selection.";
        }
      }
    }
  }
  augment "/ncs:devices/ncs:device/ncs:config/bfd:bfd/bfd:sessions/bfd:session" {
    description
      "Configure BFD group for MPLS TE.";
    container mpls-te-groups {
      tailf:ncs-device-type "netconf";
      tailf:display-when "not(../../../../../ncs:module) or ../../../../../ncs:module[ncs:name='huawei-bfd-static-mpls-te']";
      when "../is-group-static-te-lsp='true' or ../is-group-static-te-tunnel='true'" {
        tailf:xpath-root 3;
      }
      description
        "List of BFD sub-session.";
      list mpls-te-group {
        key "sub-local-discriminator";
        description
          "Configure BFD sub-session.";
        leaf sub-local-discriminator {
          type uint32 {
            range "1..16384";
          }
          description
            "Local discriminator of a BFD session. When the BFD session is created in static auto-negotiation mode, you do not need to set this parameter. Note that the local discriminator must correspond to the remote discriminator on the peer of the BFD session. That is, the value of the local discriminator must be the same as the value of the remote discriminator.";
        }
        leaf sub-remote-discriminator {
          type uint32 {
            range "1..4294967295";
          }
          mandatory true;
          description
            "Remote discriminator of a BFD session. When the BFD session is created in static auto-negotiation mode, you do not need to set this parameter. Note that the remote discriminator must correspond to the local discriminator on the peer of the BFD session. That is, the value of the remote discriminator must be the same as the value of the local discriminator.";
        }
        leaf sub-select-slot-id {
          type string {
            length "1..19";
          }
          mandatory true;
          description
            "ID of the slot for forcible board selection.";
        }
      }
    }
  }
}
