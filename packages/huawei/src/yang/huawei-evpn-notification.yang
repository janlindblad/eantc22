/*
Copyright (C) 2019 Huawei Technologies Co., Ltd. All rights reserved.
*/
module huawei-evpn-notification {
  yang-version 1;
  namespace "urn:huawei:yang:huawei-evpn-notification";
  prefix evpn-notification;
  import huawei-extension {
    prefix ext;
  }
  organization
    "Huawei Technologies Co., Ltd.";
  contact
    "Huawei Industrial Base
    Bantian, Longgang
    Shenzhen 518129
    People's Republic of China
    Website: http://www.huawei.com
    Email: support@huawei.com";
  description
    "Notification of EVPN.";
  revision 2019-11-21 {
    description
      "Init revision.";
    reference
      "Huawei private.";
  }
  ext:task-name "evpnbgp";
  notification evpn-etree-mul-err {
    description
      "In an EVPN E-Tree scenario where a CE is dual-homed to PEs, the leaf attributes of the PEs' AC interfaces bound to the EVPN instance were different, causing a traffic loop.";
    leaf evpn-instance-name {
      type string {
          length "1..31";
        }
      description
        "EVPN instance name.";
    }
    leaf interface-name {
      type string {
          length "1..63";
        }
      description
        "Interface name.";
    }
  }
  notification evpn-srv6-modify-arg {
    description
      "The minimum length of the ARG is changed, split horizon function may fail temporarily.";
    leaf last-arg-len {
      type uint32;
      description
        "Last ARG length.";
    }
    leaf current-arg-len {
      type uint32;
      description
        "Current ARG length.";
    }
  }
  notification evpn-discard-route {
    description
      "The EVPN instance discards the newly learned MAC and MAC/IP routes.";
    leaf route-type {
      type string {
        length "1..11";
      }
      description
        "The MAC or MAC/IP route type.";
    }
  }
}
