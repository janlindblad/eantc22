module ciena-pon-ctrl {
  // Generated by yanger -t ncs
  tailf:mount-id "ciena107-nc-1.0:ciena107-nc-1.0";
  tailf:ncs-device-type "netconf";

  namespace "http://www.ciena.com/ns/yang/ciena-pon-ctrl";
  prefix pon-ctrl;

  import ciena-types {
    prefix ciena;
  }
  import ietf-yang-types {
    prefix yang;
  }
  import openconfig-interfaces {
    prefix oc-if;
  }
  import ciena-openconfig-interfaces {
    prefix cn-if;
  }
  import ciena-mef-fp {
    prefix mef-fp;
  }
  import ciena-packet-typedefs {
    prefix cntypes;
  }
  import ietf-inet-types {
    prefix inet;
  }
  import yuma-ncx {
    prefix ncx;
  }
  import tailf-common {
    prefix tailf;
  }
  import tailf-ncs {
    prefix ncs;
  }

  organization
    "Ciena Corporation";
  contact
    "Web URL: http://www.ciena.com/
     E-mail:  yang@ciena.com
     Postal:  7035 Ridge Road
     Hanover, Maryland 21076
     U.S.A.
     Phone:   +1 800-921-1144
     Fax:     +1 410-694-5750";
  description
    "This YANG module defines Ciena's data model for the management of Passive
     Optical Network (PON) devices. This includes Optical Line Terminals (OLTs) and
     subtended Optical Network Units (ONUs).

     Copyright (c) 2021 Ciena Corporation. All rights reserved.

     All information contained herein is, and remains the property of Ciena
     Corporation. Dissemination of this information or reproduction of this
     material is strictly forbidden unless prior written permission is obtained
     from Ciena Corporation.";

  revision 2021-11-05 {
    description
      "Add admin state to ONU configuration.
       Add support for ONU-ID configuration.
       Add support for residential PON configuration.
       Add radius, authentication and dhcp relay state for residential PON.
       Add RPC to get/set in-band management TPID and VID on an OLT.
       Add support for automatic ONU upgrades.
       Add option to control the creation of a flooding link on NNI Networks.
       Add support for UNI Port statistics.
       Add delay and distance measurements to ONU diagnostic data.
       Add authentication and DHCP reset command.
       Add support for ALLOC-ID configuration.
       Clean-up of Residential PON statistics and correction of attribute spelling.
       Add firmware-upgrade-attempts to ONU state.
       Add range restriction to ALLOC-ID and ONU-ID configuration.
       Add support for clear command of expired/failed CPE state entries for authentication and l2-relay.
       Simplify statistics for Radius Server.
       Clean-up of Residential PON state attributes.
       Remove dhcp-sub-option.
       Add new states for Authentication and DHCP. Change cpe-mac to type of yang:mac-address.";
    reference
      "- ITU-T G.987    : 10-Gigabit-capable passive optical networks (XG-PON)
       - ITU-T G.9807.1 : 10-Gigabit-capable symmetric passive optical network (XGS-PON)
       - ITU-T G.988    : ONU management and control interface (OMCI) specification
       - IEEE 802.3av   : 10Gbit/s Ethernet PON (10G EPON) standard
       - RFC 2865       : Remote Authentication Dial In User Service (RADIUS)";
  }
  revision 2020-11-20 {
    description
      "Add ONU cross-connect configuration.
       Add NNI Network state container.
       Add RPC to clear NNI Network statistics.
       Add XCVR data container to UNI Port state.
       Change description of some list containers for better clarity.
       Split UNI Port speed and duplex enums into separate config and state enums.
       Add expected-firmware-version to OLT state.
       Change SLA Profile value ranges to reflect correct values.
       Add uptime to OLT and ONU diagnostic data.";
    reference
      "- ITU-T G.987    : 10-Gigabit-capable passive optical networks (XG-PON)
       - ITU-T G.9807.1 : 10-Gigabit-capable symmetric passive optical network (XGS-PON)
       - ITU-T G.988    : ONU management and control interface (OMCI) specification
       - IEEE 802.3av   : 10Gbit/s Ethernet PON (10G EPON) standard";
  }
  revision 2020-08-20 {
    description
      "Add ONU diagnostic data container.
       Add OLT diagnostic data container.
       Update Datalink configuration to specify 'add-ctag' PCP and VLAN-ID list.
       Add expected-firmware-version to ONU state.";
    reference
      "- ITU-T G.987    : 10-Gigabit-capable passive optical networks (XG-PON)
       - ITU-T G.9807.1 : 10-Gigabit-capable symmetric passive optical network (XGS-PON)
       - IEEE 802.3av   : 10Gbit/s Ethernet PON (10G EPON) standard";
  }
  revision 2020-06-25 {
    description
      "Add ONU UNI port configuration and state containers.
       Add RPC for ONU admission control.
       Add default values for SLA Profile.";
    reference
      "- ITU-T G.987    : 10-Gigabit-capable passive optical networks (XG-PON)
       - ITU-T G.9807.1 : 10-Gigabit-capable symmetric passive optical network (XGS-PON)
       - IEEE 802.3av   : 10Gbit/s Ethernet PON (10G EPON) standard";
  }
  revision 2020-05-04 {
    description
      "Add unknown state to olt-oper-state and onu-oper-state enums";
    reference
      "- ITU-T G.987    : 10-Gigabit-capable passive optical networks (XG-PON)
       - ITU-T G.9807.1 : 10-Gigabit-capable symmetric passive optical network (XGS-PON)
       - IEEE 802.3av   : 10Gbit/s Ethernet PON (10G EPON) standard";
  }
  revision 2020-01-20 {
    description
      "Add RPCs for OLT/ONU firmware upgrade.";
    reference
      "- ITU-T G.987    : 10-Gigabit-capable passive optical networks (XG-PON)
       - ITU-T G.9807.1 : 10-Gigabit-capable symmetric passive optical network (XGS-PON)
       - IEEE 802.3av   : 10Gbit/s Ethernet PON (10G EPON) standard";
  }
  revision 2019-09-16 {
    description
      "Restructure and rename Network configuration objects.";
    reference
      "- ITU-T G.987  : 10-Gigabit-capable passive optical networks (XG-PON)
       - IEEE 802.3av : 10Gbit/s Ethernet PON (10G EPON) standard";
  }
  revision 2019-05-01 {
    description
      "Initial version.";
    reference
      "- ITU-T G.987  : 10-Gigabit-capable passive optical networks (XG-PON)
       - IEEE 802.3av : 10Gbit/s Ethernet PON (10G EPON) standard";
  }

  typedef ncs_template_name-string {
    type string;
    description
      "Name string type.";
  }

  typedef ncs_template_pon-relay-attribute-string {
    type string;
    description
      "PON Relay string for radius, authentication and relay identifier attributes.";
  }

  typedef ncs_template_interface-ref {
    type oc-if:ncs_template_base-interface-ref;
    description
      "L3 Interface reference type.";
  }

  typedef ncs_template_radius-server-ref {
    type string;
    description
      "Radius Server reference leafref type.";
  }

  typedef ncs_template_olt-ref {
    type string;
    description
      "OLT reference leafref type.";
  }

  typedef ncs_template_nni-network-ref {
    type string;
    description
      "NNI Network reference leafref type.";
  }

  typedef ncs_template_onu-ref {
    type string;
    description
      "ONU reference leafref type.";
  }

  typedef ncs_template_datalink-ref {
    type string;
    description
      "Datalink reference leafref type.";
  }

  typedef ncs_template_uni-port-ref {
    type string;
    description
      "UNI Port reference leafref type.";
  }

  typedef ncs_template_sla-profile-ref {
    type string;
    description
      "SLA Profile reference leafref type.";
  }

  typedef ncs_template_inband-management-action {
    type string;
    description
      "In-band management action type.";
  }

  typedef ncs_template_tpid {
    type string;
    description
      "TPID type.";
  }

  typedef ncs_template_pon-mode {
    type string;
    description
      "PON-mode type.";
  }

  typedef ncs_template_encryption-mode {
    type string;
    description
      "Encryption mode type.";
  }

  typedef ncs_template_olt-oper-state {
    type string;
    description
      "OLT operational state type.";
  }

  typedef ncs_template_onu-oper-state {
    type string;
    description
      "ONU operational state type.";
  }

  typedef ncs_template_uni-port-oper-state {
    type string;
    description
      "UNI Port operational state type.";
  }

  typedef ncs_template_radius-server-oper-state {
    type string;
    description
      "Radius server operational state type.";
  }

  typedef ncs_template_dhcp-relay-oper-state {
    type string;
    description
      "DHCP relay operational state type.";
  }

  typedef ncs_template_authentication-oper-state {
    type string;
    description
      "Authentication operational state type.";
  }

  typedef ncs_template_uni-port-speed {
    type string;
    description
      "UNI Port speed type.";
  }

  typedef ncs_template_uni-port-oper-speed {
    type string;
    description
      "UNI Port operational speed type.";
  }

  typedef ncs_template_uni-port-duplex {
    type string;
    description
      "UNI Port duplex type.";
  }

  typedef ncs_template_uni-port-oper-duplex {
    type string;
    description
      "UNI Port operational duplex type.";
  }

  typedef ncs_template_onu-pluggable-xcvr-type {
    type string;
    description
      "ONU pluggable transceiver types as defined
       in ITU-T G.988 Table 9.1.5-1.";
  }

  typedef ncs_template_tag-match-vid {
    type string;
    description
      "VLAN-ID type used for network tag match fields.
       A value of 0 matches on no VLAN tag or a priority tag.
       A value of 65535 matches on any VID value, no VLAN tag or a priority tag.";
  }

  typedef ncs_template_tag-action {
    type string;
    description
      "Tag action type.";
  }

  typedef ncs_rpc_notif_name-string {
    type string {
      length "1..64";
    }
    description
      "Name string type.";
  }

  typedef ncs_rpc_notif_pon-relay-attribute-string {
    type string {
      length "1..255";
    }
    description
      "PON Relay string for radius, authentication and relay identifier attributes.";
  }

  typedef ncs_rpc_notif_interface-ref {
    type oc-if:ncs_rpc_notif_base-interface-ref;
    description
      "L3 Interface reference type.";
  }

  typedef ncs_rpc_notif_radius-server-ref {
    type string;
    description
      "Radius Server reference leafref type.";
  }

  typedef ncs_rpc_notif_olt-ref {
    type string;
    description
      "OLT reference leafref type.";
  }

  typedef ncs_rpc_notif_nni-network-ref {
    type string;
    description
      "NNI Network reference leafref type.";
  }

  typedef ncs_rpc_notif_onu-ref {
    type string;
    description
      "ONU reference leafref type.";
  }

  typedef ncs_rpc_notif_datalink-ref {
    type string;
    description
      "Datalink reference leafref type.";
  }

  typedef ncs_rpc_notif_uni-port-ref {
    type string;
    description
      "UNI Port reference leafref type.";
  }

  typedef ncs_rpc_notif_sla-profile-ref {
    type string;
    description
      "SLA Profile reference leafref type.";
  }

  typedef ncs_rpc_notif_inband-management-action {
    type enumeration {
      enum "get" {
        description
          "In-band management get action.";
      }
      enum "set" {
        description
          "In-band management set action.";
      }
    }
    description
      "In-band management action type.";
  }

  typedef ncs_rpc_notif_tpid {
    type enumeration {
      enum "0x8100" {
        value 33024;
        description
          "TPID 0x8100.";
      }
      enum "0x88a8" {
        value 34984;
        description
          "TPID 0x88a8.";
      }
    }
    description
      "TPID type.";
  }

  typedef ncs_rpc_notif_pon-mode {
    type enumeration {
      enum "xgs-pon" {
        description
          "XGS-PON mode.";
      }
      enum "10g-epon" {
        description
          "10G-EPON mode.";
      }
    }
    description
      "PON-mode type.";
  }

  typedef ncs_rpc_notif_encryption-mode {
    type enumeration {
      enum "disabled" {
        description
          "Encryption is disabled.";
      }
      enum "downstream" {
        description
          "Encryption is enabled in the downstream direction only.";
      }
      enum "bidirectional" {
        description
          "Encryption is enabled bidirectionally.";
      }
    }
    description
      "Encryption mode type.";
  }

  typedef ncs_rpc_notif_olt-oper-state {
    type enumeration {
      enum "active" {
        description
          "OLT is configured and discovered.";
      }
      enum "configured" {
        description
          "OLT is configured/pre-provisioned but not discovered.";
      }
      enum "disabled" {
        description
          "OLT is disabled.";
      }
      enum "unknown" {
        description
          "OLT was previously active or disabled but is no longer discovered.";
      }
    }
    description
      "OLT operational state type.";
  }

  typedef ncs_rpc_notif_onu-oper-state {
    type enumeration {
      enum "registered" {
        description
          "ONU is configured and registered with the OLT.";
      }
      enum "configured" {
        description
          "ONU is configured/pre-provisioned but has not yet registered with the OLT.";
      }
      enum "deregistered" {
        description
          "ONU has deregistered with the OLT.";
      }
      enum "unknown" {
        description
          "ONU state is unknown due to OLT state being unknown.";
      }
      enum "unconfigured" {
        description
          "ONU was discovered but has no corresponding configuration.";
      }
    }
    description
      "ONU operational state type.";
  }

  typedef ncs_rpc_notif_uni-port-oper-state {
    type enumeration {
      enum "up" {
        description
          "UNI Port link state is up.";
      }
      enum "down" {
        description
          "UNI Port link state is down.";
      }
      enum "unknown" {
        description
          "UNI Port link state is unknown.";
      }
    }
    description
      "UNI Port operational state type.";
  }

  typedef ncs_rpc_notif_radius-server-oper-state {
    type enumeration {
      enum "up" {
        description
          "Radius server state is up.";
      }
      enum "down" {
        description
          "Radius server state is down.";
      }
      enum "unknown" {
        description
          "Radius server state is unknown.";
      }
    }
    description
      "Radius server operational state type.";
  }

  typedef ncs_rpc_notif_dhcp-relay-oper-state {
    type enumeration {
      enum "discover" {
        description
          "DHCP relay state is discover (discover packet is sent).";
      }
      enum "offer" {
        description
          "DHCP relay state is offer (offer packet is sent).";
      }
      enum "request" {
        description
          "DHCP relay state is request (request packet is sent).";
      }
      enum "acknowledge" {
        description
          "DHCP relay state is acknowledge (initialization is complete).";
      }
      enum "not-acknowledge" {
        description
          "DHCP relay state is not-acknowledge (requested parameters are unacceptable).";
      }
      enum "decline" {
        description
          "DHCP relay state is decline (network address is in use).";
      }
      enum "release" {
        description
          "DHCP relay state is release (network address is no longer required).";
      }
      enum "inform" {
        description
          "DHCP relay state is inform (network address is manually obtained).";
      }
      enum "forced-renew" {
        description
          "DHCP relay state is forced renew.";
      }
      enum "expired" {
        description
          "DHCP relay state is expired.";
      }
      enum "reset" {
        description
          "DHCP relay state is reset.";
      }
      enum "unknown" {
        description
          "DHCP relay state is unknown.";
      }
    }
    description
      "DHCP relay operational state type.";
  }

  typedef ncs_rpc_notif_authentication-oper-state {
    type enumeration {
      enum "start" {
        description
          "Authentication state is start.";
      }
      enum "request" {
        description
          "Authentication state is request.";
      }
      enum "response" {
        description
          "Authentication state is response.";
      }
      enum "success" {
        description
          "Authentication state is success.";
      }
      enum "failure" {
        description
          "Authentication state is failure.";
      }
      enum "initiate" {
        description
          "Authentication state is initiate.";
      }
      enum "finish" {
        description
          "Authentication state is finish.";
      }
      enum "logoff" {
        description
          "Authentication state is logoff.";
      }
      enum "unknown" {
        description
          "Authentication state is unknown.";
      }
    }
    description
      "Authentication operational state type.";
  }

  typedef ncs_rpc_notif_uni-port-speed {
    type enumeration {
      enum "auto" {
        description
          "Auto-configure speed.";
      }
      enum "10Mb" {
        description
          "10 Mbps.";
      }
      enum "100Mb" {
        description
          "100 Mbps.";
      }
      enum "1Gb" {
        description
          "1 Gbps.";
      }
      enum "2500Mb" {
        description
          "2.5 Gbps.";
      }
      enum "5Gb" {
        description
          "5 Gbps.";
      }
      enum "10Gb" {
        description
          "10 Gbps.";
      }
      enum "25Gb" {
        description
          "25 Gbps.";
      }
      enum "40Gb" {
        description
          "40 Gbps.";
      }
    }
    description
      "UNI Port speed type.";
  }

  typedef ncs_rpc_notif_uni-port-oper-speed {
    type enumeration {
      enum "10Mb" {
        description
          "10 Mbps.";
      }
      enum "100Mb" {
        description
          "100 Mbps.";
      }
      enum "1Gb" {
        description
          "1 Gbps.";
      }
      enum "2500Mb" {
        description
          "2.5 Gbps.";
      }
      enum "5Gb" {
        description
          "5 Gbps.";
      }
      enum "10Gb" {
        description
          "10 Gbps.";
      }
      enum "25Gb" {
        description
          "25 Gbps.";
      }
      enum "40Gb" {
        description
          "40 Gbps.";
      }
      enum "unknown" {
        description
          "UNI Port speed is unknown.";
      }
    }
    description
      "UNI Port operational speed type.";
  }

  typedef ncs_rpc_notif_uni-port-duplex {
    type enumeration {
      enum "auto" {
        description
          "Auto-configure duplex.";
      }
      enum "full" {
        description
          "Full duplex.";
      }
      enum "half" {
        description
          "Half duplex.";
      }
    }
    description
      "UNI Port duplex type.";
  }

  typedef ncs_rpc_notif_uni-port-oper-duplex {
    type enumeration {
      enum "full" {
        description
          "Full duplex.";
      }
      enum "half" {
        description
          "Half duplex.";
      }
      enum "unknown" {
        description
          "UNI Port duplex is unknown.";
      }
    }
    description
      "UNI Port operational duplex type.";
  }

  typedef ncs_rpc_notif_onu-pluggable-xcvr-type {
    type enumeration {
      enum "gigabit-optical-ethernet" {
        description
          "Gigabit Ethernet optical IF.";
      }
      enum "ethernet-base-t" {
        description
          "10/100/1000/2500/5000/10000/25000/40000
           BASE-T Ethernet LAN IF.";
      }
      enum "unknown" {
        description
          "ONU pluggable transceiver type is unknown.";
      }
    }
    description
      "ONU pluggable transceiver types as defined
       in ITU-T G.988 Table 9.1.5-1.";
  }

  typedef ncs_rpc_notif_tag-match-vid {
    type uint32 {
      range "0..4094 | 65535";
    }
    description
      "VLAN-ID type used for network tag match fields.
       A value of 0 matches on no VLAN tag or a priority tag.
       A value of 65535 matches on any VID value, no VLAN tag or a priority tag.";
  }

  typedef ncs_rpc_notif_tag-action {
    type enumeration {
      enum "none" {
        description
          "No modifications will be made to the matched frame.";
      }
      enum "pop" {
        description
          "The outermost VLAN tag(s) will be popped (removed). The
           number of tags popped is specified in the tag-action-pop leaf.";
      }
      enum "stamp" {
        description
          "Stamp the outermost VLAN to either an 802.1ad tag, with the value specified in
           the tag-action-stag leaf, or an 802.1q tag, with the value specified in
           the tag-action-ctag leaf.";
      }
      enum "push" {
        description
          "Push either a new 802.1ad tag, with the value specified in
           the tag-action-stag leaf, or a new 802.1q tag, with the value specified in
           the tag-action-ctag leaf.";
      }
    }
    description
      "Tag action type.";
  }

  typedef live_ncs_name-string {
    type string {
      length "1..64";
    }
    description
      "Name string type.";
  }

  typedef live_ncs_pon-relay-attribute-string {
    type string {
      length "1..255";
    }
    description
      "PON Relay string for radius, authentication and relay identifier attributes.";
  }

  typedef live_ncs_interface-ref {
    type oc-if:live_ncs_base-interface-ref;
    description
      "L3 Interface reference type.";
  }

  typedef live_ncs_radius-server-ref {
    type leafref {
      path "/ncs:devices/ncs:device/ncs:live-status/pon-ctrl:pon-ctrl/pon-ctrl:radius-servers/pon-ctrl:radius-server/pon-ctrl:name" {
        tailf:xpath-root 3;
      }
    }
    description
      "Radius Server reference leafref type.";
  }

  typedef live_ncs_olt-ref {
    type leafref {
      path "/ncs:devices/ncs:device/ncs:live-status/pon-ctrl:pon-ctrl/pon-ctrl:olts/pon-ctrl:olt/pon-ctrl:name" {
        tailf:xpath-root 3;
      }
    }
    description
      "OLT reference leafref type.";
  }

  typedef live_ncs_nni-network-ref {
    type leafref {
      path "/ncs:devices/ncs:device/ncs:live-status/pon-ctrl:pon-ctrl/pon-ctrl:olts/pon-ctrl:olt/pon-ctrl:nni-networks/pon-ctrl:nni-network/pon-ctrl:name" {
        tailf:xpath-root 3;
      }
    }
    description
      "NNI Network reference leafref type.";
  }

  typedef live_ncs_onu-ref {
    type leafref {
      path "/ncs:devices/ncs:device/ncs:live-status/pon-ctrl:pon-ctrl/pon-ctrl:onus/pon-ctrl:onu/pon-ctrl:name" {
        tailf:xpath-root 3;
      }
    }
    description
      "ONU reference leafref type.";
  }

  typedef live_ncs_datalink-ref {
    type leafref {
      path "/ncs:devices/ncs:device/ncs:live-status/pon-ctrl:pon-ctrl/pon-ctrl:onus/pon-ctrl:onu/pon-ctrl:datalinks/pon-ctrl:datalink/pon-ctrl:name" {
        tailf:xpath-root 3;
      }
    }
    description
      "Datalink reference leafref type.";
  }

  typedef live_ncs_uni-port-ref {
    type leafref {
      path "/ncs:devices/ncs:device/ncs:live-status/pon-ctrl:pon-ctrl/pon-ctrl:onus/pon-ctrl:onu/pon-ctrl:uni-ports/pon-ctrl:uni-port/pon-ctrl:name" {
        tailf:xpath-root 3;
      }
    }
    description
      "UNI Port reference leafref type.";
  }

  typedef live_ncs_sla-profile-ref {
    type leafref {
      path "/ncs:devices/ncs:device/ncs:live-status/pon-ctrl:pon-ctrl/pon-ctrl:sla-profiles/pon-ctrl:sla-profile/pon-ctrl:name" {
        tailf:xpath-root 3;
      }
    }
    description
      "SLA Profile reference leafref type.";
  }

  typedef live_ncs_inband-management-action {
    type enumeration {
      enum "get" {
        description
          "In-band management get action.";
      }
      enum "set" {
        description
          "In-band management set action.";
      }
    }
    description
      "In-band management action type.";
  }

  typedef live_ncs_tpid {
    type enumeration {
      enum "0x8100" {
        value 33024;
        description
          "TPID 0x8100.";
      }
      enum "0x88a8" {
        value 34984;
        description
          "TPID 0x88a8.";
      }
    }
    description
      "TPID type.";
  }

  typedef live_ncs_pon-mode {
    type enumeration {
      enum "xgs-pon" {
        description
          "XGS-PON mode.";
      }
      enum "10g-epon" {
        description
          "10G-EPON mode.";
      }
    }
    description
      "PON-mode type.";
  }

  typedef live_ncs_encryption-mode {
    type enumeration {
      enum "disabled" {
        description
          "Encryption is disabled.";
      }
      enum "downstream" {
        description
          "Encryption is enabled in the downstream direction only.";
      }
      enum "bidirectional" {
        description
          "Encryption is enabled bidirectionally.";
      }
    }
    description
      "Encryption mode type.";
  }

  typedef live_ncs_olt-oper-state {
    type enumeration {
      enum "active" {
        description
          "OLT is configured and discovered.";
      }
      enum "configured" {
        description
          "OLT is configured/pre-provisioned but not discovered.";
      }
      enum "disabled" {
        description
          "OLT is disabled.";
      }
      enum "unknown" {
        description
          "OLT was previously active or disabled but is no longer discovered.";
      }
    }
    description
      "OLT operational state type.";
  }

  typedef live_ncs_onu-oper-state {
    type enumeration {
      enum "registered" {
        description
          "ONU is configured and registered with the OLT.";
      }
      enum "configured" {
        description
          "ONU is configured/pre-provisioned but has not yet registered with the OLT.";
      }
      enum "deregistered" {
        description
          "ONU has deregistered with the OLT.";
      }
      enum "unknown" {
        description
          "ONU state is unknown due to OLT state being unknown.";
      }
      enum "unconfigured" {
        description
          "ONU was discovered but has no corresponding configuration.";
      }
    }
    description
      "ONU operational state type.";
  }

  typedef live_ncs_uni-port-oper-state {
    type enumeration {
      enum "up" {
        description
          "UNI Port link state is up.";
      }
      enum "down" {
        description
          "UNI Port link state is down.";
      }
      enum "unknown" {
        description
          "UNI Port link state is unknown.";
      }
    }
    description
      "UNI Port operational state type.";
  }

  typedef live_ncs_radius-server-oper-state {
    type enumeration {
      enum "up" {
        description
          "Radius server state is up.";
      }
      enum "down" {
        description
          "Radius server state is down.";
      }
      enum "unknown" {
        description
          "Radius server state is unknown.";
      }
    }
    description
      "Radius server operational state type.";
  }

  typedef live_ncs_dhcp-relay-oper-state {
    type enumeration {
      enum "discover" {
        description
          "DHCP relay state is discover (discover packet is sent).";
      }
      enum "offer" {
        description
          "DHCP relay state is offer (offer packet is sent).";
      }
      enum "request" {
        description
          "DHCP relay state is request (request packet is sent).";
      }
      enum "acknowledge" {
        description
          "DHCP relay state is acknowledge (initialization is complete).";
      }
      enum "not-acknowledge" {
        description
          "DHCP relay state is not-acknowledge (requested parameters are unacceptable).";
      }
      enum "decline" {
        description
          "DHCP relay state is decline (network address is in use).";
      }
      enum "release" {
        description
          "DHCP relay state is release (network address is no longer required).";
      }
      enum "inform" {
        description
          "DHCP relay state is inform (network address is manually obtained).";
      }
      enum "forced-renew" {
        description
          "DHCP relay state is forced renew.";
      }
      enum "expired" {
        description
          "DHCP relay state is expired.";
      }
      enum "reset" {
        description
          "DHCP relay state is reset.";
      }
      enum "unknown" {
        description
          "DHCP relay state is unknown.";
      }
    }
    description
      "DHCP relay operational state type.";
  }

  typedef live_ncs_authentication-oper-state {
    type enumeration {
      enum "start" {
        description
          "Authentication state is start.";
      }
      enum "request" {
        description
          "Authentication state is request.";
      }
      enum "response" {
        description
          "Authentication state is response.";
      }
      enum "success" {
        description
          "Authentication state is success.";
      }
      enum "failure" {
        description
          "Authentication state is failure.";
      }
      enum "initiate" {
        description
          "Authentication state is initiate.";
      }
      enum "finish" {
        description
          "Authentication state is finish.";
      }
      enum "logoff" {
        description
          "Authentication state is logoff.";
      }
      enum "unknown" {
        description
          "Authentication state is unknown.";
      }
    }
    description
      "Authentication operational state type.";
  }

  typedef live_ncs_uni-port-speed {
    type enumeration {
      enum "auto" {
        description
          "Auto-configure speed.";
      }
      enum "10Mb" {
        description
          "10 Mbps.";
      }
      enum "100Mb" {
        description
          "100 Mbps.";
      }
      enum "1Gb" {
        description
          "1 Gbps.";
      }
      enum "2500Mb" {
        description
          "2.5 Gbps.";
      }
      enum "5Gb" {
        description
          "5 Gbps.";
      }
      enum "10Gb" {
        description
          "10 Gbps.";
      }
      enum "25Gb" {
        description
          "25 Gbps.";
      }
      enum "40Gb" {
        description
          "40 Gbps.";
      }
    }
    description
      "UNI Port speed type.";
  }

  typedef live_ncs_uni-port-oper-speed {
    type enumeration {
      enum "10Mb" {
        description
          "10 Mbps.";
      }
      enum "100Mb" {
        description
          "100 Mbps.";
      }
      enum "1Gb" {
        description
          "1 Gbps.";
      }
      enum "2500Mb" {
        description
          "2.5 Gbps.";
      }
      enum "5Gb" {
        description
          "5 Gbps.";
      }
      enum "10Gb" {
        description
          "10 Gbps.";
      }
      enum "25Gb" {
        description
          "25 Gbps.";
      }
      enum "40Gb" {
        description
          "40 Gbps.";
      }
      enum "unknown" {
        description
          "UNI Port speed is unknown.";
      }
    }
    description
      "UNI Port operational speed type.";
  }

  typedef live_ncs_uni-port-duplex {
    type enumeration {
      enum "auto" {
        description
          "Auto-configure duplex.";
      }
      enum "full" {
        description
          "Full duplex.";
      }
      enum "half" {
        description
          "Half duplex.";
      }
    }
    description
      "UNI Port duplex type.";
  }

  typedef live_ncs_uni-port-oper-duplex {
    type enumeration {
      enum "full" {
        description
          "Full duplex.";
      }
      enum "half" {
        description
          "Half duplex.";
      }
      enum "unknown" {
        description
          "UNI Port duplex is unknown.";
      }
    }
    description
      "UNI Port operational duplex type.";
  }

  typedef live_ncs_onu-pluggable-xcvr-type {
    type enumeration {
      enum "gigabit-optical-ethernet" {
        description
          "Gigabit Ethernet optical IF.";
      }
      enum "ethernet-base-t" {
        description
          "10/100/1000/2500/5000/10000/25000/40000
           BASE-T Ethernet LAN IF.";
      }
      enum "unknown" {
        description
          "ONU pluggable transceiver type is unknown.";
      }
    }
    description
      "ONU pluggable transceiver types as defined
       in ITU-T G.988 Table 9.1.5-1.";
  }

  typedef live_ncs_tag-match-vid {
    type uint32 {
      range "0..4094 | 65535";
    }
    description
      "VLAN-ID type used for network tag match fields.
       A value of 0 matches on no VLAN tag or a priority tag.
       A value of 65535 matches on any VID value, no VLAN tag or a priority tag.";
  }

  typedef live_ncs_tag-action {
    type enumeration {
      enum "none" {
        description
          "No modifications will be made to the matched frame.";
      }
      enum "pop" {
        description
          "The outermost VLAN tag(s) will be popped (removed). The
           number of tags popped is specified in the tag-action-pop leaf.";
      }
      enum "stamp" {
        description
          "Stamp the outermost VLAN to either an 802.1ad tag, with the value specified in
           the tag-action-stag leaf, or an 802.1q tag, with the value specified in
           the tag-action-ctag leaf.";
      }
      enum "push" {
        description
          "Push either a new 802.1ad tag, with the value specified in
           the tag-action-stag leaf, or a new 802.1q tag, with the value specified in
           the tag-action-ctag leaf.";
      }
    }
    description
      "Tag action type.";
  }

  typedef name-string {
    type string {
      length "1..64";
    }
    description
      "Name string type.";
  }

  typedef pon-relay-attribute-string {
    type string {
      length "1..255";
    }
    description
      "PON Relay string for radius, authentication and relay identifier attributes.";
  }

  typedef interface-ref {
    type oc-if:base-interface-ref;
    description
      "L3 Interface reference type.";
  }

  typedef radius-server-ref {
    type leafref {
      path "/ncs:devices/ncs:device/ncs:config/pon-ctrl:pon-ctrl/pon-ctrl:radius-servers/pon-ctrl:radius-server/pon-ctrl:name" {
        tailf:xpath-root 3;
      }
    }
    description
      "Radius Server reference leafref type.";
  }

  typedef olt-ref {
    type leafref {
      path "/ncs:devices/ncs:device/ncs:config/pon-ctrl:pon-ctrl/pon-ctrl:olts/pon-ctrl:olt/pon-ctrl:name" {
        tailf:xpath-root 3;
      }
    }
    description
      "OLT reference leafref type.";
  }

  typedef nni-network-ref {
    type leafref {
      path "/ncs:devices/ncs:device/ncs:config/pon-ctrl:pon-ctrl/pon-ctrl:olts/pon-ctrl:olt/pon-ctrl:nni-networks/pon-ctrl:nni-network/pon-ctrl:name" {
        tailf:xpath-root 3;
      }
    }
    description
      "NNI Network reference leafref type.";
  }

  typedef onu-ref {
    type leafref {
      path "/ncs:devices/ncs:device/ncs:config/pon-ctrl:pon-ctrl/pon-ctrl:onus/pon-ctrl:onu/pon-ctrl:name" {
        tailf:xpath-root 3;
      }
    }
    description
      "ONU reference leafref type.";
  }

  typedef datalink-ref {
    type leafref {
      path "/ncs:devices/ncs:device/ncs:config/pon-ctrl:pon-ctrl/pon-ctrl:onus/pon-ctrl:onu/pon-ctrl:datalinks/pon-ctrl:datalink/pon-ctrl:name" {
        tailf:xpath-root 3;
      }
    }
    description
      "Datalink reference leafref type.";
  }

  typedef uni-port-ref {
    type leafref {
      path "/ncs:devices/ncs:device/ncs:config/pon-ctrl:pon-ctrl/pon-ctrl:onus/pon-ctrl:onu/pon-ctrl:uni-ports/pon-ctrl:uni-port/pon-ctrl:name" {
        tailf:xpath-root 3;
      }
    }
    description
      "UNI Port reference leafref type.";
  }

  typedef sla-profile-ref {
    type leafref {
      path "/ncs:devices/ncs:device/ncs:config/pon-ctrl:pon-ctrl/pon-ctrl:sla-profiles/pon-ctrl:sla-profile/pon-ctrl:name" {
        tailf:xpath-root 3;
      }
    }
    description
      "SLA Profile reference leafref type.";
  }

  typedef inband-management-action {
    type enumeration {
      enum "get" {
        description
          "In-band management get action.";
      }
      enum "set" {
        description
          "In-band management set action.";
      }
    }
    description
      "In-band management action type.";
  }

  typedef tpid {
    type enumeration {
      enum "0x8100" {
        value 33024;
        description
          "TPID 0x8100.";
      }
      enum "0x88a8" {
        value 34984;
        description
          "TPID 0x88a8.";
      }
    }
    description
      "TPID type.";
  }

  typedef pon-mode {
    type enumeration {
      enum "xgs-pon" {
        description
          "XGS-PON mode.";
      }
      enum "10g-epon" {
        description
          "10G-EPON mode.";
      }
    }
    description
      "PON-mode type.";
  }

  typedef encryption-mode {
    type enumeration {
      enum "disabled" {
        description
          "Encryption is disabled.";
      }
      enum "downstream" {
        description
          "Encryption is enabled in the downstream direction only.";
      }
      enum "bidirectional" {
        description
          "Encryption is enabled bidirectionally.";
      }
    }
    description
      "Encryption mode type.";
  }

  typedef olt-oper-state {
    type enumeration {
      enum "active" {
        description
          "OLT is configured and discovered.";
      }
      enum "configured" {
        description
          "OLT is configured/pre-provisioned but not discovered.";
      }
      enum "disabled" {
        description
          "OLT is disabled.";
      }
      enum "unknown" {
        description
          "OLT was previously active or disabled but is no longer discovered.";
      }
    }
    description
      "OLT operational state type.";
  }

  typedef onu-oper-state {
    type enumeration {
      enum "registered" {
        description
          "ONU is configured and registered with the OLT.";
      }
      enum "configured" {
        description
          "ONU is configured/pre-provisioned but has not yet registered with the OLT.";
      }
      enum "deregistered" {
        description
          "ONU has deregistered with the OLT.";
      }
      enum "unknown" {
        description
          "ONU state is unknown due to OLT state being unknown.";
      }
      enum "unconfigured" {
        description
          "ONU was discovered but has no corresponding configuration.";
      }
    }
    description
      "ONU operational state type.";
  }

  typedef uni-port-oper-state {
    type enumeration {
      enum "up" {
        description
          "UNI Port link state is up.";
      }
      enum "down" {
        description
          "UNI Port link state is down.";
      }
      enum "unknown" {
        description
          "UNI Port link state is unknown.";
      }
    }
    description
      "UNI Port operational state type.";
  }

  typedef radius-server-oper-state {
    type enumeration {
      enum "up" {
        description
          "Radius server state is up.";
      }
      enum "down" {
        description
          "Radius server state is down.";
      }
      enum "unknown" {
        description
          "Radius server state is unknown.";
      }
    }
    description
      "Radius server operational state type.";
  }

  typedef dhcp-relay-oper-state {
    type enumeration {
      enum "discover" {
        description
          "DHCP relay state is discover (discover packet is sent).";
      }
      enum "offer" {
        description
          "DHCP relay state is offer (offer packet is sent).";
      }
      enum "request" {
        description
          "DHCP relay state is request (request packet is sent).";
      }
      enum "acknowledge" {
        description
          "DHCP relay state is acknowledge (initialization is complete).";
      }
      enum "not-acknowledge" {
        description
          "DHCP relay state is not-acknowledge (requested parameters are unacceptable).";
      }
      enum "decline" {
        description
          "DHCP relay state is decline (network address is in use).";
      }
      enum "release" {
        description
          "DHCP relay state is release (network address is no longer required).";
      }
      enum "inform" {
        description
          "DHCP relay state is inform (network address is manually obtained).";
      }
      enum "forced-renew" {
        description
          "DHCP relay state is forced renew.";
      }
      enum "expired" {
        description
          "DHCP relay state is expired.";
      }
      enum "reset" {
        description
          "DHCP relay state is reset.";
      }
      enum "unknown" {
        description
          "DHCP relay state is unknown.";
      }
    }
    description
      "DHCP relay operational state type.";
  }

  typedef authentication-oper-state {
    type enumeration {
      enum "start" {
        description
          "Authentication state is start.";
      }
      enum "request" {
        description
          "Authentication state is request.";
      }
      enum "response" {
        description
          "Authentication state is response.";
      }
      enum "success" {
        description
          "Authentication state is success.";
      }
      enum "failure" {
        description
          "Authentication state is failure.";
      }
      enum "initiate" {
        description
          "Authentication state is initiate.";
      }
      enum "finish" {
        description
          "Authentication state is finish.";
      }
      enum "logoff" {
        description
          "Authentication state is logoff.";
      }
      enum "unknown" {
        description
          "Authentication state is unknown.";
      }
    }
    description
      "Authentication operational state type.";
  }

  typedef uni-port-speed {
    type enumeration {
      enum "auto" {
        description
          "Auto-configure speed.";
      }
      enum "10Mb" {
        description
          "10 Mbps.";
      }
      enum "100Mb" {
        description
          "100 Mbps.";
      }
      enum "1Gb" {
        description
          "1 Gbps.";
      }
      enum "2500Mb" {
        description
          "2.5 Gbps.";
      }
      enum "5Gb" {
        description
          "5 Gbps.";
      }
      enum "10Gb" {
        description
          "10 Gbps.";
      }
      enum "25Gb" {
        description
          "25 Gbps.";
      }
      enum "40Gb" {
        description
          "40 Gbps.";
      }
    }
    description
      "UNI Port speed type.";
  }

  typedef uni-port-oper-speed {
    type enumeration {
      enum "10Mb" {
        description
          "10 Mbps.";
      }
      enum "100Mb" {
        description
          "100 Mbps.";
      }
      enum "1Gb" {
        description
          "1 Gbps.";
      }
      enum "2500Mb" {
        description
          "2.5 Gbps.";
      }
      enum "5Gb" {
        description
          "5 Gbps.";
      }
      enum "10Gb" {
        description
          "10 Gbps.";
      }
      enum "25Gb" {
        description
          "25 Gbps.";
      }
      enum "40Gb" {
        description
          "40 Gbps.";
      }
      enum "unknown" {
        description
          "UNI Port speed is unknown.";
      }
    }
    description
      "UNI Port operational speed type.";
  }

  typedef uni-port-duplex {
    type enumeration {
      enum "auto" {
        description
          "Auto-configure duplex.";
      }
      enum "full" {
        description
          "Full duplex.";
      }
      enum "half" {
        description
          "Half duplex.";
      }
    }
    description
      "UNI Port duplex type.";
  }

  typedef uni-port-oper-duplex {
    type enumeration {
      enum "full" {
        description
          "Full duplex.";
      }
      enum "half" {
        description
          "Half duplex.";
      }
      enum "unknown" {
        description
          "UNI Port duplex is unknown.";
      }
    }
    description
      "UNI Port operational duplex type.";
  }

  typedef onu-pluggable-xcvr-type {
    type enumeration {
      enum "gigabit-optical-ethernet" {
        description
          "Gigabit Ethernet optical IF.";
      }
      enum "ethernet-base-t" {
        description
          "10/100/1000/2500/5000/10000/25000/40000
           BASE-T Ethernet LAN IF.";
      }
      enum "unknown" {
        description
          "ONU pluggable transceiver type is unknown.";
      }
    }
    description
      "ONU pluggable transceiver types as defined
       in ITU-T G.988 Table 9.1.5-1.";
  }

  typedef tag-match-vid {
    type uint32 {
      range "0..4094 | 65535";
    }
    description
      "VLAN-ID type used for network tag match fields.
       A value of 0 matches on no VLAN tag or a priority tag.
       A value of 65535 matches on any VID value, no VLAN tag or a priority tag.";
  }

  typedef tag-action {
    type enumeration {
      enum "none" {
        description
          "No modifications will be made to the matched frame.";
      }
      enum "pop" {
        description
          "The outermost VLAN tag(s) will be popped (removed). The
           number of tags popped is specified in the tag-action-pop leaf.";
      }
      enum "stamp" {
        description
          "Stamp the outermost VLAN to either an 802.1ad tag, with the value specified in
           the tag-action-stag leaf, or an 802.1q tag, with the value specified in
           the tag-action-ctag leaf.";
      }
      enum "push" {
        description
          "Push either a new 802.1ad tag, with the value specified in
           the tag-action-stag leaf, or a new 802.1q tag, with the value specified in
           the tag-action-ctag leaf.";
      }
    }
    description
      "Tag action type.";
  }

  grouping ncs_template_tag-match-grouping {
    description
      "Tag match grouping";
    leaf match-stag {
      type pon-ctrl:ncs_template_tag-match-vid;
      // NCS drop mandatory statement
      description
        "Match on an 802.1ad tag. If present, this must be the first tag on the
         frame.";
    }
    leaf match-ctag-1 {
      type pon-ctrl:ncs_template_tag-match-vid;
      // NCS drop mandatory statement
      description
        "Match on an 802.1q tag. If present, this tag will be the first tag on the
         frame, or will be the first tag after an S-Tag.";
    }
    leaf match-ctag-2 {
      type pon-ctrl:ncs_template_tag-match-vid;
      // NCS drop mandatory statement
      description
        "Match on an 802.1q tag. If present, this tag will be last tag on the
         frame and will be after the S-Tag and C-Tag 1.";
    }
  }

  grouping ncs_template_tag-options-grouping {
    description
      "Tag options grouping";
    leaf tag-action {
      type pon-ctrl:ncs_template_tag-action;
      // NCS drop mandatory statement
      description
        "Tag action to perform on the matched frame.";
    }
    leaf tag-action-pop {
      // NCS drop when statement
      type string;
      // NCS drop mandatory statement
      description
        "Number of tags to pop.";
    }
    leaf tag-action-stag {
      // NCS drop when statement
      type pon-ctrl:ncs_template_tag-match-vid;
      // NCS drop must statement
      // NCS drop mandatory statement
      description
        "The 802.1ad tag to stamp or push.";
    }
    leaf tag-action-ctag {
      // NCS drop when statement
      type pon-ctrl:ncs_template_tag-match-vid;
      // NCS drop must statement
      // NCS drop mandatory statement
      description
        "The 802.1q tag to stamp or push.";
    }
  }

  grouping ncs_template_packet-counters-grouping {
    description
      "Packet counters grouping.";
    leaf rx-frames-total {
      type string;
      description
        "Total number of packets received.";
    }
    leaf tx-frames-total {
      type string;
      description
        "Total number of packets transmitted.";
    }
    leaf rx-frames-64 {
      type string;
      description
        "Count of 64-octet packets received on the interface.";
    }
    leaf tx-frames-64 {
      type string;
      description
        "Count of 64-octet packets transmitted on the interface.";
    }
    leaf rx-frames-65-127 {
      type string;
      description
        "Count of received packets on the interface with length 65 octets to 127
         octets.";
    }
    leaf tx-frames-65-127 {
      type string;
      description
        "Count of transmitted packets on the interface with length 65 octets to 127
         octets.";
    }
    leaf rx-frames-128-255 {
      type string;
      description
        "Count of received packets on the interface with length 128 octets to 255
         octets.";
    }
    leaf tx-frames-128-255 {
      type string;
      description
        "Count of transmitted packets on the interface with length 128 octets to 255
         octets.";
    }
    leaf rx-frames-256-511 {
      type string;
      description
        "Count of received packets on the interface with length 256 octets to 511
         octets.";
    }
    leaf tx-frames-256-511 {
      type string;
      description
        "Count of transmitted packets on the interface with length 256 octets to 511
         octets.";
    }
    leaf rx-frames-512-1023 {
      type string;
      description
        "Count of received packets on the interface with length 512 octets to 1023
         octets.";
    }
    leaf tx-frames-512-1023 {
      type string;
      description
        "Count of transmitted packets on the interface with length 512 octets to 1023
         octets.";
    }
    leaf rx-frames-1024-1518 {
      type string;
      description
        "Count of received packets on the interface with length 1024 octets to 1518
         octets.";
    }
    leaf tx-frames-1024-1518 {
      type string;
      description
        "Count of transmitted packets on the interface with length 1024 octets to 1518
         octets.";
    }
    leaf rx-frames-1519-plus {
      type string;
      description
        "Count of received packets on the interface with length 1519 octets up to the
         maximum size supported by the interface.";
    }
    leaf tx-frames-1519-plus {
      type string;
      description
        "Count of transmitted packets on the interface with length 1519 octets up to the
         maximum size supported by the interface.";
    }
  }

  grouping ncs_template_phy-counters-grouping {
    description
      "PHY/MAC counters grouping.";
    leaf rx-octets-total {
      type string;
      description
        "Total count of the number of octets that have been received.";
    }
    leaf tx-octets-total {
      type string;
      description
        "Total count of the number of octets that have been transmitted.";
    }
    leaf rx-encrypted-segments {
      type string;
      description
        "Count of encrypted segments received that were decrypted.";
    }
    leaf tx-encrypted-segments {
      type string;
      description
        "Count of encrypted segments transmitted.";
    }
    leaf rx-plain-segments {
      type string;
      description
        "Count of unencrypted segments received.";
    }
    leaf tx-plain-segments {
      type string;
      description
        "Count of unencrypted segments transmitted.";
    }
    leaf rx-bandwidth-reqs {
      type string;
      description
        "Number of bandwidth requests received.";
    }
    leaf tx-bandwidth-reqs {
      type string;
      description
        "Number of bandwidth requests transmitted.";
    }
    leaf rx-mpcp-ploam {
      type string;
      description
        "Number of PLOAM cells received.";
    }
    leaf tx-mpcp-ploam {
      type string;
      description
        "Number of PLOAM cells transmitted.";
    }
    leaf tx-upstream-slots {
      type string;
      description
        "Number of upstream slot grants issued (Allocations).";
    }
    leaf rx-filtered-frames {
      type string;
      description
        "Count of frames received but filtered (not forwarded).";
    }
    leaf rx-empty-slots {
      type string;
      description
        "Count of upstream slots in which data was not present.";
    }
    leaf rx-good-bip-blocks {
      type string;
      description
        "Count of BIP blocks received without error.";
    }
    leaf rx-errored-bip-blocks {
      type string;
      description
        "Count of BIP blocks received with error.";
    }
    leaf rx-errored-bip-bits {
      type string;
      description
        "Count of BIP bits received with error.";
    }
    leaf rx-hec-errors {
      type string;
      description
        "Number of errored Header Error Checksums in the XGEM header and GPON
         Framing.";
    }
    leaf rx-crc32-drops {
      type string;
      description
        "Count of segments dropped due to CRC-32 error.";
    }
    leaf rx-crc8-errors {
      type string;
      description
        "Count of received CRC-8 errors in XGS-PON Allocations/Bandwidth Requests.";
    }
    leaf rx-overflow-drops {
      type string;
      description
        "Count of segments dropped due to queue overlfow.";
    }
    leaf rx-too-short-drops {
      type string;
      description
        "Count of segments dropped due to being too short.";
    }
    leaf rx-too-long-drops {
      type string;
      description
        "Count of segments dropped due to being too long.";
    }
  }

  grouping ncs_template_flooding-counters-grouping {
    description
      "Flooding (broadcast/multicast) counters grouping.";
    leaf tx-frames-total {
      type string;
      description
        "Total number of packets transmitted.";
    }
    leaf tx-frames-64 {
      type string;
      description
        "Count of 64-octet packets transmitted on the interface.";
    }
    leaf tx-frames-65-127 {
      type string;
      description
        "Count of transmitted packets on the interface with length 65 octets to 127
         octets.";
    }
    leaf tx-frames-128-255 {
      type string;
      description
        "Count of transmitted packets on the interface with length 128 octets to 255
         octets.";
    }
    leaf tx-frames-256-511 {
      type string;
      description
        "Count of transmitted packets on the interface with length 256 octets to 511
         octets.";
    }
    leaf tx-frames-512-1023 {
      type string;
      description
        "Count of transmitted packets on the interface with length 512 octets to 1023
         octets.";
    }
    leaf tx-frames-1024-1518 {
      type string;
      description
        "Count of transmitted packets on the interface with length 1024 octets to 1518
         octets.";
    }
    leaf tx-frames-1519-plus {
      type string;
      description
        "Count of transmitted packets on the interface with length 1519 octets up to the
         maximum size supported by the interface.";
    }
    leaf tx-frames-unicast {
      type string;
      description
        "Total number of unicast packets transmitted.";
    }
    leaf tx-frames-multicast {
      type string;
      description
        "Total number of multicast packets transmitted.";
    }
    leaf tx-frames-broadcast {
      type string;
      description
        "Total number of broadcast packets transmitted.";
    }
    leaf tx-octets-unicast {
      type string;
      description
        "Total number of unicast octets transmitted.";
    }
    leaf tx-octets-multicast-broadcast {
      type string;
      description
        "Total number of multicast/broacast octets transmitted.";
    }
    leaf tx-octets-control {
      type string;
      description
        "Total number of control octets transmitted.";
    }
    leaf tx-octets-encrypted {
      type string;
      description
        "Total number of encrypted octets transmitted.";
    }
    leaf tx-octets-plain {
      type string;
      description
        "Total number of plain octets transmitted.";
    }
    leaf tx-octets-total {
      type string;
      description
        "Total number of octets transmitted.";
    }
  }

  grouping ncs_template_uni-port-packet-counters-grouping {
    description
      "UNI Port packet counters grouping.";
    leaf ds-octets-total {
      type string;
      description
        "Total number of downstream packets received.";
    }
    leaf us-octets-total {
      type string;
      description
        "Total number of upstream packets received.";
    }
    leaf ds-frames-total {
      type string;
      description
        "Total number of downstream packets received.";
    }
    leaf us-frames-total {
      type string;
      description
        "Total number of upstream packets received.";
    }
    leaf ds-frames-63-less {
      type string;
      description
        "Count of downstream packets received with a length of 63 octets or less.";
    }
    leaf us-frames-63-less {
      type string;
      description
        "Count of upstream packets received with a length of 63 octets or less.";
    }
    leaf ds-frames-64 {
      type string;
      description
        "Count of downstream packets received with a length of 64 octets.";
    }
    leaf us-frames-64 {
      type string;
      description
        "Count of upstream packets received with a length of 64 octets.";
    }
    leaf ds-frames-65-127 {
      type string;
      description
        "Count of downstream packets received with length 65 octets to 127 octets.";
    }
    leaf us-frames-65-127 {
      type string;
      description
        "Count of upstream packets received with length 65 octets to 127 octets.";
    }
    leaf ds-frames-128-255 {
      type string;
      description
        "Count of downstream packets received with length 128 octets to 255 octets.";
    }
    leaf us-frames-128-255 {
      type string;
      description
        "Count of upstream packets received with length 128 octets to 255 octets.";
    }
    leaf ds-frames-256-511 {
      type string;
      description
        "Count of downstream packets received with length 256 octets to 511 octets.";
    }
    leaf us-frames-256-511 {
      type string;
      description
        "Count of upstream packets received with length 256 octets to 511 octets.";
    }
    leaf ds-frames-512-1023 {
      type string;
      description
        "Count of downstream packets received with length 512 octets to 1023 octets.";
    }
    leaf us-frames-512-1023 {
      type string;
      description
        "Count of upstream packets received with length 512 octets to 1023 octets.";
    }
    leaf ds-frames-1024-1518 {
      type string;
      description
        "Count of downstream packets received with length 1024 octets to 1518 octets.";
    }
    leaf us-frames-1024-1518 {
      type string;
      description
        "Count of upstream packets received with length 1024 octets to 1518 octets.";
    }
    leaf ds-frames-1519-plus {
      type string;
      description
        "Count of downstream packets received with length 1519 octets up to the
         maximum size supported by the UNI Port.";
    }
    leaf us-frames-1519-plus {
      type string;
      description
        "Count of upstream packets received with length 1519 octets up to the
         maximum size supported by the UNI Port.";
    }
  }

  grouping ncs_template_relay-counters-grouping {
    description
      "DHCP realy packet counters grouping.";
    leaf rx-frames-relay-dhcp {
      type string;
      description
        "Total number of DHCP packets received.";
    }
    leaf tx-frames-relay-dhcp {
      type string;
      description
        "Total number of DHCP packets transmitted.";
    }
    leaf rx-frames-relay-eapol {
      type string;
      description
        "Total number of EAPoL packets received.";
    }
    leaf tx-frames-relay-eapol {
      type string;
      description
        "Total number of EAPoL packets transmitted.";
    }
  }

  grouping ncs_template_auth-counters-grouping {
    description
      "Authentication packet counters grouping.";
    leaf rx-frames-auth-radius {
      type string;
      description
        "Total number of packets received for radius authentication.";
    }
    leaf tx-frames-auth-radius {
      type string;
      description
        "Total number of packets transmitted for radius authentication.";
    }
    leaf rx-frames-auth-eapol {
      type string;
      description
        "Total number of EAPoL packets received for radius authentication.";
    }
    leaf tx-frames-auth-eapol {
      type string;
      description
        "Total number of EAPoL packets transmitted for radius authentication.";
    }
  }

  grouping ncs_template_dhcp-grouping {
    description
      "Dynamic host configuration protocol grouping.";
    leaf dhcp-circuit-id {
      type pon-ctrl:ncs_template_pon-relay-attribute-string;
      description
        "Dynamic host configuration protocol circuit-id.";
    }
    leaf dhcp-remote-id {
      type pon-ctrl:ncs_template_pon-relay-attribute-string;
      description
        "Dynamic host configuration protocol remote-id.";
    }
  }

  grouping ncs_template_radius-grouping {
    description
      "Radius grouping.";
    leaf NAS-identifier {
      type pon-ctrl:ncs_template_pon-relay-attribute-string;
      description
        "Network access server identifier.";
    }
    leaf NAS-port-id {
      type pon-ctrl:ncs_template_pon-relay-attribute-string;
      description
        "Network access server port identifier.";
    }
    leaf NAS-user-name-override {
      type pon-ctrl:ncs_template_pon-relay-attribute-string;
      // NCS drop default statement
      description
        "Network access server user name override.";
    }
  }

  grouping ncs_template_pon-ctrl-radius-server-grouping {
    description
      "Radius Server.";
    list radius-server-address {
      // NCS patched for predictable order
      ordered-by user;
      key "host port";
      description
        "Radius server host and port.";
      leaf host {
        type string;
        description
          "Radius server host address.";
      }
      leaf port {
        type string;
        description
          "Radius server port.";
      }
    }
  }

  grouping ncs_rpc_notif_tag-match-grouping {
    description
      "Tag match grouping";
    leaf match-stag {
      type pon-ctrl:ncs_rpc_notif_tag-match-vid;
      mandatory true;
      description
        "Match on an 802.1ad tag. If present, this must be the first tag on the
         frame.";
    }
    leaf match-ctag-1 {
      type pon-ctrl:ncs_rpc_notif_tag-match-vid;
      mandatory true;
      description
        "Match on an 802.1q tag. If present, this tag will be the first tag on the
         frame, or will be the first tag after an S-Tag.";
    }
    leaf match-ctag-2 {
      type pon-ctrl:ncs_rpc_notif_tag-match-vid;
      mandatory true;
      description
        "Match on an 802.1q tag. If present, this tag will be last tag on the
         frame and will be after the S-Tag and C-Tag 1.";
    }
  }

  grouping ncs_rpc_notif_tag-options-grouping {
    description
      "Tag options grouping";
    leaf tag-action {
      type pon-ctrl:ncs_rpc_notif_tag-action;
      mandatory true;
      description
        "Tag action to perform on the matched frame.";
    }
    leaf tag-action-pop {
      when "../tag-action = 'pop'" {
        tailf:xpath-root 3;
      }
      type uint8 {
        range "1..3";
      }
      mandatory true;
      description
        "Number of tags to pop.";
    }
    leaf tag-action-stag {
      when "(../tag-action = 'stamp' or ../tag-action = 'push')
and not(../tag-action-ctag)" {
        tailf:xpath-root 3;
      }
      type pon-ctrl:ncs_rpc_notif_tag-match-vid;
      must '. != 65535' {
        tailf:xpath-root 3;
        error-message "Illegal value for stag.";
      }
      mandatory true;
      description
        "The 802.1ad tag to stamp or push.";
    }
    leaf tag-action-ctag {
      when "(../tag-action = 'stamp' or ../tag-action = 'push')
and not(../tag-action-stag)" {
        tailf:xpath-root 3;
      }
      type pon-ctrl:ncs_rpc_notif_tag-match-vid;
      must '. != 65535' {
        tailf:xpath-root 3;
        error-message "Illegal value for ctag.";
      }
      mandatory true;
      description
        "The 802.1q tag to stamp or push.";
    }
  }

  grouping ncs_rpc_notif_packet-counters-grouping {
    description
      "Packet counters grouping.";
    leaf rx-frames-total {
      type yang:counter64;
      description
        "Total number of packets received.";
    }
    leaf tx-frames-total {
      type yang:counter64;
      description
        "Total number of packets transmitted.";
    }
    leaf rx-frames-64 {
      type yang:counter64;
      description
        "Count of 64-octet packets received on the interface.";
    }
    leaf tx-frames-64 {
      type yang:counter64;
      description
        "Count of 64-octet packets transmitted on the interface.";
    }
    leaf rx-frames-65-127 {
      type yang:counter64;
      description
        "Count of received packets on the interface with length 65 octets to 127
         octets.";
    }
    leaf tx-frames-65-127 {
      type yang:counter64;
      description
        "Count of transmitted packets on the interface with length 65 octets to 127
         octets.";
    }
    leaf rx-frames-128-255 {
      type yang:counter64;
      description
        "Count of received packets on the interface with length 128 octets to 255
         octets.";
    }
    leaf tx-frames-128-255 {
      type yang:counter64;
      description
        "Count of transmitted packets on the interface with length 128 octets to 255
         octets.";
    }
    leaf rx-frames-256-511 {
      type yang:counter64;
      description
        "Count of received packets on the interface with length 256 octets to 511
         octets.";
    }
    leaf tx-frames-256-511 {
      type yang:counter64;
      description
        "Count of transmitted packets on the interface with length 256 octets to 511
         octets.";
    }
    leaf rx-frames-512-1023 {
      type yang:counter64;
      description
        "Count of received packets on the interface with length 512 octets to 1023
         octets.";
    }
    leaf tx-frames-512-1023 {
      type yang:counter64;
      description
        "Count of transmitted packets on the interface with length 512 octets to 1023
         octets.";
    }
    leaf rx-frames-1024-1518 {
      type yang:counter64;
      description
        "Count of received packets on the interface with length 1024 octets to 1518
         octets.";
    }
    leaf tx-frames-1024-1518 {
      type yang:counter64;
      description
        "Count of transmitted packets on the interface with length 1024 octets to 1518
         octets.";
    }
    leaf rx-frames-1519-plus {
      type yang:counter64;
      description
        "Count of received packets on the interface with length 1519 octets up to the
         maximum size supported by the interface.";
    }
    leaf tx-frames-1519-plus {
      type yang:counter64;
      description
        "Count of transmitted packets on the interface with length 1519 octets up to the
         maximum size supported by the interface.";
    }
  }

  grouping ncs_rpc_notif_phy-counters-grouping {
    description
      "PHY/MAC counters grouping.";
    leaf rx-octets-total {
      type yang:counter64;
      description
        "Total count of the number of octets that have been received.";
    }
    leaf tx-octets-total {
      type yang:counter64;
      description
        "Total count of the number of octets that have been transmitted.";
    }
    leaf rx-encrypted-segments {
      type yang:counter64;
      description
        "Count of encrypted segments received that were decrypted.";
    }
    leaf tx-encrypted-segments {
      type yang:counter64;
      description
        "Count of encrypted segments transmitted.";
    }
    leaf rx-plain-segments {
      type yang:counter64;
      description
        "Count of unencrypted segments received.";
    }
    leaf tx-plain-segments {
      type yang:counter64;
      description
        "Count of unencrypted segments transmitted.";
    }
    leaf rx-bandwidth-reqs {
      type yang:counter64;
      description
        "Number of bandwidth requests received.";
    }
    leaf tx-bandwidth-reqs {
      type yang:counter64;
      description
        "Number of bandwidth requests transmitted.";
    }
    leaf rx-mpcp-ploam {
      type yang:counter64;
      description
        "Number of PLOAM cells received.";
    }
    leaf tx-mpcp-ploam {
      type yang:counter64;
      description
        "Number of PLOAM cells transmitted.";
    }
    leaf tx-upstream-slots {
      type yang:counter64;
      description
        "Number of upstream slot grants issued (Allocations).";
    }
    leaf rx-filtered-frames {
      type yang:counter64;
      description
        "Count of frames received but filtered (not forwarded).";
    }
    leaf rx-empty-slots {
      type yang:counter64;
      description
        "Count of upstream slots in which data was not present.";
    }
    leaf rx-good-bip-blocks {
      type yang:counter64;
      description
        "Count of BIP blocks received without error.";
    }
    leaf rx-errored-bip-blocks {
      type yang:counter64;
      description
        "Count of BIP blocks received with error.";
    }
    leaf rx-errored-bip-bits {
      type yang:counter64;
      description
        "Count of BIP bits received with error.";
    }
    leaf rx-hec-errors {
      type yang:counter64;
      description
        "Number of errored Header Error Checksums in the XGEM header and GPON
         Framing.";
    }
    leaf rx-crc32-drops {
      type yang:counter64;
      description
        "Count of segments dropped due to CRC-32 error.";
    }
    leaf rx-crc8-errors {
      type yang:counter64;
      description
        "Count of received CRC-8 errors in XGS-PON Allocations/Bandwidth Requests.";
    }
    leaf rx-overflow-drops {
      type yang:counter64;
      description
        "Count of segments dropped due to queue overlfow.";
    }
    leaf rx-too-short-drops {
      type yang:counter64;
      description
        "Count of segments dropped due to being too short.";
    }
    leaf rx-too-long-drops {
      type yang:counter64;
      description
        "Count of segments dropped due to being too long.";
    }
  }

  grouping ncs_rpc_notif_flooding-counters-grouping {
    description
      "Flooding (broadcast/multicast) counters grouping.";
    leaf tx-frames-total {
      type yang:counter64;
      description
        "Total number of packets transmitted.";
    }
    leaf tx-frames-64 {
      type yang:counter64;
      description
        "Count of 64-octet packets transmitted on the interface.";
    }
    leaf tx-frames-65-127 {
      type yang:counter64;
      description
        "Count of transmitted packets on the interface with length 65 octets to 127
         octets.";
    }
    leaf tx-frames-128-255 {
      type yang:counter64;
      description
        "Count of transmitted packets on the interface with length 128 octets to 255
         octets.";
    }
    leaf tx-frames-256-511 {
      type yang:counter64;
      description
        "Count of transmitted packets on the interface with length 256 octets to 511
         octets.";
    }
    leaf tx-frames-512-1023 {
      type yang:counter64;
      description
        "Count of transmitted packets on the interface with length 512 octets to 1023
         octets.";
    }
    leaf tx-frames-1024-1518 {
      type yang:counter64;
      description
        "Count of transmitted packets on the interface with length 1024 octets to 1518
         octets.";
    }
    leaf tx-frames-1519-plus {
      type yang:counter64;
      description
        "Count of transmitted packets on the interface with length 1519 octets up to the
         maximum size supported by the interface.";
    }
    leaf tx-frames-unicast {
      type yang:counter64;
      description
        "Total number of unicast packets transmitted.";
    }
    leaf tx-frames-multicast {
      type yang:counter64;
      description
        "Total number of multicast packets transmitted.";
    }
    leaf tx-frames-broadcast {
      type yang:counter64;
      description
        "Total number of broadcast packets transmitted.";
    }
    leaf tx-octets-unicast {
      type yang:counter64;
      description
        "Total number of unicast octets transmitted.";
    }
    leaf tx-octets-multicast-broadcast {
      type yang:counter64;
      description
        "Total number of multicast/broacast octets transmitted.";
    }
    leaf tx-octets-control {
      type yang:counter64;
      description
        "Total number of control octets transmitted.";
    }
    leaf tx-octets-encrypted {
      type yang:counter64;
      description
        "Total number of encrypted octets transmitted.";
    }
    leaf tx-octets-plain {
      type yang:counter64;
      description
        "Total number of plain octets transmitted.";
    }
    leaf tx-octets-total {
      type yang:counter64;
      description
        "Total number of octets transmitted.";
    }
  }

  grouping ncs_rpc_notif_uni-port-packet-counters-grouping {
    description
      "UNI Port packet counters grouping.";
    leaf ds-octets-total {
      type yang:counter64;
      description
        "Total number of downstream packets received.";
    }
    leaf us-octets-total {
      type yang:counter64;
      description
        "Total number of upstream packets received.";
    }
    leaf ds-frames-total {
      type yang:counter64;
      description
        "Total number of downstream packets received.";
    }
    leaf us-frames-total {
      type yang:counter64;
      description
        "Total number of upstream packets received.";
    }
    leaf ds-frames-63-less {
      type yang:counter64;
      description
        "Count of downstream packets received with a length of 63 octets or less.";
    }
    leaf us-frames-63-less {
      type yang:counter64;
      description
        "Count of upstream packets received with a length of 63 octets or less.";
    }
    leaf ds-frames-64 {
      type yang:counter64;
      description
        "Count of downstream packets received with a length of 64 octets.";
    }
    leaf us-frames-64 {
      type yang:counter64;
      description
        "Count of upstream packets received with a length of 64 octets.";
    }
    leaf ds-frames-65-127 {
      type yang:counter64;
      description
        "Count of downstream packets received with length 65 octets to 127 octets.";
    }
    leaf us-frames-65-127 {
      type yang:counter64;
      description
        "Count of upstream packets received with length 65 octets to 127 octets.";
    }
    leaf ds-frames-128-255 {
      type yang:counter64;
      description
        "Count of downstream packets received with length 128 octets to 255 octets.";
    }
    leaf us-frames-128-255 {
      type yang:counter64;
      description
        "Count of upstream packets received with length 128 octets to 255 octets.";
    }
    leaf ds-frames-256-511 {
      type yang:counter64;
      description
        "Count of downstream packets received with length 256 octets to 511 octets.";
    }
    leaf us-frames-256-511 {
      type yang:counter64;
      description
        "Count of upstream packets received with length 256 octets to 511 octets.";
    }
    leaf ds-frames-512-1023 {
      type yang:counter64;
      description
        "Count of downstream packets received with length 512 octets to 1023 octets.";
    }
    leaf us-frames-512-1023 {
      type yang:counter64;
      description
        "Count of upstream packets received with length 512 octets to 1023 octets.";
    }
    leaf ds-frames-1024-1518 {
      type yang:counter64;
      description
        "Count of downstream packets received with length 1024 octets to 1518 octets.";
    }
    leaf us-frames-1024-1518 {
      type yang:counter64;
      description
        "Count of upstream packets received with length 1024 octets to 1518 octets.";
    }
    leaf ds-frames-1519-plus {
      type yang:counter64;
      description
        "Count of downstream packets received with length 1519 octets up to the
         maximum size supported by the UNI Port.";
    }
    leaf us-frames-1519-plus {
      type yang:counter64;
      description
        "Count of upstream packets received with length 1519 octets up to the
         maximum size supported by the UNI Port.";
    }
  }

  grouping ncs_rpc_notif_relay-counters-grouping {
    description
      "DHCP realy packet counters grouping.";
    leaf rx-frames-relay-dhcp {
      type yang:counter64;
      description
        "Total number of DHCP packets received.";
    }
    leaf tx-frames-relay-dhcp {
      type yang:counter64;
      description
        "Total number of DHCP packets transmitted.";
    }
    leaf rx-frames-relay-eapol {
      type yang:counter64;
      description
        "Total number of EAPoL packets received.";
    }
    leaf tx-frames-relay-eapol {
      type yang:counter64;
      description
        "Total number of EAPoL packets transmitted.";
    }
  }

  grouping ncs_rpc_notif_auth-counters-grouping {
    description
      "Authentication packet counters grouping.";
    leaf rx-frames-auth-radius {
      type yang:counter64;
      description
        "Total number of packets received for radius authentication.";
    }
    leaf tx-frames-auth-radius {
      type yang:counter64;
      description
        "Total number of packets transmitted for radius authentication.";
    }
    leaf rx-frames-auth-eapol {
      type yang:counter64;
      description
        "Total number of EAPoL packets received for radius authentication.";
    }
    leaf tx-frames-auth-eapol {
      type yang:counter64;
      description
        "Total number of EAPoL packets transmitted for radius authentication.";
    }
  }

  grouping ncs_rpc_notif_dhcp-grouping {
    description
      "Dynamic host configuration protocol grouping.";
    leaf dhcp-circuit-id {
      type pon-ctrl:ncs_rpc_notif_pon-relay-attribute-string;
      description
        "Dynamic host configuration protocol circuit-id.";
    }
    leaf dhcp-remote-id {
      type pon-ctrl:ncs_rpc_notif_pon-relay-attribute-string;
      description
        "Dynamic host configuration protocol remote-id.";
    }
  }

  grouping ncs_rpc_notif_radius-grouping {
    description
      "Radius grouping.";
    leaf NAS-identifier {
      type pon-ctrl:ncs_rpc_notif_pon-relay-attribute-string;
      description
        "Network access server identifier.";
    }
    leaf NAS-port-id {
      type pon-ctrl:ncs_rpc_notif_pon-relay-attribute-string;
      description
        "Network access server port identifier.";
    }
    leaf NAS-user-name-override {
      type pon-ctrl:ncs_rpc_notif_pon-relay-attribute-string;
      default "Default";
      description
        "Network access server user name override.";
    }
  }

  grouping ncs_rpc_notif_pon-ctrl-radius-server-grouping {
    description
      "Radius Server.";
    list radius-server-address {
      key "host port";
      description
        "Radius server host and port.";
      leaf host {
        type inet:host;
        description
          "Radius server host address.";
      }
      leaf port {
        type inet:port-number;
        description
          "Radius server port.";
      }
    }
  }

  grouping live_ncs_tag-match-grouping {
    description
      "Tag match grouping";
    leaf match-stag {
      type pon-ctrl:live_ncs_tag-match-vid;
      // NCS drop mandatory statement
      description
        "Match on an 802.1ad tag. If present, this must be the first tag on the
         frame.";
    }
    leaf match-ctag-1 {
      type pon-ctrl:live_ncs_tag-match-vid;
      // NCS drop mandatory statement
      description
        "Match on an 802.1q tag. If present, this tag will be the first tag on the
         frame, or will be the first tag after an S-Tag.";
    }
    leaf match-ctag-2 {
      type pon-ctrl:live_ncs_tag-match-vid;
      // NCS drop mandatory statement
      description
        "Match on an 802.1q tag. If present, this tag will be last tag on the
         frame and will be after the S-Tag and C-Tag 1.";
    }
  }

  grouping live_ncs_tag-options-grouping {
    description
      "Tag options grouping";
    leaf tag-action {
      type pon-ctrl:live_ncs_tag-action;
      // NCS drop mandatory statement
      description
        "Tag action to perform on the matched frame.";
    }
    leaf tag-action-pop {
      // NCS drop when statement
      type uint8 {
        range "1..3";
      }
      // NCS drop mandatory statement
      description
        "Number of tags to pop.";
    }
    leaf tag-action-stag {
      // NCS drop when statement
      type pon-ctrl:live_ncs_tag-match-vid;
      // NCS drop must statement
      // NCS drop mandatory statement
      description
        "The 802.1ad tag to stamp or push.";
    }
    leaf tag-action-ctag {
      // NCS drop when statement
      type pon-ctrl:live_ncs_tag-match-vid;
      // NCS drop must statement
      // NCS drop mandatory statement
      description
        "The 802.1q tag to stamp or push.";
    }
  }

  grouping live_ncs_packet-counters-grouping {
    description
      "Packet counters grouping.";
    leaf rx-frames-total {
      type yang:counter64;
      description
        "Total number of packets received.";
    }
    leaf tx-frames-total {
      type yang:counter64;
      description
        "Total number of packets transmitted.";
    }
    leaf rx-frames-64 {
      type yang:counter64;
      description
        "Count of 64-octet packets received on the interface.";
    }
    leaf tx-frames-64 {
      type yang:counter64;
      description
        "Count of 64-octet packets transmitted on the interface.";
    }
    leaf rx-frames-65-127 {
      type yang:counter64;
      description
        "Count of received packets on the interface with length 65 octets to 127
         octets.";
    }
    leaf tx-frames-65-127 {
      type yang:counter64;
      description
        "Count of transmitted packets on the interface with length 65 octets to 127
         octets.";
    }
    leaf rx-frames-128-255 {
      type yang:counter64;
      description
        "Count of received packets on the interface with length 128 octets to 255
         octets.";
    }
    leaf tx-frames-128-255 {
      type yang:counter64;
      description
        "Count of transmitted packets on the interface with length 128 octets to 255
         octets.";
    }
    leaf rx-frames-256-511 {
      type yang:counter64;
      description
        "Count of received packets on the interface with length 256 octets to 511
         octets.";
    }
    leaf tx-frames-256-511 {
      type yang:counter64;
      description
        "Count of transmitted packets on the interface with length 256 octets to 511
         octets.";
    }
    leaf rx-frames-512-1023 {
      type yang:counter64;
      description
        "Count of received packets on the interface with length 512 octets to 1023
         octets.";
    }
    leaf tx-frames-512-1023 {
      type yang:counter64;
      description
        "Count of transmitted packets on the interface with length 512 octets to 1023
         octets.";
    }
    leaf rx-frames-1024-1518 {
      type yang:counter64;
      description
        "Count of received packets on the interface with length 1024 octets to 1518
         octets.";
    }
    leaf tx-frames-1024-1518 {
      type yang:counter64;
      description
        "Count of transmitted packets on the interface with length 1024 octets to 1518
         octets.";
    }
    leaf rx-frames-1519-plus {
      type yang:counter64;
      description
        "Count of received packets on the interface with length 1519 octets up to the
         maximum size supported by the interface.";
    }
    leaf tx-frames-1519-plus {
      type yang:counter64;
      description
        "Count of transmitted packets on the interface with length 1519 octets up to the
         maximum size supported by the interface.";
    }
  }

  grouping live_ncs_phy-counters-grouping {
    description
      "PHY/MAC counters grouping.";
    leaf rx-octets-total {
      type yang:counter64;
      description
        "Total count of the number of octets that have been received.";
    }
    leaf tx-octets-total {
      type yang:counter64;
      description
        "Total count of the number of octets that have been transmitted.";
    }
    leaf rx-encrypted-segments {
      type yang:counter64;
      description
        "Count of encrypted segments received that were decrypted.";
    }
    leaf tx-encrypted-segments {
      type yang:counter64;
      description
        "Count of encrypted segments transmitted.";
    }
    leaf rx-plain-segments {
      type yang:counter64;
      description
        "Count of unencrypted segments received.";
    }
    leaf tx-plain-segments {
      type yang:counter64;
      description
        "Count of unencrypted segments transmitted.";
    }
    leaf rx-bandwidth-reqs {
      type yang:counter64;
      description
        "Number of bandwidth requests received.";
    }
    leaf tx-bandwidth-reqs {
      type yang:counter64;
      description
        "Number of bandwidth requests transmitted.";
    }
    leaf rx-mpcp-ploam {
      type yang:counter64;
      description
        "Number of PLOAM cells received.";
    }
    leaf tx-mpcp-ploam {
      type yang:counter64;
      description
        "Number of PLOAM cells transmitted.";
    }
    leaf tx-upstream-slots {
      type yang:counter64;
      description
        "Number of upstream slot grants issued (Allocations).";
    }
    leaf rx-filtered-frames {
      type yang:counter64;
      description
        "Count of frames received but filtered (not forwarded).";
    }
    leaf rx-empty-slots {
      type yang:counter64;
      description
        "Count of upstream slots in which data was not present.";
    }
    leaf rx-good-bip-blocks {
      type yang:counter64;
      description
        "Count of BIP blocks received without error.";
    }
    leaf rx-errored-bip-blocks {
      type yang:counter64;
      description
        "Count of BIP blocks received with error.";
    }
    leaf rx-errored-bip-bits {
      type yang:counter64;
      description
        "Count of BIP bits received with error.";
    }
    leaf rx-hec-errors {
      type yang:counter64;
      description
        "Number of errored Header Error Checksums in the XGEM header and GPON
         Framing.";
    }
    leaf rx-crc32-drops {
      type yang:counter64;
      description
        "Count of segments dropped due to CRC-32 error.";
    }
    leaf rx-crc8-errors {
      type yang:counter64;
      description
        "Count of received CRC-8 errors in XGS-PON Allocations/Bandwidth Requests.";
    }
    leaf rx-overflow-drops {
      type yang:counter64;
      description
        "Count of segments dropped due to queue overlfow.";
    }
    leaf rx-too-short-drops {
      type yang:counter64;
      description
        "Count of segments dropped due to being too short.";
    }
    leaf rx-too-long-drops {
      type yang:counter64;
      description
        "Count of segments dropped due to being too long.";
    }
  }

  grouping live_ncs_flooding-counters-grouping {
    description
      "Flooding (broadcast/multicast) counters grouping.";
    leaf tx-frames-total {
      type yang:counter64;
      description
        "Total number of packets transmitted.";
    }
    leaf tx-frames-64 {
      type yang:counter64;
      description
        "Count of 64-octet packets transmitted on the interface.";
    }
    leaf tx-frames-65-127 {
      type yang:counter64;
      description
        "Count of transmitted packets on the interface with length 65 octets to 127
         octets.";
    }
    leaf tx-frames-128-255 {
      type yang:counter64;
      description
        "Count of transmitted packets on the interface with length 128 octets to 255
         octets.";
    }
    leaf tx-frames-256-511 {
      type yang:counter64;
      description
        "Count of transmitted packets on the interface with length 256 octets to 511
         octets.";
    }
    leaf tx-frames-512-1023 {
      type yang:counter64;
      description
        "Count of transmitted packets on the interface with length 512 octets to 1023
         octets.";
    }
    leaf tx-frames-1024-1518 {
      type yang:counter64;
      description
        "Count of transmitted packets on the interface with length 1024 octets to 1518
         octets.";
    }
    leaf tx-frames-1519-plus {
      type yang:counter64;
      description
        "Count of transmitted packets on the interface with length 1519 octets up to the
         maximum size supported by the interface.";
    }
    leaf tx-frames-unicast {
      type yang:counter64;
      description
        "Total number of unicast packets transmitted.";
    }
    leaf tx-frames-multicast {
      type yang:counter64;
      description
        "Total number of multicast packets transmitted.";
    }
    leaf tx-frames-broadcast {
      type yang:counter64;
      description
        "Total number of broadcast packets transmitted.";
    }
    leaf tx-octets-unicast {
      type yang:counter64;
      description
        "Total number of unicast octets transmitted.";
    }
    leaf tx-octets-multicast-broadcast {
      type yang:counter64;
      description
        "Total number of multicast/broacast octets transmitted.";
    }
    leaf tx-octets-control {
      type yang:counter64;
      description
        "Total number of control octets transmitted.";
    }
    leaf tx-octets-encrypted {
      type yang:counter64;
      description
        "Total number of encrypted octets transmitted.";
    }
    leaf tx-octets-plain {
      type yang:counter64;
      description
        "Total number of plain octets transmitted.";
    }
    leaf tx-octets-total {
      type yang:counter64;
      description
        "Total number of octets transmitted.";
    }
  }

  grouping live_ncs_uni-port-packet-counters-grouping {
    description
      "UNI Port packet counters grouping.";
    leaf ds-octets-total {
      type yang:counter64;
      description
        "Total number of downstream packets received.";
    }
    leaf us-octets-total {
      type yang:counter64;
      description
        "Total number of upstream packets received.";
    }
    leaf ds-frames-total {
      type yang:counter64;
      description
        "Total number of downstream packets received.";
    }
    leaf us-frames-total {
      type yang:counter64;
      description
        "Total number of upstream packets received.";
    }
    leaf ds-frames-63-less {
      type yang:counter64;
      description
        "Count of downstream packets received with a length of 63 octets or less.";
    }
    leaf us-frames-63-less {
      type yang:counter64;
      description
        "Count of upstream packets received with a length of 63 octets or less.";
    }
    leaf ds-frames-64 {
      type yang:counter64;
      description
        "Count of downstream packets received with a length of 64 octets.";
    }
    leaf us-frames-64 {
      type yang:counter64;
      description
        "Count of upstream packets received with a length of 64 octets.";
    }
    leaf ds-frames-65-127 {
      type yang:counter64;
      description
        "Count of downstream packets received with length 65 octets to 127 octets.";
    }
    leaf us-frames-65-127 {
      type yang:counter64;
      description
        "Count of upstream packets received with length 65 octets to 127 octets.";
    }
    leaf ds-frames-128-255 {
      type yang:counter64;
      description
        "Count of downstream packets received with length 128 octets to 255 octets.";
    }
    leaf us-frames-128-255 {
      type yang:counter64;
      description
        "Count of upstream packets received with length 128 octets to 255 octets.";
    }
    leaf ds-frames-256-511 {
      type yang:counter64;
      description
        "Count of downstream packets received with length 256 octets to 511 octets.";
    }
    leaf us-frames-256-511 {
      type yang:counter64;
      description
        "Count of upstream packets received with length 256 octets to 511 octets.";
    }
    leaf ds-frames-512-1023 {
      type yang:counter64;
      description
        "Count of downstream packets received with length 512 octets to 1023 octets.";
    }
    leaf us-frames-512-1023 {
      type yang:counter64;
      description
        "Count of upstream packets received with length 512 octets to 1023 octets.";
    }
    leaf ds-frames-1024-1518 {
      type yang:counter64;
      description
        "Count of downstream packets received with length 1024 octets to 1518 octets.";
    }
    leaf us-frames-1024-1518 {
      type yang:counter64;
      description
        "Count of upstream packets received with length 1024 octets to 1518 octets.";
    }
    leaf ds-frames-1519-plus {
      type yang:counter64;
      description
        "Count of downstream packets received with length 1519 octets up to the
         maximum size supported by the UNI Port.";
    }
    leaf us-frames-1519-plus {
      type yang:counter64;
      description
        "Count of upstream packets received with length 1519 octets up to the
         maximum size supported by the UNI Port.";
    }
  }

  grouping live_ncs_relay-counters-grouping {
    description
      "DHCP realy packet counters grouping.";
    leaf rx-frames-relay-dhcp {
      type yang:counter64;
      description
        "Total number of DHCP packets received.";
    }
    leaf tx-frames-relay-dhcp {
      type yang:counter64;
      description
        "Total number of DHCP packets transmitted.";
    }
    leaf rx-frames-relay-eapol {
      type yang:counter64;
      description
        "Total number of EAPoL packets received.";
    }
    leaf tx-frames-relay-eapol {
      type yang:counter64;
      description
        "Total number of EAPoL packets transmitted.";
    }
  }

  grouping live_ncs_auth-counters-grouping {
    description
      "Authentication packet counters grouping.";
    leaf rx-frames-auth-radius {
      type yang:counter64;
      description
        "Total number of packets received for radius authentication.";
    }
    leaf tx-frames-auth-radius {
      type yang:counter64;
      description
        "Total number of packets transmitted for radius authentication.";
    }
    leaf rx-frames-auth-eapol {
      type yang:counter64;
      description
        "Total number of EAPoL packets received for radius authentication.";
    }
    leaf tx-frames-auth-eapol {
      type yang:counter64;
      description
        "Total number of EAPoL packets transmitted for radius authentication.";
    }
  }

  grouping live_ncs_dhcp-grouping {
    description
      "Dynamic host configuration protocol grouping.";
    leaf dhcp-circuit-id {
      type pon-ctrl:live_ncs_pon-relay-attribute-string;
      description
        "Dynamic host configuration protocol circuit-id.";
    }
    leaf dhcp-remote-id {
      type pon-ctrl:live_ncs_pon-relay-attribute-string;
      description
        "Dynamic host configuration protocol remote-id.";
    }
  }

  grouping live_ncs_radius-grouping {
    description
      "Radius grouping.";
    leaf NAS-identifier {
      type pon-ctrl:live_ncs_pon-relay-attribute-string;
      description
        "Network access server identifier.";
    }
    leaf NAS-port-id {
      type pon-ctrl:live_ncs_pon-relay-attribute-string;
      description
        "Network access server port identifier.";
    }
    leaf NAS-user-name-override {
      type pon-ctrl:live_ncs_pon-relay-attribute-string;
      // NCS drop default statement
      description
        "Network access server user name override.";
    }
  }

  grouping live_ncs_pon-ctrl-radius-server-grouping {
    description
      "Radius Server.";
    list radius-server-address {
      key "host port";
      description
        "Radius server host and port.";
      leaf host {
        type inet:host;
        description
          "Radius server host address.";
      }
      leaf port {
        type inet:port-number;
        description
          "Radius server port.";
      }
    }
  }

  grouping tag-match-grouping {
    description
      "Tag match grouping";
    leaf match-stag {
      type pon-ctrl:tag-match-vid;
      mandatory true;
      description
        "Match on an 802.1ad tag. If present, this must be the first tag on the
         frame.";
    }
    leaf match-ctag-1 {
      type pon-ctrl:tag-match-vid;
      mandatory true;
      description
        "Match on an 802.1q tag. If present, this tag will be the first tag on the
         frame, or will be the first tag after an S-Tag.";
    }
    leaf match-ctag-2 {
      type pon-ctrl:tag-match-vid;
      mandatory true;
      description
        "Match on an 802.1q tag. If present, this tag will be last tag on the
         frame and will be after the S-Tag and C-Tag 1.";
    }
  }

  grouping tag-options-grouping {
    description
      "Tag options grouping";
    leaf tag-action {
      type pon-ctrl:tag-action;
      mandatory true;
      description
        "Tag action to perform on the matched frame.";
    }
    leaf tag-action-pop {
      when "../tag-action = 'pop'" {
        tailf:xpath-root 3;
      }
      type uint8 {
        range "1..3";
      }
      mandatory true;
      description
        "Number of tags to pop.";
    }
    leaf tag-action-stag {
      when "(../tag-action = 'stamp' or ../tag-action = 'push')
and not(../tag-action-ctag)" {
        tailf:xpath-root 3;
      }
      type pon-ctrl:tag-match-vid;
      must '. != 65535' {
        tailf:xpath-root 3;
        error-message "Illegal value for stag.";
      }
      mandatory true;
      description
        "The 802.1ad tag to stamp or push.";
    }
    leaf tag-action-ctag {
      when "(../tag-action = 'stamp' or ../tag-action = 'push')
and not(../tag-action-stag)" {
        tailf:xpath-root 3;
      }
      type pon-ctrl:tag-match-vid;
      must '. != 65535' {
        tailf:xpath-root 3;
        error-message "Illegal value for ctag.";
      }
      mandatory true;
      description
        "The 802.1q tag to stamp or push.";
    }
  }

  grouping packet-counters-grouping {
    description
      "Packet counters grouping.";
    leaf rx-frames-total {
      type yang:counter64;
      description
        "Total number of packets received.";
    }
    leaf tx-frames-total {
      type yang:counter64;
      description
        "Total number of packets transmitted.";
    }
    leaf rx-frames-64 {
      type yang:counter64;
      description
        "Count of 64-octet packets received on the interface.";
    }
    leaf tx-frames-64 {
      type yang:counter64;
      description
        "Count of 64-octet packets transmitted on the interface.";
    }
    leaf rx-frames-65-127 {
      type yang:counter64;
      description
        "Count of received packets on the interface with length 65 octets to 127
         octets.";
    }
    leaf tx-frames-65-127 {
      type yang:counter64;
      description
        "Count of transmitted packets on the interface with length 65 octets to 127
         octets.";
    }
    leaf rx-frames-128-255 {
      type yang:counter64;
      description
        "Count of received packets on the interface with length 128 octets to 255
         octets.";
    }
    leaf tx-frames-128-255 {
      type yang:counter64;
      description
        "Count of transmitted packets on the interface with length 128 octets to 255
         octets.";
    }
    leaf rx-frames-256-511 {
      type yang:counter64;
      description
        "Count of received packets on the interface with length 256 octets to 511
         octets.";
    }
    leaf tx-frames-256-511 {
      type yang:counter64;
      description
        "Count of transmitted packets on the interface with length 256 octets to 511
         octets.";
    }
    leaf rx-frames-512-1023 {
      type yang:counter64;
      description
        "Count of received packets on the interface with length 512 octets to 1023
         octets.";
    }
    leaf tx-frames-512-1023 {
      type yang:counter64;
      description
        "Count of transmitted packets on the interface with length 512 octets to 1023
         octets.";
    }
    leaf rx-frames-1024-1518 {
      type yang:counter64;
      description
        "Count of received packets on the interface with length 1024 octets to 1518
         octets.";
    }
    leaf tx-frames-1024-1518 {
      type yang:counter64;
      description
        "Count of transmitted packets on the interface with length 1024 octets to 1518
         octets.";
    }
    leaf rx-frames-1519-plus {
      type yang:counter64;
      description
        "Count of received packets on the interface with length 1519 octets up to the
         maximum size supported by the interface.";
    }
    leaf tx-frames-1519-plus {
      type yang:counter64;
      description
        "Count of transmitted packets on the interface with length 1519 octets up to the
         maximum size supported by the interface.";
    }
  }

  grouping phy-counters-grouping {
    description
      "PHY/MAC counters grouping.";
    leaf rx-octets-total {
      type yang:counter64;
      description
        "Total count of the number of octets that have been received.";
    }
    leaf tx-octets-total {
      type yang:counter64;
      description
        "Total count of the number of octets that have been transmitted.";
    }
    leaf rx-encrypted-segments {
      type yang:counter64;
      description
        "Count of encrypted segments received that were decrypted.";
    }
    leaf tx-encrypted-segments {
      type yang:counter64;
      description
        "Count of encrypted segments transmitted.";
    }
    leaf rx-plain-segments {
      type yang:counter64;
      description
        "Count of unencrypted segments received.";
    }
    leaf tx-plain-segments {
      type yang:counter64;
      description
        "Count of unencrypted segments transmitted.";
    }
    leaf rx-bandwidth-reqs {
      type yang:counter64;
      description
        "Number of bandwidth requests received.";
    }
    leaf tx-bandwidth-reqs {
      type yang:counter64;
      description
        "Number of bandwidth requests transmitted.";
    }
    leaf rx-mpcp-ploam {
      type yang:counter64;
      description
        "Number of PLOAM cells received.";
    }
    leaf tx-mpcp-ploam {
      type yang:counter64;
      description
        "Number of PLOAM cells transmitted.";
    }
    leaf tx-upstream-slots {
      type yang:counter64;
      description
        "Number of upstream slot grants issued (Allocations).";
    }
    leaf rx-filtered-frames {
      type yang:counter64;
      description
        "Count of frames received but filtered (not forwarded).";
    }
    leaf rx-empty-slots {
      type yang:counter64;
      description
        "Count of upstream slots in which data was not present.";
    }
    leaf rx-good-bip-blocks {
      type yang:counter64;
      description
        "Count of BIP blocks received without error.";
    }
    leaf rx-errored-bip-blocks {
      type yang:counter64;
      description
        "Count of BIP blocks received with error.";
    }
    leaf rx-errored-bip-bits {
      type yang:counter64;
      description
        "Count of BIP bits received with error.";
    }
    leaf rx-hec-errors {
      type yang:counter64;
      description
        "Number of errored Header Error Checksums in the XGEM header and GPON
         Framing.";
    }
    leaf rx-crc32-drops {
      type yang:counter64;
      description
        "Count of segments dropped due to CRC-32 error.";
    }
    leaf rx-crc8-errors {
      type yang:counter64;
      description
        "Count of received CRC-8 errors in XGS-PON Allocations/Bandwidth Requests.";
    }
    leaf rx-overflow-drops {
      type yang:counter64;
      description
        "Count of segments dropped due to queue overlfow.";
    }
    leaf rx-too-short-drops {
      type yang:counter64;
      description
        "Count of segments dropped due to being too short.";
    }
    leaf rx-too-long-drops {
      type yang:counter64;
      description
        "Count of segments dropped due to being too long.";
    }
  }

  grouping flooding-counters-grouping {
    description
      "Flooding (broadcast/multicast) counters grouping.";
    leaf tx-frames-total {
      type yang:counter64;
      description
        "Total number of packets transmitted.";
    }
    leaf tx-frames-64 {
      type yang:counter64;
      description
        "Count of 64-octet packets transmitted on the interface.";
    }
    leaf tx-frames-65-127 {
      type yang:counter64;
      description
        "Count of transmitted packets on the interface with length 65 octets to 127
         octets.";
    }
    leaf tx-frames-128-255 {
      type yang:counter64;
      description
        "Count of transmitted packets on the interface with length 128 octets to 255
         octets.";
    }
    leaf tx-frames-256-511 {
      type yang:counter64;
      description
        "Count of transmitted packets on the interface with length 256 octets to 511
         octets.";
    }
    leaf tx-frames-512-1023 {
      type yang:counter64;
      description
        "Count of transmitted packets on the interface with length 512 octets to 1023
         octets.";
    }
    leaf tx-frames-1024-1518 {
      type yang:counter64;
      description
        "Count of transmitted packets on the interface with length 1024 octets to 1518
         octets.";
    }
    leaf tx-frames-1519-plus {
      type yang:counter64;
      description
        "Count of transmitted packets on the interface with length 1519 octets up to the
         maximum size supported by the interface.";
    }
    leaf tx-frames-unicast {
      type yang:counter64;
      description
        "Total number of unicast packets transmitted.";
    }
    leaf tx-frames-multicast {
      type yang:counter64;
      description
        "Total number of multicast packets transmitted.";
    }
    leaf tx-frames-broadcast {
      type yang:counter64;
      description
        "Total number of broadcast packets transmitted.";
    }
    leaf tx-octets-unicast {
      type yang:counter64;
      description
        "Total number of unicast octets transmitted.";
    }
    leaf tx-octets-multicast-broadcast {
      type yang:counter64;
      description
        "Total number of multicast/broacast octets transmitted.";
    }
    leaf tx-octets-control {
      type yang:counter64;
      description
        "Total number of control octets transmitted.";
    }
    leaf tx-octets-encrypted {
      type yang:counter64;
      description
        "Total number of encrypted octets transmitted.";
    }
    leaf tx-octets-plain {
      type yang:counter64;
      description
        "Total number of plain octets transmitted.";
    }
    leaf tx-octets-total {
      type yang:counter64;
      description
        "Total number of octets transmitted.";
    }
  }

  grouping uni-port-packet-counters-grouping {
    description
      "UNI Port packet counters grouping.";
    leaf ds-octets-total {
      type yang:counter64;
      description
        "Total number of downstream packets received.";
    }
    leaf us-octets-total {
      type yang:counter64;
      description
        "Total number of upstream packets received.";
    }
    leaf ds-frames-total {
      type yang:counter64;
      description
        "Total number of downstream packets received.";
    }
    leaf us-frames-total {
      type yang:counter64;
      description
        "Total number of upstream packets received.";
    }
    leaf ds-frames-63-less {
      type yang:counter64;
      description
        "Count of downstream packets received with a length of 63 octets or less.";
    }
    leaf us-frames-63-less {
      type yang:counter64;
      description
        "Count of upstream packets received with a length of 63 octets or less.";
    }
    leaf ds-frames-64 {
      type yang:counter64;
      description
        "Count of downstream packets received with a length of 64 octets.";
    }
    leaf us-frames-64 {
      type yang:counter64;
      description
        "Count of upstream packets received with a length of 64 octets.";
    }
    leaf ds-frames-65-127 {
      type yang:counter64;
      description
        "Count of downstream packets received with length 65 octets to 127 octets.";
    }
    leaf us-frames-65-127 {
      type yang:counter64;
      description
        "Count of upstream packets received with length 65 octets to 127 octets.";
    }
    leaf ds-frames-128-255 {
      type yang:counter64;
      description
        "Count of downstream packets received with length 128 octets to 255 octets.";
    }
    leaf us-frames-128-255 {
      type yang:counter64;
      description
        "Count of upstream packets received with length 128 octets to 255 octets.";
    }
    leaf ds-frames-256-511 {
      type yang:counter64;
      description
        "Count of downstream packets received with length 256 octets to 511 octets.";
    }
    leaf us-frames-256-511 {
      type yang:counter64;
      description
        "Count of upstream packets received with length 256 octets to 511 octets.";
    }
    leaf ds-frames-512-1023 {
      type yang:counter64;
      description
        "Count of downstream packets received with length 512 octets to 1023 octets.";
    }
    leaf us-frames-512-1023 {
      type yang:counter64;
      description
        "Count of upstream packets received with length 512 octets to 1023 octets.";
    }
    leaf ds-frames-1024-1518 {
      type yang:counter64;
      description
        "Count of downstream packets received with length 1024 octets to 1518 octets.";
    }
    leaf us-frames-1024-1518 {
      type yang:counter64;
      description
        "Count of upstream packets received with length 1024 octets to 1518 octets.";
    }
    leaf ds-frames-1519-plus {
      type yang:counter64;
      description
        "Count of downstream packets received with length 1519 octets up to the
         maximum size supported by the UNI Port.";
    }
    leaf us-frames-1519-plus {
      type yang:counter64;
      description
        "Count of upstream packets received with length 1519 octets up to the
         maximum size supported by the UNI Port.";
    }
  }

  grouping relay-counters-grouping {
    description
      "DHCP realy packet counters grouping.";
    leaf rx-frames-relay-dhcp {
      type yang:counter64;
      description
        "Total number of DHCP packets received.";
    }
    leaf tx-frames-relay-dhcp {
      type yang:counter64;
      description
        "Total number of DHCP packets transmitted.";
    }
    leaf rx-frames-relay-eapol {
      type yang:counter64;
      description
        "Total number of EAPoL packets received.";
    }
    leaf tx-frames-relay-eapol {
      type yang:counter64;
      description
        "Total number of EAPoL packets transmitted.";
    }
  }

  grouping auth-counters-grouping {
    description
      "Authentication packet counters grouping.";
    leaf rx-frames-auth-radius {
      type yang:counter64;
      description
        "Total number of packets received for radius authentication.";
    }
    leaf tx-frames-auth-radius {
      type yang:counter64;
      description
        "Total number of packets transmitted for radius authentication.";
    }
    leaf rx-frames-auth-eapol {
      type yang:counter64;
      description
        "Total number of EAPoL packets received for radius authentication.";
    }
    leaf tx-frames-auth-eapol {
      type yang:counter64;
      description
        "Total number of EAPoL packets transmitted for radius authentication.";
    }
  }

  grouping dhcp-grouping {
    description
      "Dynamic host configuration protocol grouping.";
    leaf dhcp-circuit-id {
      type pon-ctrl:pon-relay-attribute-string;
      description
        "Dynamic host configuration protocol circuit-id.";
    }
    leaf dhcp-remote-id {
      type pon-ctrl:pon-relay-attribute-string;
      description
        "Dynamic host configuration protocol remote-id.";
    }
  }

  grouping radius-grouping {
    description
      "Radius grouping.";
    leaf NAS-identifier {
      type pon-ctrl:pon-relay-attribute-string;
      description
        "Network access server identifier.";
    }
    leaf NAS-port-id {
      type pon-ctrl:pon-relay-attribute-string;
      description
        "Network access server port identifier.";
    }
    leaf NAS-user-name-override {
      type pon-ctrl:pon-relay-attribute-string;
      default "Default";
      description
        "Network access server user name override.";
    }
  }

  grouping pon-ctrl-radius-server-grouping {
    description
      "Radius Server.";
    list radius-server-address {
      key "host port";
      description
        "Radius server host and port.";
      leaf host {
        type inet:host;
        description
          "Radius server host address.";
      }
      leaf port {
        type inet:port-number;
        description
          "Radius server port.";
      }
    }
  }

  augment "/ncs:devices/ncs:device/ncs:rpc" {
    container rpc-pon-ctrl-uni-port-statistics-clear {
      tailf:ncs-device-type "netconf";
      tailf:display-when "not(../../ncs:module) or ../../ncs:module[ncs:name='ciena-pon-ctrl']";
      tailf:action pon-ctrl-uni-port-statistics-clear {
        tailf:actionpoint ncsproxy {
          tailf:internal;
        }
        description
          "Clear the statistics of a UNI Port.";
        input {
          leaf olt {
            type pon-ctrl:ncs_rpc_notif_olt-ref;
            mandatory true;
            description
              "Name of the OLT.";
          }
          leaf onu {
            type pon-ctrl:ncs_rpc_notif_onu-ref;
            mandatory true;
            description
              "Name of the ONU.";
          }
          leaf uni-port {
            type pon-ctrl:ncs_rpc_notif_uni-port-ref;
            mandatory true;
            description
              "ID of the UNI Port on the ONU.";
          }
        }
        output {
          leaf status {
            type string;
            description
              "Status of the statistics clear operation.";
          }
        }
      }
    }
  }
  augment "/ncs:devices/ncs:device-group/ncs:ned-id/ncs:rpc" {
    container rpc-pon-ctrl-uni-port-statistics-clear {
      tailf:ncs-device-type "netconf";
      tailf:display-when "/ncs:devices/ncs:device[ncs:name=current()/../../../ncs:member]/ncs:module[ncs:name='ciena-pon-ctrl']";
      tailf:action pon-ctrl-uni-port-statistics-clear {
        tailf:actionpoint ncsproxy {
          tailf:internal;
        }
        description
          "Clear the statistics of a UNI Port.";
        input {
          leaf olt {
            type pon-ctrl:ncs_rpc_notif_olt-ref;
            mandatory true;
            description
              "Name of the OLT.";
          }
          leaf onu {
            type pon-ctrl:ncs_rpc_notif_onu-ref;
            mandatory true;
            description
              "Name of the ONU.";
          }
          leaf uni-port {
            type pon-ctrl:ncs_rpc_notif_uni-port-ref;
            mandatory true;
            description
              "ID of the UNI Port on the ONU.";
          }
        }
        output {
          container "device" {
            leaf "name" {
              type string;
            }
            leaf "info" {
              type string;
            }
            container "result" {
              leaf status {
                type string;
                description
                  "Status of the statistics clear operation.";
              }
            }
          }
        }
      }
    }
  }
  augment "/ncs:devices/ncs:device/ncs:rpc" {
    container rpc-pon-ctrl-olt-inband-management {
      tailf:ncs-device-type "netconf";
      tailf:display-when "not(../../ncs:module) or ../../ncs:module[ncs:name='ciena-pon-ctrl']";
      tailf:action pon-ctrl-olt-inband-management {
        tailf:actionpoint ncsproxy {
          tailf:internal;
        }
        description
          "Get/Set the OLT in-band management TPID and VID.";
        input {
          leaf action {
            type pon-ctrl:ncs_rpc_notif_inband-management-action;
            mandatory true;
            description
              "Action to perform on the OLT.";
          }
          leaf olt {
            type pon-ctrl:ncs_rpc_notif_olt-ref;
            mandatory true;
            description
              "Name of the OLT.";
          }
          leaf management-tpid {
            type pon-ctrl:ncs_rpc_notif_tpid;
            must "../action = 'set'" {
              tailf:xpath-root 3;
              error-message "management-tpid can be set only if in-band mangement action is 'set'.";
            }
            description
              "TPID to be configured for in-band management.";
          }
          leaf management-vid {
            type mef-fp:ncs_rpc_notif_vlan-id;
            must "../action = 'set'" {
              tailf:xpath-root 3;
              error-message "management-vid can be set only if in-band mangement action is 'set'.";
            }
            description
              "VID to be configured for in-band management.";
          }
        }
        output {
          leaf status {
            type string;
            description
              "Status of the OLT in-band management get/set operation.";
          }
          leaf management-tpid {
            type pon-ctrl:ncs_rpc_notif_tpid;
            description
              "TPID configured for in-band management.";
          }
          leaf management-vid {
            type mef-fp:ncs_rpc_notif_vlan-id;
            description
              "VID configured for in-band management.";
          }
        }
      }
    }
  }
  augment "/ncs:devices/ncs:device-group/ncs:ned-id/ncs:rpc" {
    container rpc-pon-ctrl-olt-inband-management {
      tailf:ncs-device-type "netconf";
      tailf:display-when "/ncs:devices/ncs:device[ncs:name=current()/../../../ncs:member]/ncs:module[ncs:name='ciena-pon-ctrl']";
      tailf:action pon-ctrl-olt-inband-management {
        tailf:actionpoint ncsproxy {
          tailf:internal;
        }
        description
          "Get/Set the OLT in-band management TPID and VID.";
        input {
          leaf action {
            type pon-ctrl:ncs_rpc_notif_inband-management-action;
            mandatory true;
            description
              "Action to perform on the OLT.";
          }
          leaf olt {
            type pon-ctrl:ncs_rpc_notif_olt-ref;
            mandatory true;
            description
              "Name of the OLT.";
          }
          leaf management-tpid {
            type pon-ctrl:ncs_rpc_notif_tpid;
            must "../action = 'set'" {
              tailf:xpath-root 4;
              error-message "management-tpid can be set only if in-band mangement action is 'set'.";
            }
            description
              "TPID to be configured for in-band management.";
          }
          leaf management-vid {
            type mef-fp:ncs_rpc_notif_vlan-id;
            must "../action = 'set'" {
              tailf:xpath-root 4;
              error-message "management-vid can be set only if in-band mangement action is 'set'.";
            }
            description
              "VID to be configured for in-band management.";
          }
        }
        output {
          container "device" {
            leaf "name" {
              type string;
            }
            leaf "info" {
              type string;
            }
            container "result" {
              leaf status {
                type string;
                description
                  "Status of the OLT in-band management get/set operation.";
              }
              leaf management-tpid {
                type pon-ctrl:ncs_rpc_notif_tpid;
                description
                  "TPID configured for in-band management.";
              }
              leaf management-vid {
                type mef-fp:ncs_rpc_notif_vlan-id;
                description
                  "VID configured for in-band management.";
              }
            }
          }
        }
      }
    }
  }
  augment "/ncs:devices/ncs:device/ncs:rpc" {
    container rpc-pon-ctrl-relay-state-clear {
      tailf:ncs-device-type "netconf";
      tailf:display-when "not(../../ncs:module) or ../../ncs:module[ncs:name='ciena-pon-ctrl']";
      tailf:action pon-ctrl-relay-state-clear {
        tailf:actionpoint ncsproxy {
          tailf:internal;
        }
        description
          "Clear the CPE state for authentication or l2-relay.
           Authentication state is cleared if it is failure or unknown.
           L2 Relay state is cleared if it is expired or unknown.";
        input {
          leaf olt {
            type pon-ctrl:ncs_rpc_notif_olt-ref;
            mandatory true;
            description
              "Name of the OLT.";
          }
          leaf onu {
            type pon-ctrl:ncs_rpc_notif_onu-ref;
            mandatory true;
            description
              "Name of the ONU.";
          }
          leaf datalink {
            type pon-ctrl:ncs_rpc_notif_datalink-ref;
            mandatory true;
            description
              "Name of the Datalink on the ONU.";
          }
          leaf clear-authenticator {
            type boolean;
            description
              "When true, clear is for authenticator.";
          }
          leaf clear-l2-dhcp-relay {
            type boolean;
            description
              "When true, clear is for l2-relay.";
          }
        }
        output {
          leaf status {
            type string;
            description
              "Status of the clear operation.";
          }
        }
      }
    }
  }
  augment "/ncs:devices/ncs:device-group/ncs:ned-id/ncs:rpc" {
    container rpc-pon-ctrl-relay-state-clear {
      tailf:ncs-device-type "netconf";
      tailf:display-when "/ncs:devices/ncs:device[ncs:name=current()/../../../ncs:member]/ncs:module[ncs:name='ciena-pon-ctrl']";
      tailf:action pon-ctrl-relay-state-clear {
        tailf:actionpoint ncsproxy {
          tailf:internal;
        }
        description
          "Clear the CPE state for authentication or l2-relay.
           Authentication state is cleared if it is failure or unknown.
           L2 Relay state is cleared if it is expired or unknown.";
        input {
          leaf olt {
            type pon-ctrl:ncs_rpc_notif_olt-ref;
            mandatory true;
            description
              "Name of the OLT.";
          }
          leaf onu {
            type pon-ctrl:ncs_rpc_notif_onu-ref;
            mandatory true;
            description
              "Name of the ONU.";
          }
          leaf datalink {
            type pon-ctrl:ncs_rpc_notif_datalink-ref;
            mandatory true;
            description
              "Name of the Datalink on the ONU.";
          }
          leaf clear-authenticator {
            type boolean;
            description
              "When true, clear is for authenticator.";
          }
          leaf clear-l2-dhcp-relay {
            type boolean;
            description
              "When true, clear is for l2-relay.";
          }
        }
        output {
          container "device" {
            leaf "name" {
              type string;
            }
            leaf "info" {
              type string;
            }
            container "result" {
              leaf status {
                type string;
                description
                  "Status of the clear operation.";
              }
            }
          }
        }
      }
    }
  }
  augment "/ncs:devices/ncs:device/ncs:rpc" {
    container rpc-pon-ctrl-datalink-dhcp-reset {
      tailf:ncs-device-type "netconf";
      tailf:display-when "not(../../ncs:module) or ../../ncs:module[ncs:name='ciena-pon-ctrl']";
      tailf:action pon-ctrl-datalink-dhcp-reset {
        tailf:actionpoint ncsproxy {
          tailf:internal;
        }
        description
          "Reset DHCP relay on the selected CPE.";
        input {
          leaf olt {
            type pon-ctrl:ncs_rpc_notif_olt-ref;
            description
              "Name of the OLT.";
          }
          leaf onu {
            type pon-ctrl:ncs_rpc_notif_onu-ref;
            description
              "Name of the ONU.";
          }
          leaf datalink {
            type pon-ctrl:ncs_rpc_notif_datalink-ref;
            description
              "Name of the Datalink.";
          }
          leaf cpe-mac {
            type yang:mac-address;
            description
              "Customer Premise Equipment MAC address.";
          }
        }
        output {
          leaf status {
            type string;
            description
              "Status of the reset operation.";
          }
        }
      }
    }
  }
  augment "/ncs:devices/ncs:device-group/ncs:ned-id/ncs:rpc" {
    container rpc-pon-ctrl-datalink-dhcp-reset {
      tailf:ncs-device-type "netconf";
      tailf:display-when "/ncs:devices/ncs:device[ncs:name=current()/../../../ncs:member]/ncs:module[ncs:name='ciena-pon-ctrl']";
      tailf:action pon-ctrl-datalink-dhcp-reset {
        tailf:actionpoint ncsproxy {
          tailf:internal;
        }
        description
          "Reset DHCP relay on the selected CPE.";
        input {
          leaf olt {
            type pon-ctrl:ncs_rpc_notif_olt-ref;
            description
              "Name of the OLT.";
          }
          leaf onu {
            type pon-ctrl:ncs_rpc_notif_onu-ref;
            description
              "Name of the ONU.";
          }
          leaf datalink {
            type pon-ctrl:ncs_rpc_notif_datalink-ref;
            description
              "Name of the Datalink.";
          }
          leaf cpe-mac {
            type yang:mac-address;
            description
              "Customer Premise Equipment MAC address.";
          }
        }
        output {
          container "device" {
            leaf "name" {
              type string;
            }
            leaf "info" {
              type string;
            }
            container "result" {
              leaf status {
                type string;
                description
                  "Status of the reset operation.";
              }
            }
          }
        }
      }
    }
  }
  augment "/ncs:devices/ncs:device/ncs:rpc" {
    container rpc-pon-ctrl-datalink-authentication-reset {
      tailf:ncs-device-type "netconf";
      tailf:display-when "not(../../ncs:module) or ../../ncs:module[ncs:name='ciena-pon-ctrl']";
      tailf:action pon-ctrl-datalink-authentication-reset {
        tailf:actionpoint ncsproxy {
          tailf:internal;
        }
        description
          "Reset authentication on the selected CPE.";
        input {
          leaf olt {
            type pon-ctrl:ncs_rpc_notif_olt-ref;
            description
              "Name of the OLT.";
          }
          leaf onu {
            type pon-ctrl:ncs_rpc_notif_onu-ref;
            description
              "Name of the ONU.";
          }
          leaf datalink {
            type pon-ctrl:ncs_rpc_notif_datalink-ref;
            description
              "Name of the Datalink.";
          }
          leaf cpe-mac {
            type yang:mac-address;
            description
              "Customer Premise Equipment MAC address.";
          }
        }
        output {
          leaf status {
            type string;
            description
              "Status of the reset operation.";
          }
        }
      }
    }
  }
  augment "/ncs:devices/ncs:device-group/ncs:ned-id/ncs:rpc" {
    container rpc-pon-ctrl-datalink-authentication-reset {
      tailf:ncs-device-type "netconf";
      tailf:display-when "/ncs:devices/ncs:device[ncs:name=current()/../../../ncs:member]/ncs:module[ncs:name='ciena-pon-ctrl']";
      tailf:action pon-ctrl-datalink-authentication-reset {
        tailf:actionpoint ncsproxy {
          tailf:internal;
        }
        description
          "Reset authentication on the selected CPE.";
        input {
          leaf olt {
            type pon-ctrl:ncs_rpc_notif_olt-ref;
            description
              "Name of the OLT.";
          }
          leaf onu {
            type pon-ctrl:ncs_rpc_notif_onu-ref;
            description
              "Name of the ONU.";
          }
          leaf datalink {
            type pon-ctrl:ncs_rpc_notif_datalink-ref;
            description
              "Name of the Datalink.";
          }
          leaf cpe-mac {
            type yang:mac-address;
            description
              "Customer Premise Equipment MAC address.";
          }
        }
        output {
          container "device" {
            leaf "name" {
              type string;
            }
            leaf "info" {
              type string;
            }
            container "result" {
              leaf status {
                type string;
                description
                  "Status of the reset operation.";
              }
            }
          }
        }
      }
    }
  }
  augment "/ncs:devices/ncs:device/ncs:rpc" {
    container rpc-pon-ctrl-nni-network-statistics-clear {
      tailf:ncs-device-type "netconf";
      tailf:display-when "not(../../ncs:module) or ../../ncs:module[ncs:name='ciena-pon-ctrl']";
      tailf:action pon-ctrl-nni-network-statistics-clear {
        tailf:actionpoint ncsproxy {
          tailf:internal;
        }
        description
          "Clear the statistics of an NNI Network.";
        input {
          leaf olt {
            type pon-ctrl:ncs_rpc_notif_olt-ref;
            mandatory true;
            description
              "Name of the OLT.";
          }
          leaf nni-network {
            type pon-ctrl:ncs_rpc_notif_nni-network-ref;
            mandatory true;
            description
              "Name of the NNI Network.";
          }
          leaf flooding-statistics {
            type boolean;
            mandatory true;
            description
              "When true, flooding statistics on the NNI Network are cleared.";
          }
        }
        output {
          leaf status {
            type string;
            description
              "Status of the statistics clear operation.";
          }
        }
      }
    }
  }
  augment "/ncs:devices/ncs:device-group/ncs:ned-id/ncs:rpc" {
    container rpc-pon-ctrl-nni-network-statistics-clear {
      tailf:ncs-device-type "netconf";
      tailf:display-when "/ncs:devices/ncs:device[ncs:name=current()/../../../ncs:member]/ncs:module[ncs:name='ciena-pon-ctrl']";
      tailf:action pon-ctrl-nni-network-statistics-clear {
        tailf:actionpoint ncsproxy {
          tailf:internal;
        }
        description
          "Clear the statistics of an NNI Network.";
        input {
          leaf olt {
            type pon-ctrl:ncs_rpc_notif_olt-ref;
            mandatory true;
            description
              "Name of the OLT.";
          }
          leaf nni-network {
            type pon-ctrl:ncs_rpc_notif_nni-network-ref;
            mandatory true;
            description
              "Name of the NNI Network.";
          }
          leaf flooding-statistics {
            type boolean;
            mandatory true;
            description
              "When true, flooding statistics on the NNI Network are cleared.";
          }
        }
        output {
          container "device" {
            leaf "name" {
              type string;
            }
            leaf "info" {
              type string;
            }
            container "result" {
              leaf status {
                type string;
                description
                  "Status of the statistics clear operation.";
              }
            }
          }
        }
      }
    }
  }
  augment "/ncs:devices/ncs:device/ncs:rpc" {
    container rpc-pon-ctrl-onu-admission-control {
      tailf:ncs-device-type "netconf";
      tailf:display-when "not(../../ncs:module) or ../../ncs:module[ncs:name='ciena-pon-ctrl']";
      tailf:action pon-ctrl-onu-admission-control {
        tailf:actionpoint ncsproxy {
          tailf:internal;
        }
        description
          "Control whether an ONU is allowed to register or disallowed
           from registering on an OLT.";
        input {
          leaf olt {
            type pon-ctrl:ncs_rpc_notif_olt-ref;
            mandatory true;
            description
              "Name of the OLT.";
          }
          leaf onu {
            type pon-ctrl:ncs_rpc_notif_onu-ref;
            mandatory true;
            description
              "Name of the ONU.";
          }
          leaf registration-allowed {
            type boolean;
            mandatory true;
            description
              "When true, an ONU is allowed to register. When false,
               an ONU is disallowed from registering. An ONU that is
               disallowed from registering on the OLT will show up in
               a 'Deregistered' state with a deregister-reason of
               'Disallowed'. Note that disallowing an ONU from being
               admitted to the OLT does not persist over OLT
               reboots.";
          }
        }
        output {
          leaf status {
            type string;
            description
              "Status of the ONU admission control operation.";
          }
        }
      }
    }
  }
  augment "/ncs:devices/ncs:device-group/ncs:ned-id/ncs:rpc" {
    container rpc-pon-ctrl-onu-admission-control {
      tailf:ncs-device-type "netconf";
      tailf:display-when "/ncs:devices/ncs:device[ncs:name=current()/../../../ncs:member]/ncs:module[ncs:name='ciena-pon-ctrl']";
      tailf:action pon-ctrl-onu-admission-control {
        tailf:actionpoint ncsproxy {
          tailf:internal;
        }
        description
          "Control whether an ONU is allowed to register or disallowed
           from registering on an OLT.";
        input {
          leaf olt {
            type pon-ctrl:ncs_rpc_notif_olt-ref;
            mandatory true;
            description
              "Name of the OLT.";
          }
          leaf onu {
            type pon-ctrl:ncs_rpc_notif_onu-ref;
            mandatory true;
            description
              "Name of the ONU.";
          }
          leaf registration-allowed {
            type boolean;
            mandatory true;
            description
              "When true, an ONU is allowed to register. When false,
               an ONU is disallowed from registering. An ONU that is
               disallowed from registering on the OLT will show up in
               a 'Deregistered' state with a deregister-reason of
               'Disallowed'. Note that disallowing an ONU from being
               admitted to the OLT does not persist over OLT
               reboots.";
          }
        }
        output {
          container "device" {
            leaf "name" {
              type string;
            }
            leaf "info" {
              type string;
            }
            container "result" {
              leaf status {
                type string;
                description
                  "Status of the ONU admission control operation.";
              }
            }
          }
        }
      }
    }
  }
  augment "/ncs:devices/ncs:device/ncs:rpc" {
    container rpc-pon-ctrl-onu-firmware-activate {
      tailf:ncs-device-type "netconf";
      tailf:display-when "not(../../ncs:module) or ../../ncs:module[ncs:name='ciena-pon-ctrl']";
      tailf:action pon-ctrl-onu-firmware-activate {
        tailf:actionpoint ncsproxy {
          tailf:internal;
        }
        description
          "Activate the specified firmware version on an ONU.";
        input {
          leaf olt {
            type pon-ctrl:ncs_rpc_notif_olt-ref;
            mandatory true;
            description
              "Name of the OLT.";
          }
          leaf onu {
            type pon-ctrl:ncs_rpc_notif_onu-ref;
            mandatory true;
            description
              "Name of the ONU.";
          }
          leaf firmware-version {
            type string;
            mandatory true;
            description
              "Version of firmware to activate on this ONU.
               Firmware must already be installed.";
          }
        }
        output {
          leaf status {
            type string;
            description
              "Status of the ONU firmware activate operation.";
          }
        }
      }
    }
  }
  augment "/ncs:devices/ncs:device-group/ncs:ned-id/ncs:rpc" {
    container rpc-pon-ctrl-onu-firmware-activate {
      tailf:ncs-device-type "netconf";
      tailf:display-when "/ncs:devices/ncs:device[ncs:name=current()/../../../ncs:member]/ncs:module[ncs:name='ciena-pon-ctrl']";
      tailf:action pon-ctrl-onu-firmware-activate {
        tailf:actionpoint ncsproxy {
          tailf:internal;
        }
        description
          "Activate the specified firmware version on an ONU.";
        input {
          leaf olt {
            type pon-ctrl:ncs_rpc_notif_olt-ref;
            mandatory true;
            description
              "Name of the OLT.";
          }
          leaf onu {
            type pon-ctrl:ncs_rpc_notif_onu-ref;
            mandatory true;
            description
              "Name of the ONU.";
          }
          leaf firmware-version {
            type string;
            mandatory true;
            description
              "Version of firmware to activate on this ONU.
               Firmware must already be installed.";
          }
        }
        output {
          container "device" {
            leaf "name" {
              type string;
            }
            leaf "info" {
              type string;
            }
            container "result" {
              leaf status {
                type string;
                description
                  "Status of the ONU firmware activate operation.";
              }
            }
          }
        }
      }
    }
  }
  augment "/ncs:devices/ncs:device/ncs:rpc" {
    container rpc-pon-ctrl-onu-firmware-install {
      tailf:ncs-device-type "netconf";
      tailf:display-when "not(../../ncs:module) or ../../ncs:module[ncs:name='ciena-pon-ctrl']";
      tailf:action pon-ctrl-onu-firmware-install {
        tailf:actionpoint ncsproxy {
          tailf:internal;
        }
        description
          "Install new firmware on an ONU.";
        input {
          leaf olt {
            type pon-ctrl:ncs_rpc_notif_olt-ref;
            mandatory true;
            description
              "Name of the OLT.";
          }
          leaf onu {
            type pon-ctrl:ncs_rpc_notif_onu-ref;
            mandatory true;
            description
              "Name of the ONU.";
          }
          leaf firmware-file-name {
            type string;
            description
              "Name of the firmware file to install on this ONU.";
          }
          leaf defer-activation {
            type boolean;
            description
              "When true, ONU firmware activation is deferred until explicitly invoked.";
          }
        }
        output {
          leaf status {
            type string;
            description
              "Status of the ONU firmware install operation.";
          }
        }
      }
    }
  }
  augment "/ncs:devices/ncs:device-group/ncs:ned-id/ncs:rpc" {
    container rpc-pon-ctrl-onu-firmware-install {
      tailf:ncs-device-type "netconf";
      tailf:display-when "/ncs:devices/ncs:device[ncs:name=current()/../../../ncs:member]/ncs:module[ncs:name='ciena-pon-ctrl']";
      tailf:action pon-ctrl-onu-firmware-install {
        tailf:actionpoint ncsproxy {
          tailf:internal;
        }
        description
          "Install new firmware on an ONU.";
        input {
          leaf olt {
            type pon-ctrl:ncs_rpc_notif_olt-ref;
            mandatory true;
            description
              "Name of the OLT.";
          }
          leaf onu {
            type pon-ctrl:ncs_rpc_notif_onu-ref;
            mandatory true;
            description
              "Name of the ONU.";
          }
          leaf firmware-file-name {
            type string;
            description
              "Name of the firmware file to install on this ONU.";
          }
          leaf defer-activation {
            type boolean;
            description
              "When true, ONU firmware activation is deferred until explicitly invoked.";
          }
        }
        output {
          container "device" {
            leaf "name" {
              type string;
            }
            leaf "info" {
              type string;
            }
            container "result" {
              leaf status {
                type string;
                description
                  "Status of the ONU firmware install operation.";
              }
            }
          }
        }
      }
    }
  }
  augment "/ncs:devices/ncs:device/ncs:rpc" {
    container rpc-pon-ctrl-olt-firmware-activate {
      tailf:ncs-device-type "netconf";
      tailf:display-when "not(../../ncs:module) or ../../ncs:module[ncs:name='ciena-pon-ctrl']";
      tailf:action pon-ctrl-olt-firmware-activate {
        tailf:actionpoint ncsproxy {
          tailf:internal;
        }
        description
          "Activate the specified firmware version on an OLT.";
        input {
          leaf olt {
            type pon-ctrl:ncs_rpc_notif_olt-ref;
            mandatory true;
            description
              "Name of the OLT.";
          }
          leaf firmware-version {
            type string;
            mandatory true;
            description
              "Version of firmware to activate on this OLT.
               Firmware must already be installed.";
          }
        }
        output {
          leaf status {
            type string;
            description
              "Status of the OLT firmware activate operation.";
          }
        }
      }
    }
  }
  augment "/ncs:devices/ncs:device-group/ncs:ned-id/ncs:rpc" {
    container rpc-pon-ctrl-olt-firmware-activate {
      tailf:ncs-device-type "netconf";
      tailf:display-when "/ncs:devices/ncs:device[ncs:name=current()/../../../ncs:member]/ncs:module[ncs:name='ciena-pon-ctrl']";
      tailf:action pon-ctrl-olt-firmware-activate {
        tailf:actionpoint ncsproxy {
          tailf:internal;
        }
        description
          "Activate the specified firmware version on an OLT.";
        input {
          leaf olt {
            type pon-ctrl:ncs_rpc_notif_olt-ref;
            mandatory true;
            description
              "Name of the OLT.";
          }
          leaf firmware-version {
            type string;
            mandatory true;
            description
              "Version of firmware to activate on this OLT.
               Firmware must already be installed.";
          }
        }
        output {
          container "device" {
            leaf "name" {
              type string;
            }
            leaf "info" {
              type string;
            }
            container "result" {
              leaf status {
                type string;
                description
                  "Status of the OLT firmware activate operation.";
              }
            }
          }
        }
      }
    }
  }
  augment "/ncs:devices/ncs:device/ncs:rpc" {
    container rpc-pon-ctrl-olt-firmware-install {
      tailf:ncs-device-type "netconf";
      tailf:display-when "not(../../ncs:module) or ../../ncs:module[ncs:name='ciena-pon-ctrl']";
      tailf:action pon-ctrl-olt-firmware-install {
        tailf:actionpoint ncsproxy {
          tailf:internal;
        }
        description
          "Install new firmware on an OLT.";
        input {
          leaf olt {
            type pon-ctrl:ncs_rpc_notif_olt-ref;
            mandatory true;
            description
              "Name of the OLT.";
          }
          leaf defer-activation {
            type boolean;
            description
              "When true, OLT firmware activation is deferred until explicitly invoked.";
          }
        }
        output {
          leaf status {
            type string;
            description
              "Status of the OLT firmware install operation.";
          }
        }
      }
    }
  }
  augment "/ncs:devices/ncs:device-group/ncs:ned-id/ncs:rpc" {
    container rpc-pon-ctrl-olt-firmware-install {
      tailf:ncs-device-type "netconf";
      tailf:display-when "/ncs:devices/ncs:device[ncs:name=current()/../../../ncs:member]/ncs:module[ncs:name='ciena-pon-ctrl']";
      tailf:action pon-ctrl-olt-firmware-install {
        tailf:actionpoint ncsproxy {
          tailf:internal;
        }
        description
          "Install new firmware on an OLT.";
        input {
          leaf olt {
            type pon-ctrl:ncs_rpc_notif_olt-ref;
            mandatory true;
            description
              "Name of the OLT.";
          }
          leaf defer-activation {
            type boolean;
            description
              "When true, OLT firmware activation is deferred until explicitly invoked.";
          }
        }
        output {
          container "device" {
            leaf "name" {
              type string;
            }
            leaf "info" {
              type string;
            }
            container "result" {
              leaf status {
                type string;
                description
                  "Status of the OLT firmware install operation.";
              }
            }
          }
        }
      }
    }
  }
  augment "/ncs:devices/ncs:device/ncs:rpc" {
    container rpc-pon-ctrl-relay-statistics-clear {
      tailf:ncs-device-type "netconf";
      tailf:display-when "not(../../ncs:module) or ../../ncs:module[ncs:name='ciena-pon-ctrl']";
      tailf:action pon-ctrl-relay-statistics-clear {
        tailf:actionpoint ncsproxy {
          tailf:internal;
        }
        description
          "Clear the radius and/or l2-relay and/or DHCP and EAPoL statistics of the OLT or DATALINK or authenticator or l2-relay.";
        input {
          leaf olt {
            type pon-ctrl:ncs_rpc_notif_olt-ref;
            mandatory true;
            description
              "Name of the OLT.";
          }
          leaf onu {
            type pon-ctrl:ncs_rpc_notif_onu-ref;
            description
              "Name of the ONU.";
          }
          leaf datalink {
            type pon-ctrl:ncs_rpc_notif_datalink-ref;
            description
              "Name of the Datalink on the ONU.";
          }
          leaf clear-authenticator {
            type boolean;
            description
              "When true, clear statistics is for authenticator.";
          }
          leaf clear-l2-dhcp-relay {
            type boolean;
            description
              "When true, clear statistics is for l2-relay.";
          }
          leaf cpe-mac {
            type yang:mac-address;
            description
              "Customer Premise Equipment MAC address.";
          }
        }
        output {
          leaf status {
            type string;
            description
              "Status of the statistics clear operation.";
          }
        }
      }
    }
  }
  augment "/ncs:devices/ncs:device-group/ncs:ned-id/ncs:rpc" {
    container rpc-pon-ctrl-relay-statistics-clear {
      tailf:ncs-device-type "netconf";
      tailf:display-when "/ncs:devices/ncs:device[ncs:name=current()/../../../ncs:member]/ncs:module[ncs:name='ciena-pon-ctrl']";
      tailf:action pon-ctrl-relay-statistics-clear {
        tailf:actionpoint ncsproxy {
          tailf:internal;
        }
        description
          "Clear the radius and/or l2-relay and/or DHCP and EAPoL statistics of the OLT or DATALINK or authenticator or l2-relay.";
        input {
          leaf olt {
            type pon-ctrl:ncs_rpc_notif_olt-ref;
            mandatory true;
            description
              "Name of the OLT.";
          }
          leaf onu {
            type pon-ctrl:ncs_rpc_notif_onu-ref;
            description
              "Name of the ONU.";
          }
          leaf datalink {
            type pon-ctrl:ncs_rpc_notif_datalink-ref;
            description
              "Name of the Datalink on the ONU.";
          }
          leaf clear-authenticator {
            type boolean;
            description
              "When true, clear statistics is for authenticator.";
          }
          leaf clear-l2-dhcp-relay {
            type boolean;
            description
              "When true, clear statistics is for l2-relay.";
          }
          leaf cpe-mac {
            type yang:mac-address;
            description
              "Customer Premise Equipment MAC address.";
          }
        }
        output {
          container "device" {
            leaf "name" {
              type string;
            }
            leaf "info" {
              type string;
            }
            container "result" {
              leaf status {
                type string;
                description
                  "Status of the statistics clear operation.";
              }
            }
          }
        }
      }
    }
  }
  augment "/ncs:devices/ncs:device/ncs:rpc" {
    container rpc-pon-ctrl-onu-statistics-clear {
      tailf:ncs-device-type "netconf";
      tailf:display-when "not(../../ncs:module) or ../../ncs:module[ncs:name='ciena-pon-ctrl']";
      tailf:action pon-ctrl-onu-statistics-clear {
        tailf:actionpoint ncsproxy {
          tailf:internal;
        }
        description
          "Clear the statistics of an ONU, or the statistics
           of a Datalink on the ONU.";
        input {
          leaf olt {
            type pon-ctrl:ncs_rpc_notif_olt-ref;
            mandatory true;
            description
              "Name of the OLT.";
          }
          leaf onu {
            type pon-ctrl:ncs_rpc_notif_onu-ref;
            mandatory true;
            description
              "Name of the ONU.";
          }
          leaf datalink {
            type pon-ctrl:ncs_rpc_notif_datalink-ref;
            description
              "Name of the Datalink on the ONU.";
          }
        }
        output {
          leaf status {
            type string;
            description
              "Status of the statistics clear operation.";
          }
        }
      }
    }
  }
  augment "/ncs:devices/ncs:device-group/ncs:ned-id/ncs:rpc" {
    container rpc-pon-ctrl-onu-statistics-clear {
      tailf:ncs-device-type "netconf";
      tailf:display-when "/ncs:devices/ncs:device[ncs:name=current()/../../../ncs:member]/ncs:module[ncs:name='ciena-pon-ctrl']";
      tailf:action pon-ctrl-onu-statistics-clear {
        tailf:actionpoint ncsproxy {
          tailf:internal;
        }
        description
          "Clear the statistics of an ONU, or the statistics
           of a Datalink on the ONU.";
        input {
          leaf olt {
            type pon-ctrl:ncs_rpc_notif_olt-ref;
            mandatory true;
            description
              "Name of the OLT.";
          }
          leaf onu {
            type pon-ctrl:ncs_rpc_notif_onu-ref;
            mandatory true;
            description
              "Name of the ONU.";
          }
          leaf datalink {
            type pon-ctrl:ncs_rpc_notif_datalink-ref;
            description
              "Name of the Datalink on the ONU.";
          }
        }
        output {
          container "device" {
            leaf "name" {
              type string;
            }
            leaf "info" {
              type string;
            }
            container "result" {
              leaf status {
                type string;
                description
                  "Status of the statistics clear operation.";
              }
            }
          }
        }
      }
    }
  }
  augment "/ncs:devices/ncs:device/ncs:rpc" {
    container rpc-pon-ctrl-olt-statistics-clear {
      tailf:ncs-device-type "netconf";
      tailf:display-when "not(../../ncs:module) or ../../ncs:module[ncs:name='ciena-pon-ctrl']";
      tailf:action pon-ctrl-olt-statistics-clear {
        tailf:actionpoint ncsproxy {
          tailf:internal;
        }
        description
          "Clear the statistics of an OLT.";
        input {
          leaf olt {
            type pon-ctrl:ncs_rpc_notif_olt-ref;
            mandatory true;
            description
              "Name of the OLT.";
          }
        }
        output {
          leaf status {
            type string;
            description
              "Status of the statistics clear operation.";
          }
        }
      }
    }
  }
  augment "/ncs:devices/ncs:device-group/ncs:ned-id/ncs:rpc" {
    container rpc-pon-ctrl-olt-statistics-clear {
      tailf:ncs-device-type "netconf";
      tailf:display-when "/ncs:devices/ncs:device[ncs:name=current()/../../../ncs:member]/ncs:module[ncs:name='ciena-pon-ctrl']";
      tailf:action pon-ctrl-olt-statistics-clear {
        tailf:actionpoint ncsproxy {
          tailf:internal;
        }
        description
          "Clear the statistics of an OLT.";
        input {
          leaf olt {
            type pon-ctrl:ncs_rpc_notif_olt-ref;
            mandatory true;
            description
              "Name of the OLT.";
          }
        }
        output {
          container "device" {
            leaf "name" {
              type string;
            }
            leaf "info" {
              type string;
            }
            container "result" {
              leaf status {
                type string;
                description
                  "Status of the statistics clear operation.";
              }
            }
          }
        }
      }
    }
  }
  augment "/ncs:devices/ncs:device/ncs:rpc" {
    container rpc-pon-ctrl-radius-server-statistics-clear {
      tailf:ncs-device-type "netconf";
      tailf:display-when "not(../../ncs:module) or ../../ncs:module[ncs:name='ciena-pon-ctrl']";
      tailf:action pon-ctrl-radius-server-statistics-clear {
        tailf:actionpoint ncsproxy {
          tailf:internal;
        }
        description
          "Clear the statistics of a Radius Server or Radius Server hostname.";
        input {
          leaf radius-server {
            type pon-ctrl:ncs_rpc_notif_radius-server-ref;
            mandatory true;
            description
              "Name of the Radius Server.";
          }
          leaf host {
            type inet:host;
            description
              "Radius server host address.";
          }
          leaf port {
            type inet:port-number;
            description
              "Radius server port.";
          }
        }
        output {
          leaf status {
            type string;
            description
              "Status of the statistics clear operation.";
          }
        }
      }
    }
  }
  augment "/ncs:devices/ncs:device-group/ncs:ned-id/ncs:rpc" {
    container rpc-pon-ctrl-radius-server-statistics-clear {
      tailf:ncs-device-type "netconf";
      tailf:display-when "/ncs:devices/ncs:device[ncs:name=current()/../../../ncs:member]/ncs:module[ncs:name='ciena-pon-ctrl']";
      tailf:action pon-ctrl-radius-server-statistics-clear {
        tailf:actionpoint ncsproxy {
          tailf:internal;
        }
        description
          "Clear the statistics of a Radius Server or Radius Server hostname.";
        input {
          leaf radius-server {
            type pon-ctrl:ncs_rpc_notif_radius-server-ref;
            mandatory true;
            description
              "Name of the Radius Server.";
          }
          leaf host {
            type inet:host;
            description
              "Radius server host address.";
          }
          leaf port {
            type inet:port-number;
            description
              "Radius server port.";
          }
        }
        output {
          container "device" {
            leaf "name" {
              type string;
            }
            leaf "info" {
              type string;
            }
            container "result" {
              leaf status {
                type string;
                description
                  "Status of the statistics clear operation.";
              }
            }
          }
        }
      }
    }
  }
  augment "/ncs:devices/ncs:device/ncs:rpc" {
    container rpc-pon-ctrl-onu-reset {
      tailf:ncs-device-type "netconf";
      tailf:display-when "not(../../ncs:module) or ../../ncs:module[ncs:name='ciena-pon-ctrl']";
      tailf:action pon-ctrl-onu-reset {
        tailf:actionpoint ncsproxy {
          tailf:internal;
        }
        description
          "Reset an ONU.";
        input {
          leaf olt {
            type pon-ctrl:ncs_rpc_notif_olt-ref;
            mandatory true;
            description
              "Name of the OLT.";
          }
          leaf onu {
            type pon-ctrl:ncs_rpc_notif_onu-ref;
            mandatory true;
            description
              "Name of the ONU.";
          }
        }
        output {
          leaf status {
            type string;
            description
              "Status of the ONU reset operation.";
          }
        }
      }
    }
  }
  augment "/ncs:devices/ncs:device-group/ncs:ned-id/ncs:rpc" {
    container rpc-pon-ctrl-onu-reset {
      tailf:ncs-device-type "netconf";
      tailf:display-when "/ncs:devices/ncs:device[ncs:name=current()/../../../ncs:member]/ncs:module[ncs:name='ciena-pon-ctrl']";
      tailf:action pon-ctrl-onu-reset {
        tailf:actionpoint ncsproxy {
          tailf:internal;
        }
        description
          "Reset an ONU.";
        input {
          leaf olt {
            type pon-ctrl:ncs_rpc_notif_olt-ref;
            mandatory true;
            description
              "Name of the OLT.";
          }
          leaf onu {
            type pon-ctrl:ncs_rpc_notif_onu-ref;
            mandatory true;
            description
              "Name of the ONU.";
          }
        }
        output {
          container "device" {
            leaf "name" {
              type string;
            }
            leaf "info" {
              type string;
            }
            container "result" {
              leaf status {
                type string;
                description
                  "Status of the ONU reset operation.";
              }
            }
          }
        }
      }
    }
  }
  augment "/ncs:devices/ncs:device/ncs:rpc" {
    container rpc-pon-ctrl-olt-reset {
      tailf:ncs-device-type "netconf";
      tailf:display-when "not(../../ncs:module) or ../../ncs:module[ncs:name='ciena-pon-ctrl']";
      tailf:action pon-ctrl-olt-reset {
        tailf:actionpoint ncsproxy {
          tailf:internal;
        }
        description
          "Reset an OLT.";
        input {
          leaf olt {
            type pon-ctrl:ncs_rpc_notif_olt-ref;
            mandatory true;
            description
              "Name of the OLT.";
          }
        }
        output {
          leaf status {
            type string;
            description
              "Status of the OLT reset operation.";
          }
        }
      }
    }
  }
  augment "/ncs:devices/ncs:device-group/ncs:ned-id/ncs:rpc" {
    container rpc-pon-ctrl-olt-reset {
      tailf:ncs-device-type "netconf";
      tailf:display-when "/ncs:devices/ncs:device[ncs:name=current()/../../../ncs:member]/ncs:module[ncs:name='ciena-pon-ctrl']";
      tailf:action pon-ctrl-olt-reset {
        tailf:actionpoint ncsproxy {
          tailf:internal;
        }
        description
          "Reset an OLT.";
        input {
          leaf olt {
            type pon-ctrl:ncs_rpc_notif_olt-ref;
            mandatory true;
            description
              "Name of the OLT.";
          }
        }
        output {
          container "device" {
            leaf "name" {
              type string;
            }
            leaf "info" {
              type string;
            }
            container "result" {
              leaf status {
                type string;
                description
                  "Status of the OLT reset operation.";
              }
            }
          }
        }
      }
    }
  }
  augment "/ncs:devices/ncs:device/ncs:notifications/ncs:received-notifications/ncs:notification/ncs:data" {
    container authentication-oper-state-change {
      presence "";
      config false;
      description
        "Generated when the operational state of an authentication changes.";
      leaf olt {
        type pon-ctrl:ncs_rpc_notif_olt-ref;
        description
          "Name of the OLT.";
      }
      leaf onu {
        type pon-ctrl:ncs_rpc_notif_onu-ref;
        description
          "Name of the ONU.";
      }
      leaf datalink {
        type pon-ctrl:ncs_rpc_notif_datalink-ref;
        description
          "Name of the Datalink.";
      }
      leaf cpe-mac {
        type yang:mac-address;
        description
          "Customer Premise Equipment MAC address.";
      }
      leaf oper-state {
        type pon-ctrl:ncs_rpc_notif_authentication-oper-state;
        description
          "Operational state of authentication.";
      }
    }
  }
  augment "/ncs:devices/ncs:device/ncs:notifications/ncs:received-notifications/ncs:notification/ncs:data" {
    container dhcp-relay-oper-state-change {
      presence "";
      config false;
      description
        "Generated when the operational state of an DHCP relay changes.";
      leaf olt {
        type pon-ctrl:ncs_rpc_notif_olt-ref;
        description
          "Name of the OLT.";
      }
      leaf onu {
        type pon-ctrl:ncs_rpc_notif_onu-ref;
        description
          "Name of the ONU.";
      }
      leaf datalink {
        type pon-ctrl:ncs_rpc_notif_datalink-ref;
        description
          "Name of the Datalink.";
      }
      leaf cpe-mac {
        type yang:mac-address;
        description
          "Customer Premise Equipment MAC address.";
      }
      leaf oper-state {
        type pon-ctrl:ncs_rpc_notif_dhcp-relay-oper-state;
        description
          "Operational state of the DHCP relay.";
      }
    }
  }
  augment "/ncs:devices/ncs:device/ncs:notifications/ncs:received-notifications/ncs:notification/ncs:data" {
    container radius-server-oper-state-change {
      presence "";
      config false;
      description
        "Generated when the operational state of a radius server changes.";
      leaf radius-server {
        type pon-ctrl:ncs_rpc_notif_radius-server-ref;
        description
          "Name of the radius server.";
      }
      leaf host {
        type inet:host;
        description
          "Radius server host address.";
      }
      leaf port {
        type inet:port-number;
        description
          "Radius server port.";
      }
      leaf oper-state {
        type pon-ctrl:ncs_rpc_notif_radius-server-oper-state;
        description
          "Operational state of the radius server.";
      }
    }
  }
  augment "/ncs:devices/ncs:device/ncs:notifications/ncs:received-notifications/ncs:notification/ncs:data" {
    container uni-port-oper-state-change {
      presence "";
      config false;
      description
        "Generated when the operational state of an ONU UNI Port changes.";
      leaf olt {
        type pon-ctrl:ncs_rpc_notif_olt-ref;
        description
          "Name of the OLT.";
      }
      leaf onu {
        type pon-ctrl:ncs_rpc_notif_onu-ref;
        description
          "Name of the ONU.";
      }
      leaf uni-port {
        type pon-ctrl:ncs_rpc_notif_uni-port-ref;
        description
          "ID of the UNI Port whose operational state has changed.";
      }
      leaf oper-state {
        type pon-ctrl:ncs_rpc_notif_uni-port-oper-state;
        description
          "Operational state of the UNI Port.";
      }
      leaf speed {
        type pon-ctrl:ncs_rpc_notif_uni-port-oper-speed;
        description
          "Operational speed of the UNI Port
           Set when the oper-state of the ONU is 'up'.";
      }
      leaf duplex {
        type pon-ctrl:ncs_rpc_notif_uni-port-oper-duplex;
        description
          "Operational duplex of the UNI Port.
           Set when the oper-state of the ONU is 'up'.";
      }
    }
  }
  augment "/ncs:devices/ncs:device/ncs:notifications/ncs:received-notifications/ncs:notification/ncs:data" {
    container onu-oper-state-change {
      presence "";
      config false;
      description
        "Generated when the operational state of an ONU changes.";
      leaf olt {
        type pon-ctrl:ncs_rpc_notif_olt-ref;
        description
          "Name of the OLT.";
      }
      leaf onu {
        type pon-ctrl:ncs_rpc_notif_onu-ref;
        description
          "Name of the ONU whose operational state has changed.";
      }
      leaf oper-state {
        type pon-ctrl:ncs_rpc_notif_onu-oper-state;
        description
          "Operational state of the ONU.";
      }
      leaf deregister-reason {
        type string;
        description
          "The reason for the last ONU deregistration.
           Set when the oper-state of the ONU is 'deregistered'.";
      }
    }
  }
  augment "/ncs:devices/ncs:device/ncs:notifications/ncs:received-notifications/ncs:notification/ncs:data" {
    container olt-oper-state-change {
      presence "";
      config false;
      description
        "Generated when the operational state of an OLT changes.";
      leaf olt {
        type pon-ctrl:ncs_rpc_notif_olt-ref;
        description
          "Name of the OLT whose operational state has changed.";
      }
      leaf oper-state {
        type pon-ctrl:ncs_rpc_notif_olt-oper-state;
        description
          "Operational state of the OLT.";
      }
    }
  }
  augment "/ncs:devices/ncs:device/ncs:notifications/ncs:received-notifications/ncs:notification/ncs:data" {
    container onu-discovered {
      presence "";
      config false;
      description
        "Generated when a new ONU is discovered on an OLT and has not yet been configured.";
      leaf olt {
        type pon-ctrl:ncs_rpc_notif_olt-ref;
        description
          "Name of the OLT on which this ONU was discovered.";
      }
      leaf onu-serial-number {
        type string {
          pattern '[a-zA-Z]{4}[0-9a-fA-F]{8}';
        }
        description
          "The serial number of the discovered ONU.";
      }
    }
  }
  augment "/ncs:devices/ncs:device/ncs:notifications/ncs:received-notifications/ncs:notification/ncs:data" {
    container olt-discovered {
      presence "";
      config false;
      description
        "Generated when a new OLT is discovered on an interface and has not yet been configured.";
      leaf l3-interface {
        type pon-ctrl:ncs_rpc_notif_interface-ref;
        description
          "Name of the L3 interface on which this OLT was discovered.";
      }
      leaf olt-mac-address {
        type yang:mac-address;
        description
          "The MAC address of the discovered OLT.";
      }
    }
  }
  augment "/ncs:devices/ncs:device/ncs:netconf-notifications/ncs:received-notifications/ncs:notification/ncs:data" {
    container authentication-oper-state-change {
      presence "";
      config false;
      description
        "Generated when the operational state of an authentication changes.";
      leaf olt {
        type pon-ctrl:ncs_rpc_notif_olt-ref;
        description
          "Name of the OLT.";
      }
      leaf onu {
        type pon-ctrl:ncs_rpc_notif_onu-ref;
        description
          "Name of the ONU.";
      }
      leaf datalink {
        type pon-ctrl:ncs_rpc_notif_datalink-ref;
        description
          "Name of the Datalink.";
      }
      leaf cpe-mac {
        type yang:mac-address;
        description
          "Customer Premise Equipment MAC address.";
      }
      leaf oper-state {
        type pon-ctrl:ncs_rpc_notif_authentication-oper-state;
        description
          "Operational state of authentication.";
      }
    }
  }
  augment "/ncs:devices/ncs:device/ncs:netconf-notifications/ncs:received-notifications/ncs:notification/ncs:data" {
    container dhcp-relay-oper-state-change {
      presence "";
      config false;
      description
        "Generated when the operational state of an DHCP relay changes.";
      leaf olt {
        type pon-ctrl:ncs_rpc_notif_olt-ref;
        description
          "Name of the OLT.";
      }
      leaf onu {
        type pon-ctrl:ncs_rpc_notif_onu-ref;
        description
          "Name of the ONU.";
      }
      leaf datalink {
        type pon-ctrl:ncs_rpc_notif_datalink-ref;
        description
          "Name of the Datalink.";
      }
      leaf cpe-mac {
        type yang:mac-address;
        description
          "Customer Premise Equipment MAC address.";
      }
      leaf oper-state {
        type pon-ctrl:ncs_rpc_notif_dhcp-relay-oper-state;
        description
          "Operational state of the DHCP relay.";
      }
    }
  }
  augment "/ncs:devices/ncs:device/ncs:netconf-notifications/ncs:received-notifications/ncs:notification/ncs:data" {
    container radius-server-oper-state-change {
      presence "";
      config false;
      description
        "Generated when the operational state of a radius server changes.";
      leaf radius-server {
        type pon-ctrl:ncs_rpc_notif_radius-server-ref;
        description
          "Name of the radius server.";
      }
      leaf host {
        type inet:host;
        description
          "Radius server host address.";
      }
      leaf port {
        type inet:port-number;
        description
          "Radius server port.";
      }
      leaf oper-state {
        type pon-ctrl:ncs_rpc_notif_radius-server-oper-state;
        description
          "Operational state of the radius server.";
      }
    }
  }
  augment "/ncs:devices/ncs:device/ncs:netconf-notifications/ncs:received-notifications/ncs:notification/ncs:data" {
    container uni-port-oper-state-change {
      presence "";
      config false;
      description
        "Generated when the operational state of an ONU UNI Port changes.";
      leaf olt {
        type pon-ctrl:ncs_rpc_notif_olt-ref;
        description
          "Name of the OLT.";
      }
      leaf onu {
        type pon-ctrl:ncs_rpc_notif_onu-ref;
        description
          "Name of the ONU.";
      }
      leaf uni-port {
        type pon-ctrl:ncs_rpc_notif_uni-port-ref;
        description
          "ID of the UNI Port whose operational state has changed.";
      }
      leaf oper-state {
        type pon-ctrl:ncs_rpc_notif_uni-port-oper-state;
        description
          "Operational state of the UNI Port.";
      }
      leaf speed {
        type pon-ctrl:ncs_rpc_notif_uni-port-oper-speed;
        description
          "Operational speed of the UNI Port
           Set when the oper-state of the ONU is 'up'.";
      }
      leaf duplex {
        type pon-ctrl:ncs_rpc_notif_uni-port-oper-duplex;
        description
          "Operational duplex of the UNI Port.
           Set when the oper-state of the ONU is 'up'.";
      }
    }
  }
  augment "/ncs:devices/ncs:device/ncs:netconf-notifications/ncs:received-notifications/ncs:notification/ncs:data" {
    container onu-oper-state-change {
      presence "";
      config false;
      description
        "Generated when the operational state of an ONU changes.";
      leaf olt {
        type pon-ctrl:ncs_rpc_notif_olt-ref;
        description
          "Name of the OLT.";
      }
      leaf onu {
        type pon-ctrl:ncs_rpc_notif_onu-ref;
        description
          "Name of the ONU whose operational state has changed.";
      }
      leaf oper-state {
        type pon-ctrl:ncs_rpc_notif_onu-oper-state;
        description
          "Operational state of the ONU.";
      }
      leaf deregister-reason {
        type string;
        description
          "The reason for the last ONU deregistration.
           Set when the oper-state of the ONU is 'deregistered'.";
      }
    }
  }
  augment "/ncs:devices/ncs:device/ncs:netconf-notifications/ncs:received-notifications/ncs:notification/ncs:data" {
    container olt-oper-state-change {
      presence "";
      config false;
      description
        "Generated when the operational state of an OLT changes.";
      leaf olt {
        type pon-ctrl:ncs_rpc_notif_olt-ref;
        description
          "Name of the OLT whose operational state has changed.";
      }
      leaf oper-state {
        type pon-ctrl:ncs_rpc_notif_olt-oper-state;
        description
          "Operational state of the OLT.";
      }
    }
  }
  augment "/ncs:devices/ncs:device/ncs:netconf-notifications/ncs:received-notifications/ncs:notification/ncs:data" {
    container onu-discovered {
      presence "";
      config false;
      description
        "Generated when a new ONU is discovered on an OLT and has not yet been configured.";
      leaf olt {
        type pon-ctrl:ncs_rpc_notif_olt-ref;
        description
          "Name of the OLT on which this ONU was discovered.";
      }
      leaf onu-serial-number {
        type string {
          pattern '[a-zA-Z]{4}[0-9a-fA-F]{8}';
        }
        description
          "The serial number of the discovered ONU.";
      }
    }
  }
  augment "/ncs:devices/ncs:device/ncs:netconf-notifications/ncs:received-notifications/ncs:notification/ncs:data" {
    container olt-discovered {
      presence "";
      config false;
      description
        "Generated when a new OLT is discovered on an interface and has not yet been configured.";
      leaf l3-interface {
        type pon-ctrl:ncs_rpc_notif_interface-ref;
        description
          "Name of the L3 interface on which this OLT was discovered.";
      }
      leaf olt-mac-address {
        type yang:mac-address;
        description
          "The MAC address of the discovered OLT.";
      }
    }
  }
  augment "/ncs:devices/ncs:device/ncs:config" {
    container pon-ctrl {
      tailf:ncs-device-type "netconf";
      tailf:display-when "not(../../ncs:module) or ../../ncs:module[ncs:name='ciena-pon-ctrl']";
      description
        "PON configuration data.";
      container radius-servers {
        description
          "The configuration data for all radius servers.";
        list radius-server {
          key "name";
          description
            "An radius server on the system.";
          leaf name {
            type pon-ctrl:name-string;
            description
              "Name of the Radius Server.";
          }
          leaf management-interface {
            type pon-ctrl:interface-ref;
            must "/oc-if:interfaces/oc-if:interface[oc-if:name = current()]/oc-if:config/cn-if:type = 'ip'" {
              tailf:xpath-root 3;
              error-message "Referenced interface must be of type 'ip'.";
            }
            mandatory true;
            description
              "Reference to the L3 interface on which this OLT is to be
               managed.";
          }
          leaf shared-secret {
            ncx:password;
            type pon-ctrl:pon-relay-attribute-string;
            description
              "Shared secret string.";
          }
          leaf revive-interval {
            type uint32;
            description
              "Revive interval.";
          }
          leaf failure-threshold {
            type uint32;
            description
              "Failure Threshold.";
          }
          leaf uam-username {
            type pon-ctrl:pon-relay-attribute-string;
            default "username";
            description
              "Universal access method username.";
          }
          leaf uam-enable {
            type boolean;
            default "false";
            description
              "Universal access method enable.";
          }
          leaf uam-recover-threshold {
            type uint32;
            default "2";
            description
              "Universal access method recover threshold.";
          }
          leaf uam-check-interval {
            type uint32;
            units "seconds";
            default "60";
            description
              "Universal access method check internval (seconds).";
          }
          uses pon-ctrl-radius-server-grouping;
        }
      }
      container olts {
        description
          "The configuration data for all OLTs.";
        list olt {
          key "name";
          description
            "An OLT on the system.";
          leaf name {
            type pon-ctrl:name-string;
            description
              "Name of the OLT.";
          }
          leaf admin-state {
            type ciena:admin-state;
            default "enabled";
            description
              "Enable or disable the OLT.";
          }
          leaf mac-address {
            type yang:mac-address;
            mandatory true;
            description
              "The MAC address of the OLT.";
          }
          leaf management-interface {
            type pon-ctrl:interface-ref;
            must "/oc-if:interfaces/oc-if:interface[oc-if:name = current()]/oc-if:config/cn-if:type = 'ip'" {
              tailf:xpath-root 3;
              error-message "Referenced interface must be of type 'ip'.";
            }
            mandatory true;
            description
              "Reference to the L3 interface on which this OLT is to be
               managed.";
          }
          leaf pon-mode {
            type pon-ctrl:pon-mode;
            default "xgs-pon";
            description
              "The PON mode this OLT will operate in.";
          }
          leaf auto-assigned-ids {
            type ciena:admin-state;
            default "enabled";
            description
              "Enable or disable automatic ONU-ID and ALLOC-ID assignment on the OLT. Only valid in XGS-PON mode.
               Note, when enabled the OLT will automatically register ONUs discovered on the PON.";
          }
          leaf auto-onu-upgrade {
            type ciena:admin-state;
            default "disabled";
            description
              "Enable or disable automatic ONU upgrades on the OLT.
               Note, this only applies to ONUs where the expected firmware version is known and where
               the firmware status is set to 'Upgrade Required'.";
          }
          leaf auto-boot-mode {
            type ciena:admin-state;
            default "disabled";
            description
              "Enable or disable autonomous boot mode on the OLT.";
          }
          leaf upstream-fec-0 {
            when "../pon-mode = 'xgs-pon'" {
              tailf:xpath-root 3;
            }
            type ciena:admin-state;
            default "enabled";
            description
              "Enable or disable upstream FEC (Forward Error Correction)
               for burst profile 0 on the OLT in XGS-PON mode.";
          }
          leaf upstream-preamble-0 {
            when "../pon-mode = 'xgs-pon'" {
              tailf:xpath-root 3;
            }
            type uint16 {
              range "16..1000";
            }
            default "64";
            description
              "The amount of preamble at the start of burst for profile 0
               on the OLT in XGS-PON mode; measured in units of upstream slots (12.8ns).";
          }
          leaf downstream-fec {
            type ciena:admin-state;
            default "enabled";
            description
              "Enable or disable downstream FEC (Forward Error Correction) on the OLT.";
          }
          leaf encryption-mode {
            type pon-ctrl:encryption-mode;
            default "disabled";
            description
              "The encryption mode on the OLT.";
          }
          leaf guard-time {
            when "../pon-mode = 'xgs-pon'" {
              tailf:xpath-root 3;
            }
            type uint16 {
              range "16..1000";
            }
            default "16";
            description
              "The guard time used by the OLT in XGS-PON mode.
               This is the amount of dead time between upstream burst slots
               measured in units of upstream slots (12.8ns).";
          }
          leaf max-nni-frame-size {
            type uint16 {
              range "512..12500";
            }
            default "9600";
            description
              "The NNI port's MTU on the OLT.
               Maximum supported MTU is 9600 in XGS-PON mode and
               12500 in 10G-EPON mode.";
          }
          leaf max-pon-frame-size {
            type uint16 {
              range "512..12500";
            }
            default "9600";
            description
              "The PON port's MTU on the OLT.
               Maximum supported MTU is 9600 in XGS-PON mode and
               12500 in 10G-EPON mode.";
          }
          container nni-networks {
            description
              "The configuration data for all NNI Networks.
               NNI Networks are the configuration construct that enables user traffic to flow through the OLT.
               Inside the OLT, an NNI Network is a Layer-2 Switching Domain (an instance of an IEEE 802.1Q MAC
               Bridge and Virtual Bridge). Like any bridge, a network in the OLT has ports. In the OLT, the bridge ports
               for an NNI Network are the Datalinks (an LLID in 10G-EPON, and an XGEM port in XGS-PON) configured for each ONU and the OLT.";
            list nni-network {
              key "name";
              description
                "An NNI Network used by the OLT.";
              leaf name {
                type pon-ctrl:name-string;
                description
                  "Name of the NNI Network.";
              }
              leaf flooding-link {
                type ciena:admin-state;
                default "enabled";
                description
                  "Controls the creation of a flooding link on the NNI Network.
                   If the flooding link is disabled on the NNI Network then only one PON Connection will be
                   allowed to be created on the NNI Network. In that scenario, any flooding traffic on the NNI Network
                   will use the Datalink specified by that PON Connection.";
              }
              uses pon-ctrl:tag-match-grouping;
              uses pon-ctrl:tag-options-grouping;
            }
          }
          container cross-connects {
            description
              "The configuration data for all Cross Connects.
               Cross Connects are the configuration construct that enables user traffic to flow between ONUs via the OLT.
               To cross-connect two ONUs, a Datalink from each ONU must be attached to the same Cross Connect via the PON Connection
               configuration.";
            list cross-connect {
              key "name";
              description
                "A Cross Connect used by the OLT.";
              leaf name {
                type pon-ctrl:name-string;
                description
                  "Name of the Cross Connect.";
              }
            }
          }
        }
      }
      container onus {
        description
          "The configuration data for all ONUs.";
        list onu {
          key "name olt";
          description
            "An ONU used by the OLT.";
          leaf name {
            type pon-ctrl:name-string;
            description
              "Name of the ONU.";
          }
          leaf olt {
            type pon-ctrl:olt-ref;
            mandatory true;
            description
              "Name of the OLT this ONU is subtended from.";
          }
          leaf admin-state {
            type ciena:admin-state;
            default "enabled";
            description
              "Enable or disable the ONU. Sends a Disable_Serial_Number PLOAM message to the ONU.";
          }
          leaf serial-number {
            type string {
              pattern '[a-zA-Z]{4}[0-9a-fA-F]{8}';
            }
            mandatory true;
            description
              "The serial number the OLT expects to retrieve from the ONU.";
          }
          leaf onu-id {
            type uint16 {
              range "1..128";
            }
            description
              "The ONU-ID that will be assigned to the ONU.";
          }
          leaf auto-upgrade-firmware-file-name {
            type pon-ctrl:name-string;
            description
              "Name of the firmware file to use when auto-upgrading this ONU.
               Note, this will only take effect when the 'auto-onu-upgrade' option
               is enabled on the OLT.";
          }
          leaf auto-upgrade-defer-activation {
            type boolean;
            description
              "When set to true, ONU firmware activation after auto-upgrading
               this ONU is deferred until explicitly invoked.
               Note, this will only take effect when the 'auto-onu-upgrade' option
               is enabled on the OLT.";
          }
          container datalinks {
            description
              "The configuration data for all Datalinks.
               A Datalink is an LLID in 10G-EPON mode or an XGEM port in XGS-PON mode.";
            list datalink {
              key "name";
              description
                "A Datalink used by the ONU.";
              leaf name {
                type pon-ctrl:name-string;
                description
                  "Name of the Datalink.";
              }
              leaf admin-state {
                type ciena:admin-state;
                default "enabled";
                description
                  "Enable or disable traffic on this Datalink.";
              }
              leaf-list uni-ports {
                type uint8 {
                  range "1..5";
                }
                min-elements 1;
                max-elements 5;
                description
                  "List of ONU UNI Ports to apply the Datalink on.";
              }
              leaf-list vlan-ids {
                type pon-ctrl:tag-match-vid;
                max-elements 12;
                description
                  "List of VLAN IDs to be forwarded on this Datalink.
                   Traffic will only be allowed on this Datalink if it matches
                   one of the values specified. Not specifying this field or
                   specifying a value of 65535 will match on any VID value,
                   no VLAN tag or a priority tag. Values specified must be unique
                   across all Datalinks on the same UNI Port.";
              }
              leaf sla-profile {
                type pon-ctrl:sla-profile-ref;
                mandatory true;
                description
                  "Name of the SLA Profile this Datalink implements.";
              }
              leaf add-ctag {
                type mef-fp:vlan-id;
                description
                  "Add an optional C-Tag at the ONU for all upstream traffic on this Datalink.
                   This tag is popped (removed) in the downstream direction.";
              }
              leaf add-ctag-pcp {
                when '../add-ctag' {
                  tailf:xpath-root 3;
                }
                type uint8 {
                  range "0..7";
                }
                description
                  "Specify the 802.1p priority of the added C-Tag on this Datalink.
                   This is only valid when the add-ctag parameter is specified.
                   When this field is not specified, a PCP value of 0 is assumed for
                   untagged frames. For tagged frames the PCP value of the added C-Tag
                   is copied from the existing VLAN.";
              }
              uses pon-ctrl:dhcp-grouping;
              uses pon-ctrl:radius-grouping;
              leaf alloc-id {
                type uint16 {
                  range "1154..1535";
                }
                must '. != 1278' {
                  tailf:xpath-root 3;
                  error-message "Illegal value for ALLOC-ID. ALLOC-ID 1278 is reserved.";
                }
                description
                  "The configured ALLOC-ID of this Datalink.
                   Only valid in XGS-PON mode.";
              }
            }
          }
          container pon-connections {
            description
              "The configuration data for all PON Connections.
               PON Connections are the configuration construct that links a Datalink on the ONU to
               an NNI Network or Cross Connect on the OLT.";
            list pon-connection {
              key "name";
              description
                "A PON Connection used by the ONU.";
              leaf name {
                type pon-ctrl:name-string;
                description
                  "Name of the PON Connection.";
              }
              leaf datalink {
                type leafref {
                  path "../../../datalinks/datalink/name";
                }
                mandatory true;
                description
                  "Reference to the Datalink on the ONU.
                   Datalink must be configured on the same ONU as this PON Connection.";
              }
              leaf nni-network {
                when 'not(../cross-connect)' {
                  tailf:xpath-root 3;
                }
                type leafref {
                  path "/ncs:devices/ncs:device/ncs:config/pon-ctrl:pon-ctrl/pon-ctrl:olts/pon-ctrl:olt[name=current()/../../../olt]/pon-ctrl:nni-networks/pon-ctrl:nni-network/pon-ctrl:name" {
                    tailf:xpath-root 3;
                  }
                }
                mandatory true;
                description
                  "Reference to the NNI Network on the OLT.
                   NNI Network must be configured on the same OLT as the ONU where this PON Connection exists.
                   The NNI Network reference is mutually exclusive with the Cross Connect reference.";
              }
              leaf cross-connect {
                when 'not(../nni-network)' {
                  tailf:xpath-root 3;
                }
                type leafref {
                  path "/ncs:devices/ncs:device/ncs:config/pon-ctrl:pon-ctrl/pon-ctrl:olts/pon-ctrl:olt[name=current()/../../../olt]/pon-ctrl:cross-connects/pon-ctrl:cross-connect/pon-ctrl:name" {
                    tailf:xpath-root 3;
                  }
                }
                mandatory true;
                description
                  "Reference to the Cross Connect on the OLT.
                   Cross Connect must be configured on the same OLT as the ONU where this PON Connection exists.
                   The Cross Connect reference is mutually exclusive with the NNI Network reference.";
              }
              uses pon-ctrl:tag-match-grouping;
              uses pon-ctrl:tag-options-grouping;
            }
          }
          container uni-ports {
            description
              "The configuration data for all UNI Ports.
               This configuration construct is optional and can be used to modify specific UNI Port parameters
               under this ONU.";
            list uni-port {
              key "name";
              max-elements 5;
              description
                "A UNI Port on the ONU.";
              leaf name {
                type pon-ctrl:name-string;
                description
                  "The numerical identifier of this UNI Port.
                   Must be a numercical value between 1 and 5.";
              }
              leaf description {
                type pon-ctrl:name-string;
                description
                  "A string description of this UNI Port.";
              }
              leaf admin-state {
                type ciena:admin-state;
                default "enabled";
                description
                  "Enable or disable the UNI Port.";
              }
              leaf max-frame-size {
                type uint16 {
                  range "64..9216";
                }
                default "9216";
                description
                  "The UNI Port's configured MTU.";
              }
              leaf speed {
                type pon-ctrl:uni-port-speed;
                default "auto";
                description
                  "The UNI Port's configured speed.";
              }
              leaf duplex {
                type pon-ctrl:uni-port-duplex;
                default "auto";
                description
                  "The UNI Port's configured duplex.";
              }
              leaf stats-collection {
                type ciena:admin-state;
                default "disabled";
                description
                  "Determines whether stats collection will be enabled or disabled for the UNI Port.";
              }
            }
          }
        }
      }
      container sla-profiles {
        description
          "The configuration data for all SLA Profiles.";
        list sla-profile {
          key "name";
          description
            "An SLA Profile used by a Datalink.";
          leaf name {
            type pon-ctrl:name-string;
            description
              "Name of the SLA Profile.";
          }
          leaf up-fixed-rate {
            type uint32 {
              range "0..8000000";
            }
            units "Kbps";
            default "0";
            description
              "Fixed grant rate in Kbps. This is an unsolicited
               grant by the DBA regardless of need.";
          }
          leaf up-guaranteed-rate {
            type uint32 {
              range "0 | 128..10000000";
            }
            units "Kbps";
            default "128";
            description
              "Guaranteed (high priority) upstream rate in Kbps.";
          }
          leaf up-guaranteed-max-burst {
            type uint32 {
              range "16000..1000000";
            }
            units "Bytes";
            default "409600";
            description
              "Maximum upstream burst size in Bytes. The
               guaranteed rate is enforced at this burst size.";
          }
          leaf up-best-effort-rate {
            type uint32 {
              range "0 | 128..10000000";
            }
            units "Kbps";
            default "10000000";
            description
              "Best Effort (low priority) upstream rate in Kbps.";
          }
          leaf up-best-effort-max-burst {
            type uint32 {
              range "16000..1000000";
            }
            units "Bytes";
            default "409600";
            description
              "Maximum upstream burst size in Bytes. The best
               effort rate is enforced at this burst size.";
          }
          leaf up-priority {
            type uint8 {
              range "1..8";
            }
            default "1";
            description
              "Priority level for the Guaranteed portion of the SLA.";
          }
          leaf up-service-limit {
            type uint16 {
              range "2..150";
            }
            units "kBytes";
            default "128";
            description
              "Maximum grant size for an upstream slot in Kilobytes.";
          }
          leaf up-min-grant-period {
            type uint16 {
              range "0..100";
            }
            default "0";
            description
              "The minimum allowed spacing between grants on this service.";
          }
          leaf up-max-grant-period {
            type uint16 {
              range "3..200";
            }
            default "10";
            description
              "The maximum allowed time between grants on
               this service. This field will cause a polling grant
               when the ONU is idle.";
          }
          leaf down-guaranteed-rate {
            type uint32 {
              range "0 | 128..10000000";
            }
            units "Kbps";
            default "128";
            description
              "Guaranteed (high priority) downstream rate in Kbps.";
          }
          leaf down-guaranteed-max-burst {
            type uint32 {
              range "16000..1000000";
            }
            units "Bytes";
            default "409600";
            description
              "Maximum downstream burst size in Bytes. The
               guaranteed rate is enforced at this burst size.";
          }
          leaf down-best-effort-rate {
            type uint32 {
              range "0 | 128..10000000";
            }
            units "Kbps";
            default "10000000";
            description
              "Best Effort (low priority) downstream rate in Kbps.";
          }
          leaf down-best-effort-max-burst {
            type uint32 {
              range "16000..1000000";
            }
            units "Bytes";
            default "409600";
            description
              "Maximum downstream burst size in Bytes. The best
               effort rate is enforced at this burst size.";
          }
        }
      }
    }
    // NCS drop config false container 'pon-ctrl-state'
  }
  augment "/ncs:devices/ncs:device/ncs:live-status" {
    container pon-ctrl {
      tailf:ncs-device-type "netconf";
      tailf:display-when "not(../../ncs:module) or ../../ncs:module[ncs:name='ciena-pon-ctrl'] or (../../ncs:live-status-protocol[not(ncs:capability)]) or (../../ncs:live-status-protocol/ncs:capability/ncs:module[.='ciena-pon-ctrl'])";
      description
        "PON configuration data.";
      container radius-servers {
        description
          "The configuration data for all radius servers.";
        list radius-server {
          key "name";
          description
            "An radius server on the system.";
          leaf name {
            type pon-ctrl:live_ncs_name-string;
            description
              "Name of the Radius Server.";
          }
          leaf management-interface {
            type pon-ctrl:live_ncs_interface-ref;
            // NCS drop must statement
            // NCS drop mandatory statement
            description
              "Reference to the L3 interface on which this OLT is to be
               managed.";
          }
          leaf shared-secret {
            ncx:password;
            type pon-ctrl:live_ncs_pon-relay-attribute-string;
            description
              "Shared secret string.";
          }
          leaf revive-interval {
            type uint32;
            description
              "Revive interval.";
          }
          leaf failure-threshold {
            type uint32;
            description
              "Failure Threshold.";
          }
          leaf uam-username {
            type pon-ctrl:live_ncs_pon-relay-attribute-string;
            // NCS drop default statement
            description
              "Universal access method username.";
          }
          leaf uam-enable {
            type boolean;
            // NCS drop default statement
            description
              "Universal access method enable.";
          }
          leaf uam-recover-threshold {
            type uint32;
            // NCS drop default statement
            description
              "Universal access method recover threshold.";
          }
          leaf uam-check-interval {
            type uint32;
            units "seconds";
            // NCS drop default statement
            description
              "Universal access method check internval (seconds).";
          }
          uses live_ncs_pon-ctrl-radius-server-grouping;
        }
      }
      container olts {
        description
          "The configuration data for all OLTs.";
        list olt {
          key "name";
          description
            "An OLT on the system.";
          leaf name {
            type pon-ctrl:live_ncs_name-string;
            description
              "Name of the OLT.";
          }
          leaf admin-state {
            type ciena:live_ncs_admin-state;
            // NCS drop default statement
            description
              "Enable or disable the OLT.";
          }
          leaf mac-address {
            type yang:mac-address;
            // NCS drop mandatory statement
            description
              "The MAC address of the OLT.";
          }
          leaf management-interface {
            type pon-ctrl:live_ncs_interface-ref;
            // NCS drop must statement
            // NCS drop mandatory statement
            description
              "Reference to the L3 interface on which this OLT is to be
               managed.";
          }
          leaf pon-mode {
            type pon-ctrl:live_ncs_pon-mode;
            // NCS drop default statement
            description
              "The PON mode this OLT will operate in.";
          }
          leaf auto-assigned-ids {
            type ciena:live_ncs_admin-state;
            // NCS drop default statement
            description
              "Enable or disable automatic ONU-ID and ALLOC-ID assignment on the OLT. Only valid in XGS-PON mode.
               Note, when enabled the OLT will automatically register ONUs discovered on the PON.";
          }
          leaf auto-onu-upgrade {
            type ciena:live_ncs_admin-state;
            // NCS drop default statement
            description
              "Enable or disable automatic ONU upgrades on the OLT.
               Note, this only applies to ONUs where the expected firmware version is known and where
               the firmware status is set to 'Upgrade Required'.";
          }
          leaf auto-boot-mode {
            type ciena:live_ncs_admin-state;
            // NCS drop default statement
            description
              "Enable or disable autonomous boot mode on the OLT.";
          }
          leaf upstream-fec-0 {
            // NCS drop when statement
            type ciena:live_ncs_admin-state;
            // NCS drop default statement
            description
              "Enable or disable upstream FEC (Forward Error Correction)
               for burst profile 0 on the OLT in XGS-PON mode.";
          }
          leaf upstream-preamble-0 {
            // NCS drop when statement
            type uint16 {
              range "16..1000";
            }
            // NCS drop default statement
            description
              "The amount of preamble at the start of burst for profile 0
               on the OLT in XGS-PON mode; measured in units of upstream slots (12.8ns).";
          }
          leaf downstream-fec {
            type ciena:live_ncs_admin-state;
            // NCS drop default statement
            description
              "Enable or disable downstream FEC (Forward Error Correction) on the OLT.";
          }
          leaf encryption-mode {
            type pon-ctrl:live_ncs_encryption-mode;
            // NCS drop default statement
            description
              "The encryption mode on the OLT.";
          }
          leaf guard-time {
            // NCS drop when statement
            type uint16 {
              range "16..1000";
            }
            // NCS drop default statement
            description
              "The guard time used by the OLT in XGS-PON mode.
               This is the amount of dead time between upstream burst slots
               measured in units of upstream slots (12.8ns).";
          }
          leaf max-nni-frame-size {
            type uint16 {
              range "512..12500";
            }
            // NCS drop default statement
            description
              "The NNI port's MTU on the OLT.
               Maximum supported MTU is 9600 in XGS-PON mode and
               12500 in 10G-EPON mode.";
          }
          leaf max-pon-frame-size {
            type uint16 {
              range "512..12500";
            }
            // NCS drop default statement
            description
              "The PON port's MTU on the OLT.
               Maximum supported MTU is 9600 in XGS-PON mode and
               12500 in 10G-EPON mode.";
          }
          container nni-networks {
            description
              "The configuration data for all NNI Networks.
               NNI Networks are the configuration construct that enables user traffic to flow through the OLT.
               Inside the OLT, an NNI Network is a Layer-2 Switching Domain (an instance of an IEEE 802.1Q MAC
               Bridge and Virtual Bridge). Like any bridge, a network in the OLT has ports. In the OLT, the bridge ports
               for an NNI Network are the Datalinks (an LLID in 10G-EPON, and an XGEM port in XGS-PON) configured for each ONU and the OLT.";
            list nni-network {
              key "name";
              description
                "An NNI Network used by the OLT.";
              leaf name {
                type pon-ctrl:live_ncs_name-string;
                description
                  "Name of the NNI Network.";
              }
              leaf flooding-link {
                type ciena:live_ncs_admin-state;
                // NCS drop default statement
                description
                  "Controls the creation of a flooding link on the NNI Network.
                   If the flooding link is disabled on the NNI Network then only one PON Connection will be
                   allowed to be created on the NNI Network. In that scenario, any flooding traffic on the NNI Network
                   will use the Datalink specified by that PON Connection.";
              }
              uses pon-ctrl:live_ncs_tag-match-grouping;
              uses pon-ctrl:live_ncs_tag-options-grouping;
            }
          }
          container cross-connects {
            description
              "The configuration data for all Cross Connects.
               Cross Connects are the configuration construct that enables user traffic to flow between ONUs via the OLT.
               To cross-connect two ONUs, a Datalink from each ONU must be attached to the same Cross Connect via the PON Connection
               configuration.";
            list cross-connect {
              key "name";
              description
                "A Cross Connect used by the OLT.";
              leaf name {
                type pon-ctrl:live_ncs_name-string;
                description
                  "Name of the Cross Connect.";
              }
            }
          }
        }
      }
      container onus {
        description
          "The configuration data for all ONUs.";
        list onu {
          key "name olt";
          description
            "An ONU used by the OLT.";
          leaf name {
            type pon-ctrl:live_ncs_name-string;
            description
              "Name of the ONU.";
          }
          leaf olt {
            type pon-ctrl:live_ncs_olt-ref;
            // NCS drop mandatory statement
            description
              "Name of the OLT this ONU is subtended from.";
          }
          leaf admin-state {
            type ciena:live_ncs_admin-state;
            // NCS drop default statement
            description
              "Enable or disable the ONU. Sends a Disable_Serial_Number PLOAM message to the ONU.";
          }
          leaf serial-number {
            type string {
              pattern '[a-zA-Z]{4}[0-9a-fA-F]{8}';
            }
            // NCS drop mandatory statement
            description
              "The serial number the OLT expects to retrieve from the ONU.";
          }
          leaf onu-id {
            type uint16 {
              range "1..128";
            }
            description
              "The ONU-ID that will be assigned to the ONU.";
          }
          leaf auto-upgrade-firmware-file-name {
            type pon-ctrl:live_ncs_name-string;
            description
              "Name of the firmware file to use when auto-upgrading this ONU.
               Note, this will only take effect when the 'auto-onu-upgrade' option
               is enabled on the OLT.";
          }
          leaf auto-upgrade-defer-activation {
            type boolean;
            description
              "When set to true, ONU firmware activation after auto-upgrading
               this ONU is deferred until explicitly invoked.
               Note, this will only take effect when the 'auto-onu-upgrade' option
               is enabled on the OLT.";
          }
          container datalinks {
            description
              "The configuration data for all Datalinks.
               A Datalink is an LLID in 10G-EPON mode or an XGEM port in XGS-PON mode.";
            list datalink {
              key "name";
              description
                "A Datalink used by the ONU.";
              leaf name {
                type pon-ctrl:live_ncs_name-string;
                description
                  "Name of the Datalink.";
              }
              leaf admin-state {
                type ciena:live_ncs_admin-state;
                // NCS drop default statement
                description
                  "Enable or disable traffic on this Datalink.";
              }
              leaf-list uni-ports {
                type uint8 {
                  range "1..5";
                }
                // NCS drop min-elements statement
                // NCS drop max-elements statement
                description
                  "List of ONU UNI Ports to apply the Datalink on.";
              }
              leaf-list vlan-ids {
                type pon-ctrl:live_ncs_tag-match-vid;
                // NCS drop max-elements statement
                description
                  "List of VLAN IDs to be forwarded on this Datalink.
                   Traffic will only be allowed on this Datalink if it matches
                   one of the values specified. Not specifying this field or
                   specifying a value of 65535 will match on any VID value,
                   no VLAN tag or a priority tag. Values specified must be unique
                   across all Datalinks on the same UNI Port.";
              }
              leaf sla-profile {
                type pon-ctrl:live_ncs_sla-profile-ref;
                // NCS drop mandatory statement
                description
                  "Name of the SLA Profile this Datalink implements.";
              }
              leaf add-ctag {
                type mef-fp:live_ncs_vlan-id;
                description
                  "Add an optional C-Tag at the ONU for all upstream traffic on this Datalink.
                   This tag is popped (removed) in the downstream direction.";
              }
              leaf add-ctag-pcp {
                // NCS drop when statement
                type uint8 {
                  range "0..7";
                }
                description
                  "Specify the 802.1p priority of the added C-Tag on this Datalink.
                   This is only valid when the add-ctag parameter is specified.
                   When this field is not specified, a PCP value of 0 is assumed for
                   untagged frames. For tagged frames the PCP value of the added C-Tag
                   is copied from the existing VLAN.";
              }
              uses pon-ctrl:live_ncs_dhcp-grouping;
              uses pon-ctrl:live_ncs_radius-grouping;
              leaf alloc-id {
                type uint16 {
                  range "1154..1535";
                }
                // NCS drop must statement
                description
                  "The configured ALLOC-ID of this Datalink.
                   Only valid in XGS-PON mode.";
              }
            }
          }
          container pon-connections {
            description
              "The configuration data for all PON Connections.
               PON Connections are the configuration construct that links a Datalink on the ONU to
               an NNI Network or Cross Connect on the OLT.";
            list pon-connection {
              key "name";
              description
                "A PON Connection used by the ONU.";
              leaf name {
                type pon-ctrl:live_ncs_name-string;
                description
                  "Name of the PON Connection.";
              }
              leaf datalink {
                type leafref {
                  path "../../../datalinks/datalink/name";
                }
                // NCS drop mandatory statement
                description
                  "Reference to the Datalink on the ONU.
                   Datalink must be configured on the same ONU as this PON Connection.";
              }
              leaf nni-network {
                // NCS drop when statement
                type leafref {
                  path "/ncs:devices/ncs:device/ncs:live-status/pon-ctrl:pon-ctrl/pon-ctrl:olts/pon-ctrl:olt[name=current()/../../../olt]/pon-ctrl:nni-networks/pon-ctrl:nni-network/pon-ctrl:name" {
                    tailf:xpath-root 3;
                  }
                }
                // NCS drop mandatory statement
                description
                  "Reference to the NNI Network on the OLT.
                   NNI Network must be configured on the same OLT as the ONU where this PON Connection exists.
                   The NNI Network reference is mutually exclusive with the Cross Connect reference.";
              }
              leaf cross-connect {
                // NCS drop when statement
                type leafref {
                  path "/ncs:devices/ncs:device/ncs:live-status/pon-ctrl:pon-ctrl/pon-ctrl:olts/pon-ctrl:olt[name=current()/../../../olt]/pon-ctrl:cross-connects/pon-ctrl:cross-connect/pon-ctrl:name" {
                    tailf:xpath-root 3;
                  }
                }
                // NCS drop mandatory statement
                description
                  "Reference to the Cross Connect on the OLT.
                   Cross Connect must be configured on the same OLT as the ONU where this PON Connection exists.
                   The Cross Connect reference is mutually exclusive with the NNI Network reference.";
              }
              uses pon-ctrl:live_ncs_tag-match-grouping;
              uses pon-ctrl:live_ncs_tag-options-grouping;
            }
          }
          container uni-ports {
            description
              "The configuration data for all UNI Ports.
               This configuration construct is optional and can be used to modify specific UNI Port parameters
               under this ONU.";
            list uni-port {
              key "name";
              // NCS drop max-elements statement
              description
                "A UNI Port on the ONU.";
              leaf name {
                type pon-ctrl:live_ncs_name-string;
                description
                  "The numerical identifier of this UNI Port.
                   Must be a numercical value between 1 and 5.";
              }
              leaf description {
                type pon-ctrl:live_ncs_name-string;
                description
                  "A string description of this UNI Port.";
              }
              leaf admin-state {
                type ciena:live_ncs_admin-state;
                // NCS drop default statement
                description
                  "Enable or disable the UNI Port.";
              }
              leaf max-frame-size {
                type uint16 {
                  range "64..9216";
                }
                // NCS drop default statement
                description
                  "The UNI Port's configured MTU.";
              }
              leaf speed {
                type pon-ctrl:live_ncs_uni-port-speed;
                // NCS drop default statement
                description
                  "The UNI Port's configured speed.";
              }
              leaf duplex {
                type pon-ctrl:live_ncs_uni-port-duplex;
                // NCS drop default statement
                description
                  "The UNI Port's configured duplex.";
              }
              leaf stats-collection {
                type ciena:live_ncs_admin-state;
                // NCS drop default statement
                description
                  "Determines whether stats collection will be enabled or disabled for the UNI Port.";
              }
            }
          }
        }
      }
      container sla-profiles {
        description
          "The configuration data for all SLA Profiles.";
        list sla-profile {
          key "name";
          description
            "An SLA Profile used by a Datalink.";
          leaf name {
            type pon-ctrl:live_ncs_name-string;
            description
              "Name of the SLA Profile.";
          }
          leaf up-fixed-rate {
            type uint32 {
              range "0..8000000";
            }
            units "Kbps";
            // NCS drop default statement
            description
              "Fixed grant rate in Kbps. This is an unsolicited
               grant by the DBA regardless of need.";
          }
          leaf up-guaranteed-rate {
            type uint32 {
              range "0 | 128..10000000";
            }
            units "Kbps";
            // NCS drop default statement
            description
              "Guaranteed (high priority) upstream rate in Kbps.";
          }
          leaf up-guaranteed-max-burst {
            type uint32 {
              range "16000..1000000";
            }
            units "Bytes";
            // NCS drop default statement
            description
              "Maximum upstream burst size in Bytes. The
               guaranteed rate is enforced at this burst size.";
          }
          leaf up-best-effort-rate {
            type uint32 {
              range "0 | 128..10000000";
            }
            units "Kbps";
            // NCS drop default statement
            description
              "Best Effort (low priority) upstream rate in Kbps.";
          }
          leaf up-best-effort-max-burst {
            type uint32 {
              range "16000..1000000";
            }
            units "Bytes";
            // NCS drop default statement
            description
              "Maximum upstream burst size in Bytes. The best
               effort rate is enforced at this burst size.";
          }
          leaf up-priority {
            type uint8 {
              range "1..8";
            }
            // NCS drop default statement
            description
              "Priority level for the Guaranteed portion of the SLA.";
          }
          leaf up-service-limit {
            type uint16 {
              range "2..150";
            }
            units "kBytes";
            // NCS drop default statement
            description
              "Maximum grant size for an upstream slot in Kilobytes.";
          }
          leaf up-min-grant-period {
            type uint16 {
              range "0..100";
            }
            // NCS drop default statement
            description
              "The minimum allowed spacing between grants on this service.";
          }
          leaf up-max-grant-period {
            type uint16 {
              range "3..200";
            }
            // NCS drop default statement
            description
              "The maximum allowed time between grants on
               this service. This field will cause a polling grant
               when the ONU is idle.";
          }
          leaf down-guaranteed-rate {
            type uint32 {
              range "0 | 128..10000000";
            }
            units "Kbps";
            // NCS drop default statement
            description
              "Guaranteed (high priority) downstream rate in Kbps.";
          }
          leaf down-guaranteed-max-burst {
            type uint32 {
              range "16000..1000000";
            }
            units "Bytes";
            // NCS drop default statement
            description
              "Maximum downstream burst size in Bytes. The
               guaranteed rate is enforced at this burst size.";
          }
          leaf down-best-effort-rate {
            type uint32 {
              range "0 | 128..10000000";
            }
            units "Kbps";
            // NCS drop default statement
            description
              "Best Effort (low priority) downstream rate in Kbps.";
          }
          leaf down-best-effort-max-burst {
            type uint32 {
              range "16000..1000000";
            }
            units "Bytes";
            // NCS drop default statement
            description
              "Maximum downstream burst size in Bytes. The best
               effort rate is enforced at this burst size.";
          }
        }
      }
    }
    container pon-ctrl-state {
      tailf:ncs-device-type "netconf";
      tailf:display-when "not(../../ncs:module) or ../../ncs:module[ncs:name='ciena-pon-ctrl'] or (../../ncs:live-status-protocol[not(ncs:capability)]) or (../../ncs:live-status-protocol/ncs:capability/ncs:module[.='ciena-pon-ctrl'])";
      description
        "PON state data.";
      container radius-servers {
        description
          "The state data for all radius servers.";
        list radius-server {
          key "name";
          description
            "List of radius servers.";
          leaf name {
            type pon-ctrl:live_ncs_name-string;
            description
              "Name of the radius server.";
          }
          list radius-server-address {
            key "host port";
            description
              "Radius server host and port.";
            leaf host {
              type inet:host;
              description
                "Radius server host address.";
            }
            leaf port {
              type inet:port-number;
              description
                "Radius server port.";
            }
            leaf oper-state {
              type pon-ctrl:live_ncs_radius-server-oper-state;
              description
                "Operational state of the radius server.";
            }
            container statistics {
              description
                "Statistics objects.";
              leaf total-auth-complete {
                type yang:counter64;
                description
                  "Total authentication attempts completed successfully for this radius server.";
              }
              leaf total-auth-timeout {
                type yang:counter64;
                description
                  "Total authentication attempts that timed-out for this radius server.";
              }
            }
          }
        }
      }
      container olts {
        description
          "The state data for all OLTs.";
        list olt {
          key "name";
          description
            "List of OLTs.";
          leaf name {
            type pon-ctrl:live_ncs_name-string;
            description
              "Name of the OLT.";
          }
          leaf oper-state {
            type pon-ctrl:live_ncs_olt-oper-state;
            description
              "Operational state of the OLT.";
          }
          leaf physical-interface {
            type string;
            description
              "The physical port on the device that hosts this OLT.";
          }
          leaf host-management-address {
            type string;
            description
              "The management address of the device hosting this OLT.";
          }
          leaf host-system-name {
            type string;
            description
              "The system name of the device hosting this OLT.";
          }
          leaf management-tpid {
            type pon-ctrl:live_ncs_tpid;
            description
              "TPID used for in-band management of this OLT.";
          }
          leaf management-vid {
            type mef-fp:live_ncs_vlan-id;
            description
              "VID used for in-band management of this OLT.";
          }
          leaf firmware-version {
            type string;
            description
              "Version of the firmware running on this OLT.";
          }
          leaf standby-firmware-version {
            type string;
            description
              "Version of the firmware in the standby bank on this OLT.";
          }
          leaf expected-firmware-version {
            type string;
            description
              "Version of the firmware that is expected to be running
               on this OLT.";
          }
          leaf firmware-status {
            type string;
            description
              "Status of the firmware running on this OLT.";
          }
          leaf hardware-version {
            type string;
            description
              "Version of the OLT's hardware.";
          }
          leaf model {
            type string;
            description
              "Model of this OLT.";
          }
          leaf model-number {
            type string;
            description
              "Model number of this OLT.";
          }
          leaf serial-number {
            type string;
            description
              "Serial number of this OLT.";
          }
          leaf num-configured-onus {
            type uint16;
            description
              "Number of configured ONUs under this OLT.";
          }
          leaf num-registered-onus {
            type uint16;
            description
              "Number of registered ONUs under this OLT.";
          }
          leaf num-deregistered-onus {
            type uint16;
            description
              "Number of deregistered ONUs under this OLT.";
          }
          leaf num-unconfigured-onus {
            type uint16;
            description
              "Number of unconfigured ONUs under this OLT.";
          }
          leaf-list unconfigured-onu {
            type string;
            description
              "The list of ONU serial numbers which have been discovered
               but not configured.";
          }
          leaf num-links {
            type uint16;
            description
              "Number of Datalinks under this OLT.";
          }
          container statistics {
            description
              "OLT statistics.";
            container nni {
              description
                "OLT NNI statistics";
              uses pon-ctrl:live_ncs_packet-counters-grouping;
              leaf rx-oam {
                type yang:counter64;
                description
                  "Count of OAM frames received on the interface.";
              }
              leaf tx-oam {
                type yang:counter64;
                description
                  "Count of OAM frames transmitted on the interface.";
              }
              leaf rx-mac-control-frames {
                type yang:counter64;
                description
                  "Count of MAC Control frames received on the interface.";
              }
              leaf rx-filtered-frames {
                type yang:counter64;
                description
                  "Count of frames received on the interface but filtered (not forwarded).";
              }
              leaf rx-crc32-drops {
                type yang:counter64;
                description
                  "Count of frames received on the interface and dropped due to invalid CRC32.";
              }
              leaf rx-overflow-drops {
                type yang:counter64;
                description
                  "Count of frames received on the interface and dropped due to input queues being full.";
              }
              leaf rx-too-short-drops {
                type yang:counter64;
                description
                  "Count of frames received on the interface and dropped due to the frame being too short.";
              }
              leaf rx-too-long-drops {
                type yang:counter64;
                description
                  "Count of frames received on the interface and dropped due to the frame being too long.";
              }
            }
            container pon {
              description
                "OLT PON statistics";
              uses pon-ctrl:live_ncs_packet-counters-grouping;
              uses pon-ctrl:live_ncs_phy-counters-grouping;
            }
            container radius {
              description
                "OLT Radius statistics";
              uses live_ncs_auth-counters-grouping;
              uses live_ncs_relay-counters-grouping;
            }
          }
          container diagnostic-data {
            description
              "The diagnostic data for this OLT.";
            leaf asic-temperature {
              type int16;
              units "C";
              description
                "The OLT's ASIC temperature in degrees C.";
            }
            leaf xcvr-temperature {
              type int16;
              units "C";
              description
                "The OLT's transceiver temperature in degrees C.";
            }
            leaf laser-temperature {
              type int16;
              units "C";
              description
                "The OLT's laser temperature in degrees C.";
            }
            leaf vcc {
              type cntypes:live_ncs_decimal-2-dig;
              units "mV";
              description
                "The OLT's VCC in mV.";
            }
            leaf tec-current {
              type cntypes:live_ncs_decimal-2-dig;
              units "uA";
              description
                "The OLT's TEC current in uA.";
            }
            leaf transmit-bias {
              type cntypes:live_ncs_decimal-2-dig;
              units "uA";
              description
                "The OLT's transmit bias current in uA.";
            }
            leaf idle-receive-power {
              type cntypes:live_ncs_decimal-2-dig;
              units "dBm";
              description
                "The OLT's idle receive power in dBm.";
            }
            leaf transmit-power {
              type cntypes:live_ncs_decimal-2-dig;
              units "dBm";
              description
                "The OLT's transmit power in dBm.";
            }
            leaf last-shutdown-reason {
              type string;
              description
                "The reason for the latest shutdown of the OLT's laser.";
            }
            leaf is-laser-shutdown {
              type boolean;
              description
                "When true, indicates that the OLT's laser is currently shutdown.
                 When false, indicates that the OLT's laser is currently active.";
            }
            leaf uptime {
              type uint64;
              units "seconds";
              description
                "The OLT's uptime in seconds.";
            }
          }
          container nni-networks {
            description
              "The state data for all NNI Networks.";
            list nni-network {
              key "name";
              description
                "List of NNI Networks.";
              leaf name {
                type pon-ctrl:live_ncs_name-string;
                description
                  "Name of the NNI Network.";
              }
              leaf default-port-id {
                type uint16;
                description
                  "The XGEM port ID of the default downstream flooding link for this NNI Network";
              }
              container flooding-statistics {
                description
                  "Flooding link statistics on this NNI Network as viewed by the OLT.";
                uses pon-ctrl:live_ncs_flooding-counters-grouping;
              }
            }
          }
        }
      }
      container onus {
        description
          "The state data for all ONUs.";
        list onu {
          key "name olt";
          description
            "List of ONUs.";
          leaf name {
            type pon-ctrl:live_ncs_name-string;
            description
              "Name of the ONU.";
          }
          leaf olt {
            type pon-ctrl:live_ncs_olt-ref;
            description
              "Name of the OLT this ONU is subtended from.";
          }
          leaf oper-state {
            type pon-ctrl:live_ncs_onu-oper-state;
            description
              "Operational state of the ONU.";
          }
          leaf onu-id {
            type uint16;
            description
              "The ONU-ID of this ONU as assigned by the OLT.";
          }
          leaf deregister-reason {
            type string;
            description
              "The reason for the last ONU deregistration.
               Set when the oper-state of the ONU is 'deregistered'.";
          }
          leaf firmware-version {
            type string;
            description
              "Version of the firmware running on this ONU.";
          }
          leaf standby-firmware-version {
            type string;
            description
              "Version of the firmware in the standby bank on this ONU.";
          }
          leaf expected-firmware-version {
            type string;
            description
              "Version of the firmware that is expected to be running
               on this ONU based on the model number.";
          }
          leaf firmware-status {
            type string;
            description
              "Status of the firmware running on this ONU.";
          }
          leaf firmware-upgrade-progress {
            type uint16;
            description
              "Percentage completion of the ONU firmware upgrade operation.
               Set when the ONU firmware status is 'Upgrading'.";
          }
          leaf firmware-upgrade-fail-reason {
            type string;
            description
              "The reason for the last ONU firmware upgrade failure.
               Set when the ONU firmware status is 'Upgrade Failed'.";
          }
          leaf firmware-upgrade-attempts {
            type uint16;
            description
              "The number of times the ONU firmware upgrade operation was attempted.
               Set when the ONU firmware status is 'Upgrading' or 'Upgrade Failed'.";
          }
          leaf model {
            type string;
            description
              "Model number of this ONU.";
          }
          leaf mode {
            type string;
            description
              "Mode that this ONU is operating in.";
          }
          leaf num-links {
            type uint16;
            description
              "Number of Datalinks under this ONU.";
          }
          leaf num-uni-ports {
            type uint8;
            description
              "Number of UNI Ports on this ONU.";
          }
          container datalinks {
            description
              "The state data for all Datalinks.";
            list datalink {
              key "name";
              description
                "List of Datalinks.";
              leaf name {
                type pon-ctrl:live_ncs_name-string;
                description
                  "Name of the Datalink.";
              }
              leaf alloc-id {
                type uint16;
                description
                  "The ALLOC-ID of this Datalink as assigned by the OLT/ONU.
                   Only valid in XGS-PON mode.";
              }
              leaf llid {
                type uint16;
                description
                  "The LLID of this Datalink as assigned by the OLT/ONU.
                   Only valid in 10G-EPON mode.";
              }
              container statistics {
                description
                  "Datalink statistics as viewed by the OLT.";
                uses pon-ctrl:live_ncs_packet-counters-grouping;
                uses pon-ctrl:live_ncs_phy-counters-grouping;
                leaf rx-fec-good-blocks {
                  type yang:counter64;
                  description
                    "Count of FEC blocks received without errors.";
                }
                leaf rx-fec-corrected-blocks {
                  type yang:counter64;
                  description
                    "Count of FEC blocks received with errors that were correctable.";
                }
                leaf rx-fec-uncorrectable-blocks {
                  type yang:counter64;
                  description
                    "Count of FEC blocks received with errors that were not correctable.";
                }
                leaf rx-fec-corrections {
                  type yang:counter64;
                  description
                    "Count of FEC blocks received with correctable errors that were corrected.";
                }
              }
            }
            list datalink-relay {
              key "name";
              description
                "List of Datalink Relays.";
              leaf name {
                type pon-ctrl:live_ncs_name-string;
                description
                  "Name of the Datalink.";
              }
              list datalink-relay-state {
                key "cpe-mac";
                description
                  "List of CPE states.";
                leaf cpe-mac {
                  type yang:mac-address;
                  description
                    "Customer Premise Equipment MAC address.";
                }
                leaf oper-state {
                  type pon-ctrl:live_ncs_dhcp-relay-oper-state;
                  description
                    "Operational state of DHCP relay.";
                }
                leaf client-address {
                  type pon-ctrl:live_ncs_pon-relay-attribute-string;
                  description
                    "Dynamic host configuration protocol client address.";
                }
                leaf client-requested-address {
                  type pon-ctrl:live_ncs_pon-relay-attribute-string;
                  description
                    "Dynamic host configuration protocol client requested address.";
                }
                leaf client-identifier {
                  type pon-ctrl:live_ncs_pon-relay-attribute-string;
                  description
                    "Dynamic host configuration protocol client identifier.";
                }
                leaf server-identifier {
                  type pon-ctrl:live_ncs_pon-relay-attribute-string;
                  description
                    "Dynamic host configuration protocol server identifier.";
                }
                leaf circuit-identifier {
                  type pon-ctrl:live_ncs_pon-relay-attribute-string;
                  description
                    "Dynamic host configuration protocol circuit identifier";
                }
                leaf remote-identifier {
                  type pon-ctrl:live_ncs_pon-relay-attribute-string;
                  description
                    "Dynamic host configuration protocol remote identifier.";
                }
                leaf unicast-identifier {
                  type uint32;
                  description
                    "Dynamic host configuration protocol unicast identifier.";
                }
                leaf create-time {
                  type pon-ctrl:live_ncs_pon-relay-attribute-string;
                  description
                    "Dynamic host configuration protocol create time.";
                }
                leaf expiry-time {
                  type pon-ctrl:live_ncs_pon-relay-attribute-string;
                  description
                    "Dynamic host configuration protocol expiry time.";
                }
                leaf reset-count {
                  type uint32;
                  description
                    "Dynamic host configuration protocol reset count.";
                }
                leaf last-success-time {
                  type pon-ctrl:live_ncs_pon-relay-attribute-string;
                  description
                    "Dynamic host configuration protocol last success time.";
                }
                container statistics {
                  description
                    "DHCP relay statistics as viewed by the CPE address.";
                  uses pon-ctrl:live_ncs_relay-counters-grouping;
                }
              }
              container statistics {
                description
                  "DHCP relay statistics as viewed by the Datalink.";
                uses pon-ctrl:live_ncs_relay-counters-grouping;
              }
            }
            list datalink-authentication {
              key "name";
              description
                "List of Datalink Authentications.";
              leaf name {
                type pon-ctrl:live_ncs_name-string;
                description
                  "Name of the Datalink.";
              }
              list datalink-authentication-state {
                key "cpe-mac";
                description
                  "List of CPE states.";
                leaf cpe-mac {
                  type yang:mac-address;
                  description
                    "Customer Premise Equipment MAC address.";
                }
                leaf oper-state {
                  type pon-ctrl:live_ncs_authentication-oper-state;
                  description
                    "Operational state of authentication.";
                }
                leaf create-time {
                  type pon-ctrl:live_ncs_pon-relay-attribute-string;
                  description
                    "Authentication create time.";
                }
                leaf last-success-time {
                  type pon-ctrl:live_ncs_pon-relay-attribute-string;
                  description
                    "Authentication last success time.";
                }
                leaf unicast-identifier {
                  type uint32;
                  description
                    "Authentication unicast identifier.";
                }
                leaf reset-count {
                  type uint32;
                  description
                    "Authentication reset count.";
                }
                container statistics {
                  description
                    "Authentication statistics as viewed by the CPE address.";
                  uses pon-ctrl:live_ncs_auth-counters-grouping;
                }
              }
              container statistics {
                description
                  "Authentication statistics as viewed by the Datalink.";
                uses pon-ctrl:live_ncs_auth-counters-grouping;
              }
            }
          }
          container uni-ports {
            description
              "The state data for all UNI Ports.";
            list uni-port {
              key "name";
              description
                "List of UNI Ports.";
              leaf name {
                type pon-ctrl:live_ncs_name-string;
                description
                  "The numerical identifier of this UNI Port.";
              }
              leaf oper-state {
                type pon-ctrl:live_ncs_uni-port-oper-state;
                description
                  "Operational state of the UNI Port.";
              }
              leaf speed {
                type pon-ctrl:live_ncs_uni-port-oper-speed;
                description
                  "Operational speed of the UNI Port.";
              }
              leaf duplex {
                type pon-ctrl:live_ncs_uni-port-oper-duplex;
                description
                  "Operational duplex of the UNI Port.";
              }
              container xcvr-data {
                description
                  "The Small Form-factor (SFP) Pluggable transceiver data
                   for this UNI Port.
                   Only applicable to ONUs with pluggable transceivers.";
                leaf vendor-name {
                  type string;
                  description
                    "The vendor name of the transceiver.";
                }
                leaf vendor-part-number {
                  type string;
                  description
                    "The vendor part number of the transceiver.";
                }
                leaf vendor-revision {
                  type string;
                  description
                    "The vendor revision of the transceiver.";
                }
                leaf vendor-serial-number {
                  type string;
                  description
                    "The vendor serial number of the transceiver.";
                }
                leaf type {
                  type pon-ctrl:live_ncs_onu-pluggable-xcvr-type;
                  description
                    "The type of the transceiver.";
                }
              }
              container statistics {
                description
                  "UNI Port statistics.";
                uses pon-ctrl:live_ncs_uni-port-packet-counters-grouping;
                leaf ds-frames-broadcast {
                  type yang:counter64;
                  description
                    "Total number of downstream broadcast packets transmitted by the UNI Port.";
                }
                leaf us-frames-broadcast {
                  type yang:counter64;
                  description
                    "Total number of upstream broadcast packets transmitted by the UNI Port.";
                }
                leaf ds-frames-multicast {
                  type yang:counter64;
                  description
                    "Total number of downstream multicast packets transmitted by the UNI Port.";
                }
                leaf us-frames-multicast {
                  type yang:counter64;
                  description
                    "Total number of upstream multicast packets transmitted by the UNI Port.";
                }
                leaf ds-frames-crc-error {
                  type yang:counter64;
                  description
                    "Total number of downstream packets received by the UNI Port that had a bad
                     frame check sequence.";
                }
                leaf us-frames-crc-error {
                  type yang:counter64;
                  description
                    "Total number of upstream packets received by the UNI Port that had a bad
                     frame check sequence.";
                }
                leaf ds-drop-events {
                  type yang:counter64;
                  description
                    "Total number of events in which downstream packets were dropped on the UNI Port
                     due to a lack of resources. This is not necessarily the number of downstream packets
                     dropped.";
                }
                leaf us-drop-events {
                  type yang:counter64;
                  description
                    "Total number of events in which upstream packets were dropped on the UNI Port
                     due to a lack of resources. This is not necessarily the number of upstream packets
                     dropped.";
                }
              }
            }
          }
          container diagnostic-data {
            description
              "The diagnostic data for this ONU.";
            leaf olt-rx-power {
              type cntypes:live_ncs_decimal-2-dig;
              units "dBm";
              description
                "The OLT's Rx optical power for this ONU in dBm.";
            }
            leaf olt-tx-power {
              type cntypes:live_ncs_decimal-2-dig;
              units "dBm";
              description
                "The OLT's Tx optical power in dBm.";
            }
            leaf onu-rx-power {
              type cntypes:live_ncs_decimal-2-dig;
              units "dBm";
              description
                "The ONU's Rx optical power in dBm.";
            }
            leaf onu-tx-power {
              type cntypes:live_ncs_decimal-2-dig;
              units "dBm";
              description
                "The ONU's Tx optical power in dBm.";
            }
            leaf laser-bias-current {
              type cntypes:live_ncs_decimal-2-dig;
              units "mA";
              description
                "The ONU's laser bias current in mA.";
            }
            leaf power-feed-voltage {
              type cntypes:live_ncs_decimal-2-dig;
              units "V";
              description
                "The ONU's power feed voltage in V.";
            }
            leaf temperature {
              type int16;
              units "C";
              description
                "The ONU's temperature in degrees C.";
            }
            leaf uptime {
              type uint64;
              units "seconds";
              description
                "The ONU's uptime in seconds.";
            }
            leaf equalization-delay {
              type uint16;
              units "timeslots";
              description
                "The ONU’s equalization delay (in timeslots) as detected by the OLT.";
            }
            leaf one-way-delay {
              type cntypes:live_ncs_decimal-3-dig;
              units "microseconds";
              description
                "The calculated transit delay on the PON between the OLT and ONU in microseconds.
                 This is derived from the equalization-delay value.";
            }
            leaf fiber-distance {
              type cntypes:live_ncs_decimal-3-dig;
              units "kilometers";
              description
                "The calculated distance between the OLT and ONU in kilometers.
                 This is derived from the equalization-delay value.";
            }
          }
        }
      }
    }
  }
  augment "/ncs:devices/ncs:template/ncs:ned-id/ncs:config" {
    container pon-ctrl {
      description
        "PON configuration data.";
      container radius-servers {
        description
          "The configuration data for all radius servers.";
        list radius-server {
          // NCS patched for predictable order
          ordered-by user;
          key "name";
          description
            "An radius server on the system.";
          leaf name {
            type pon-ctrl:ncs_template_name-string;
            description
              "Name of the Radius Server.";
          }
          leaf management-interface {
            type pon-ctrl:ncs_template_interface-ref;
            // NCS drop must statement
            // NCS drop mandatory statement
            description
              "Reference to the L3 interface on which this OLT is to be
               managed.";
          }
          leaf shared-secret {
            ncx:password;
            type pon-ctrl:ncs_template_pon-relay-attribute-string;
            description
              "Shared secret string.";
          }
          leaf revive-interval {
            type string;
            description
              "Revive interval.";
          }
          leaf failure-threshold {
            type string;
            description
              "Failure Threshold.";
          }
          leaf uam-username {
            type pon-ctrl:ncs_template_pon-relay-attribute-string;
            // NCS drop default statement
            description
              "Universal access method username.";
          }
          leaf uam-enable {
            type string;
            // NCS drop default statement
            description
              "Universal access method enable.";
          }
          leaf uam-recover-threshold {
            type string;
            // NCS drop default statement
            description
              "Universal access method recover threshold.";
          }
          leaf uam-check-interval {
            type string;
            units "seconds";
            // NCS drop default statement
            description
              "Universal access method check internval (seconds).";
          }
          uses ncs_template_pon-ctrl-radius-server-grouping;
        }
      }
      container olts {
        description
          "The configuration data for all OLTs.";
        list olt {
          // NCS patched for predictable order
          ordered-by user;
          key "name";
          description
            "An OLT on the system.";
          leaf name {
            type pon-ctrl:ncs_template_name-string;
            description
              "Name of the OLT.";
          }
          leaf admin-state {
            type ciena:ncs_template_admin-state;
            // NCS drop default statement
            description
              "Enable or disable the OLT.";
          }
          leaf mac-address {
            type string;
            // NCS drop mandatory statement
            description
              "The MAC address of the OLT.";
          }
          leaf management-interface {
            type pon-ctrl:ncs_template_interface-ref;
            // NCS drop must statement
            // NCS drop mandatory statement
            description
              "Reference to the L3 interface on which this OLT is to be
               managed.";
          }
          leaf pon-mode {
            type pon-ctrl:ncs_template_pon-mode;
            // NCS drop default statement
            description
              "The PON mode this OLT will operate in.";
          }
          leaf auto-assigned-ids {
            type ciena:ncs_template_admin-state;
            // NCS drop default statement
            description
              "Enable or disable automatic ONU-ID and ALLOC-ID assignment on the OLT. Only valid in XGS-PON mode.
               Note, when enabled the OLT will automatically register ONUs discovered on the PON.";
          }
          leaf auto-onu-upgrade {
            type ciena:ncs_template_admin-state;
            // NCS drop default statement
            description
              "Enable or disable automatic ONU upgrades on the OLT.
               Note, this only applies to ONUs where the expected firmware version is known and where
               the firmware status is set to 'Upgrade Required'.";
          }
          leaf auto-boot-mode {
            type ciena:ncs_template_admin-state;
            // NCS drop default statement
            description
              "Enable or disable autonomous boot mode on the OLT.";
          }
          leaf upstream-fec-0 {
            // NCS drop when statement
            type ciena:ncs_template_admin-state;
            // NCS drop default statement
            description
              "Enable or disable upstream FEC (Forward Error Correction)
               for burst profile 0 on the OLT in XGS-PON mode.";
          }
          leaf upstream-preamble-0 {
            // NCS drop when statement
            type string;
            // NCS drop default statement
            description
              "The amount of preamble at the start of burst for profile 0
               on the OLT in XGS-PON mode; measured in units of upstream slots (12.8ns).";
          }
          leaf downstream-fec {
            type ciena:ncs_template_admin-state;
            // NCS drop default statement
            description
              "Enable or disable downstream FEC (Forward Error Correction) on the OLT.";
          }
          leaf encryption-mode {
            type pon-ctrl:ncs_template_encryption-mode;
            // NCS drop default statement
            description
              "The encryption mode on the OLT.";
          }
          leaf guard-time {
            // NCS drop when statement
            type string;
            // NCS drop default statement
            description
              "The guard time used by the OLT in XGS-PON mode.
               This is the amount of dead time between upstream burst slots
               measured in units of upstream slots (12.8ns).";
          }
          leaf max-nni-frame-size {
            type string;
            // NCS drop default statement
            description
              "The NNI port's MTU on the OLT.
               Maximum supported MTU is 9600 in XGS-PON mode and
               12500 in 10G-EPON mode.";
          }
          leaf max-pon-frame-size {
            type string;
            // NCS drop default statement
            description
              "The PON port's MTU on the OLT.
               Maximum supported MTU is 9600 in XGS-PON mode and
               12500 in 10G-EPON mode.";
          }
          container nni-networks {
            description
              "The configuration data for all NNI Networks.
               NNI Networks are the configuration construct that enables user traffic to flow through the OLT.
               Inside the OLT, an NNI Network is a Layer-2 Switching Domain (an instance of an IEEE 802.1Q MAC
               Bridge and Virtual Bridge). Like any bridge, a network in the OLT has ports. In the OLT, the bridge ports
               for an NNI Network are the Datalinks (an LLID in 10G-EPON, and an XGEM port in XGS-PON) configured for each ONU and the OLT.";
            list nni-network {
              // NCS patched for predictable order
              ordered-by user;
              key "name";
              description
                "An NNI Network used by the OLT.";
              leaf name {
                type pon-ctrl:ncs_template_name-string;
                description
                  "Name of the NNI Network.";
              }
              leaf flooding-link {
                type ciena:ncs_template_admin-state;
                // NCS drop default statement
                description
                  "Controls the creation of a flooding link on the NNI Network.
                   If the flooding link is disabled on the NNI Network then only one PON Connection will be
                   allowed to be created on the NNI Network. In that scenario, any flooding traffic on the NNI Network
                   will use the Datalink specified by that PON Connection.";
              }
              uses pon-ctrl:ncs_template_tag-match-grouping;
              uses pon-ctrl:ncs_template_tag-options-grouping;
            }
          }
          container cross-connects {
            description
              "The configuration data for all Cross Connects.
               Cross Connects are the configuration construct that enables user traffic to flow between ONUs via the OLT.
               To cross-connect two ONUs, a Datalink from each ONU must be attached to the same Cross Connect via the PON Connection
               configuration.";
            list cross-connect {
              // NCS patched for predictable order
              ordered-by user;
              key "name";
              description
                "A Cross Connect used by the OLT.";
              leaf name {
                type pon-ctrl:ncs_template_name-string;
                description
                  "Name of the Cross Connect.";
              }
            }
          }
        }
      }
      container onus {
        description
          "The configuration data for all ONUs.";
        list onu {
          // NCS patched for predictable order
          ordered-by user;
          key "name olt";
          description
            "An ONU used by the OLT.";
          leaf name {
            type pon-ctrl:ncs_template_name-string;
            description
              "Name of the ONU.";
          }
          leaf olt {
            type pon-ctrl:ncs_template_olt-ref;
            // NCS drop mandatory statement
            description
              "Name of the OLT this ONU is subtended from.";
          }
          leaf admin-state {
            type ciena:ncs_template_admin-state;
            // NCS drop default statement
            description
              "Enable or disable the ONU. Sends a Disable_Serial_Number PLOAM message to the ONU.";
          }
          leaf serial-number {
            type string;
            // NCS drop mandatory statement
            description
              "The serial number the OLT expects to retrieve from the ONU.";
          }
          leaf onu-id {
            type string;
            description
              "The ONU-ID that will be assigned to the ONU.";
          }
          leaf auto-upgrade-firmware-file-name {
            type pon-ctrl:ncs_template_name-string;
            description
              "Name of the firmware file to use when auto-upgrading this ONU.
               Note, this will only take effect when the 'auto-onu-upgrade' option
               is enabled on the OLT.";
          }
          leaf auto-upgrade-defer-activation {
            type string;
            description
              "When set to true, ONU firmware activation after auto-upgrading
               this ONU is deferred until explicitly invoked.
               Note, this will only take effect when the 'auto-onu-upgrade' option
               is enabled on the OLT.";
          }
          container datalinks {
            description
              "The configuration data for all Datalinks.
               A Datalink is an LLID in 10G-EPON mode or an XGEM port in XGS-PON mode.";
            list datalink {
              // NCS patched for predictable order
              ordered-by user;
              key "name";
              description
                "A Datalink used by the ONU.";
              leaf name {
                type pon-ctrl:ncs_template_name-string;
                description
                  "Name of the Datalink.";
              }
              leaf admin-state {
                type ciena:ncs_template_admin-state;
                // NCS drop default statement
                description
                  "Enable or disable traffic on this Datalink.";
              }
              leaf-list uni-ports {
                // NCS patched for predictable order
                ordered-by user;
                type string;
                // NCS drop min-elements statement
                // NCS drop max-elements statement
                description
                  "List of ONU UNI Ports to apply the Datalink on.";
              }
              leaf-list vlan-ids {
                // NCS patched for predictable order
                ordered-by user;
                type pon-ctrl:ncs_template_tag-match-vid;
                // NCS drop max-elements statement
                description
                  "List of VLAN IDs to be forwarded on this Datalink.
                   Traffic will only be allowed on this Datalink if it matches
                   one of the values specified. Not specifying this field or
                   specifying a value of 65535 will match on any VID value,
                   no VLAN tag or a priority tag. Values specified must be unique
                   across all Datalinks on the same UNI Port.";
              }
              leaf sla-profile {
                type pon-ctrl:ncs_template_sla-profile-ref;
                // NCS drop mandatory statement
                description
                  "Name of the SLA Profile this Datalink implements.";
              }
              leaf add-ctag {
                type mef-fp:ncs_template_vlan-id;
                description
                  "Add an optional C-Tag at the ONU for all upstream traffic on this Datalink.
                   This tag is popped (removed) in the downstream direction.";
              }
              leaf add-ctag-pcp {
                // NCS drop when statement
                type string;
                description
                  "Specify the 802.1p priority of the added C-Tag on this Datalink.
                   This is only valid when the add-ctag parameter is specified.
                   When this field is not specified, a PCP value of 0 is assumed for
                   untagged frames. For tagged frames the PCP value of the added C-Tag
                   is copied from the existing VLAN.";
              }
              uses pon-ctrl:ncs_template_dhcp-grouping;
              uses pon-ctrl:ncs_template_radius-grouping;
              leaf alloc-id {
                type string;
                // NCS drop must statement
                description
                  "The configured ALLOC-ID of this Datalink.
                   Only valid in XGS-PON mode.";
              }
            }
          }
          container pon-connections {
            description
              "The configuration data for all PON Connections.
               PON Connections are the configuration construct that links a Datalink on the ONU to
               an NNI Network or Cross Connect on the OLT.";
            list pon-connection {
              // NCS patched for predictable order
              ordered-by user;
              key "name";
              description
                "A PON Connection used by the ONU.";
              leaf name {
                type pon-ctrl:ncs_template_name-string;
                description
                  "Name of the PON Connection.";
              }
              leaf datalink {
                type string;
                // NCS drop mandatory statement
                description
                  "Reference to the Datalink on the ONU.
                   Datalink must be configured on the same ONU as this PON Connection.";
              }
              leaf nni-network {
                // NCS drop when statement
                type string;
                // NCS drop mandatory statement
                description
                  "Reference to the NNI Network on the OLT.
                   NNI Network must be configured on the same OLT as the ONU where this PON Connection exists.
                   The NNI Network reference is mutually exclusive with the Cross Connect reference.";
              }
              leaf cross-connect {
                // NCS drop when statement
                type string;
                // NCS drop mandatory statement
                description
                  "Reference to the Cross Connect on the OLT.
                   Cross Connect must be configured on the same OLT as the ONU where this PON Connection exists.
                   The Cross Connect reference is mutually exclusive with the NNI Network reference.";
              }
              uses pon-ctrl:ncs_template_tag-match-grouping;
              uses pon-ctrl:ncs_template_tag-options-grouping;
            }
          }
          container uni-ports {
            description
              "The configuration data for all UNI Ports.
               This configuration construct is optional and can be used to modify specific UNI Port parameters
               under this ONU.";
            list uni-port {
              // NCS patched for predictable order
              ordered-by user;
              key "name";
              // NCS drop max-elements statement
              description
                "A UNI Port on the ONU.";
              leaf name {
                type pon-ctrl:ncs_template_name-string;
                description
                  "The numerical identifier of this UNI Port.
                   Must be a numercical value between 1 and 5.";
              }
              leaf description {
                type pon-ctrl:ncs_template_name-string;
                description
                  "A string description of this UNI Port.";
              }
              leaf admin-state {
                type ciena:ncs_template_admin-state;
                // NCS drop default statement
                description
                  "Enable or disable the UNI Port.";
              }
              leaf max-frame-size {
                type string;
                // NCS drop default statement
                description
                  "The UNI Port's configured MTU.";
              }
              leaf speed {
                type pon-ctrl:ncs_template_uni-port-speed;
                // NCS drop default statement
                description
                  "The UNI Port's configured speed.";
              }
              leaf duplex {
                type pon-ctrl:ncs_template_uni-port-duplex;
                // NCS drop default statement
                description
                  "The UNI Port's configured duplex.";
              }
              leaf stats-collection {
                type ciena:ncs_template_admin-state;
                // NCS drop default statement
                description
                  "Determines whether stats collection will be enabled or disabled for the UNI Port.";
              }
            }
          }
        }
      }
      container sla-profiles {
        description
          "The configuration data for all SLA Profiles.";
        list sla-profile {
          // NCS patched for predictable order
          ordered-by user;
          key "name";
          description
            "An SLA Profile used by a Datalink.";
          leaf name {
            type pon-ctrl:ncs_template_name-string;
            description
              "Name of the SLA Profile.";
          }
          leaf up-fixed-rate {
            type string;
            units "Kbps";
            // NCS drop default statement
            description
              "Fixed grant rate in Kbps. This is an unsolicited
               grant by the DBA regardless of need.";
          }
          leaf up-guaranteed-rate {
            type string;
            units "Kbps";
            // NCS drop default statement
            description
              "Guaranteed (high priority) upstream rate in Kbps.";
          }
          leaf up-guaranteed-max-burst {
            type string;
            units "Bytes";
            // NCS drop default statement
            description
              "Maximum upstream burst size in Bytes. The
               guaranteed rate is enforced at this burst size.";
          }
          leaf up-best-effort-rate {
            type string;
            units "Kbps";
            // NCS drop default statement
            description
              "Best Effort (low priority) upstream rate in Kbps.";
          }
          leaf up-best-effort-max-burst {
            type string;
            units "Bytes";
            // NCS drop default statement
            description
              "Maximum upstream burst size in Bytes. The best
               effort rate is enforced at this burst size.";
          }
          leaf up-priority {
            type string;
            // NCS drop default statement
            description
              "Priority level for the Guaranteed portion of the SLA.";
          }
          leaf up-service-limit {
            type string;
            units "kBytes";
            // NCS drop default statement
            description
              "Maximum grant size for an upstream slot in Kilobytes.";
          }
          leaf up-min-grant-period {
            type string;
            // NCS drop default statement
            description
              "The minimum allowed spacing between grants on this service.";
          }
          leaf up-max-grant-period {
            type string;
            // NCS drop default statement
            description
              "The maximum allowed time between grants on
               this service. This field will cause a polling grant
               when the ONU is idle.";
          }
          leaf down-guaranteed-rate {
            type string;
            units "Kbps";
            // NCS drop default statement
            description
              "Guaranteed (high priority) downstream rate in Kbps.";
          }
          leaf down-guaranteed-max-burst {
            type string;
            units "Bytes";
            // NCS drop default statement
            description
              "Maximum downstream burst size in Bytes. The
               guaranteed rate is enforced at this burst size.";
          }
          leaf down-best-effort-rate {
            type string;
            units "Kbps";
            // NCS drop default statement
            description
              "Best Effort (low priority) downstream rate in Kbps.";
          }
          leaf down-best-effort-max-burst {
            type string;
            units "Bytes";
            // NCS drop default statement
            description
              "Maximum downstream burst size in Bytes. The best
               effort rate is enforced at this burst size.";
          }
        }
      }
    }
    // NCS drop config false container 'pon-ctrl-state'
  }
}
