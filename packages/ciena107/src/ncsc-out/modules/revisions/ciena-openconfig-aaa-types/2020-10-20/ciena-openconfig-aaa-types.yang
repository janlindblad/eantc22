module ciena-openconfig-aaa-types {
  // Generated by yanger -t ncs
  tailf:mount-id "ciena107-nc-1.0:ciena107-nc-1.0";
  tailf:ncs-device-type "netconf";

  namespace "http://www.ciena.com/ns/yang/ciena-openconfig-aaa-types";
  prefix ciena-oc-aaa-types;

  import tailf-common {
    prefix tailf;
  }
  import tailf-ncs {
    prefix ncs;
  }

  organization
    "Ciena Corporation";
  contact
    "Web URL: http://www.ciena.com/
     E-mail:  yang@ciena.com
     Postal:  7035 Ridge Road
              Hanover, Maryland 21076
              U.S.A.
     Phone:   +1 800-921-1144
     Fax:     +1 410-694-5750";
  description
    "This YANG module defines Ciena's types for openconfig-aaa.

      Copyright (c) 2020 Ciena Corporation.  All rights
      reserved.

      All information contained herein is, and remains
      the property of Ciena Corporation. Dissemination of this
      information or reproduction of this material is strictly
      forbidden unless prior written permission is obtained from
      Ciena Corporation.";

  revision 2020-10-20 {
    description
      "Added identities for AUTHEN_PVDR_TYPE.";
    reference "";
  }
  revision 2020-08-14 {
    description
      "Added identities for user roles.";
    reference "";
  }

  identity RADSEC {
    base AUTHEN_PVDR_TYPE;
    description
      "Built-in type for radsec authentication";
    reference
      "RFC 6614 - Transport Layer Security (TLS)
       Encryption for RADIUS";
  }

  identity RADIUS {
    base AUTHEN_PVDR_TYPE;
    description
      "Built-in type for radius authentication";
    reference "";
  }

  identity TACACS {
    base AUTHEN_PVDR_TYPE;
    description
      "Built-in type for tacacs authentication";
    reference "";
  }

  identity LOCAL {
    base AUTHEN_PVDR_TYPE;
    description
      "Built-in type for local authentication";
    reference "";
  }

  identity AUTHEN_PVDR_TYPE {
    description
      "Base authentication provider type";
    reference "";
  }

  identity SYSTEM_ROLE_USER {
    base ciena-oc-aaa-types:CIENA_SYSTEM_DEFINED_ROLES;
    description
      "Built-in role that allows access to yp-shell.";
  }

  identity SYSTEM_ROLE_DIAG {
    base ciena-oc-aaa-types:CIENA_SYSTEM_DEFINED_ROLES;
    description
      "Built-in role that allows access to linux.";
  }

  identity CIENA_SYSTEM_DEFINED_ROLES {
    description
      "Base identity for ciena-specific system-defined roles that can be assigned
       to users.";
  }
}
