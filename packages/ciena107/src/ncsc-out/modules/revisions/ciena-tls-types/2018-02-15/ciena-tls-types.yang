module ciena-tls-types {
  // Generated by yanger -t ncs
  tailf:mount-id "ciena107-nc-1.0:ciena107-nc-1.0";
  tailf:ncs-device-type "netconf";

  namespace "http://www.ciena.com/tls/yang/ciena-tls-types";
  prefix ciena-tls-types;

  import ietf-tls-common {
    prefix ietf-tls;
  }
  import tailf-common {
    prefix tailf;
  }
  import tailf-ncs {
    prefix ncs;
  }

  organization
    "Ciena Corporation";
  contact
    "Web URL: http://www.ciena.com/
     E-mail:  yang@ciena.com
     Postal:  7035 Ridge Road
              Hanover, Maryland 21076
              U.S.A.
     Phone:   +1 800-921-1144
     Fax:     +1 410-694-5750";
  description
    "This YANG module defines the nodes
     for TLS for the NETCONF protocol.

     Copyright (c) 2018 Ciena Corporation.  All rights
     reserved.

     All information contained herein is, and remains
     the property of Ciena Corporation. Dissemination of this
     information or reproduction of this material is strictly
     forbidden unless prior written permission is obtained from
     Ciena Corporation.";

  revision 2018-02-15 {
    description
      "Initial revision.";
    reference "RFC XXXX: YANG Groupings for TLS Clients and TLS Servers";
  }

  typedef ncs_template_timeout {
    type string;
    description
      "Timeout duration.";
  }

  typedef ncs_rpc_notif_timeout {
    type uint32 {
      range "0..max";
    }
    description
      "Timeout duration.";
  }

  typedef live_ncs_timeout {
    type uint32 {
      range "0..max";
    }
    description
      "Timeout duration.";
  }

  typedef timeout {
    type uint32 {
      range "0..max";
    }
    description
      "Timeout duration.";
  }

  identity sect283r1 {
    base elliptic-curve-base;
    description
      "Elliptic-curve sect283r1.";
    reference
      "RFC 4992: The Transport Layer Security (TLS) Protocol
       Version 1.2";
  }

  identity sect283k1 {
    base elliptic-curve-base;
    description
      "Elliptic-curve sect283k1.";
    reference
      "RFC 4992: The Transport Layer Security (TLS) Protocol
       Version 1.2";
  }

  identity sect409r1 {
    base elliptic-curve-base;
    description
      "Elliptic-curve sect409r1.";
    reference
      "RFC 4992: The Transport Layer Security (TLS) Protocol
        Version 1.2";
  }

  identity sect409k1 {
    base elliptic-curve-base;
    description
      "Elliptic-curve sect409k1.";
    reference
      "RFC 4992: The Transport Layer Security (TLS) Protocol
       Version 1.2";
  }

  identity sect571k1 {
    base elliptic-curve-base;
    description
      "Elliptic-curve sect571k1.";
    reference
      "RFC 4992: The Transport Layer Security (TLS) Protocol
       Version 1.2";
  }

  identity sect571r1 {
    base elliptic-curve-base;
    description
      "Elliptic-curve sect571r1.";
    reference
      "RFC 4992: The Transport Layer Security (TLS) Protocol
       Version 1.2";
  }

  identity secp256k1 {
    base elliptic-curve-base;
    description
      "Elliptic-curve secp256k1.";
    reference
      "RFC 4992: The Transport Layer Security (TLS) Protocol
       Version 1.2";
  }

  identity brainpoolP256r1 {
    base elliptic-curve-base;
    description
      "Elliptic-curve brainpoolP256r1.";
    reference
      "RFC 7027: The Transport Layer Security (TLS) Protocol
       Version 1.2";
  }

  identity secp384r1 {
    base elliptic-curve-base;
    description
      "Elliptic-curve secp384r1.";
    reference
      "RFC 4992: The Transport Layer Security (TLS) Protocol
        Version 1.2";
  }

  identity brainpoolP384r1 {
    base elliptic-curve-base;
    description
      "Elliptic-curve brainpoolP384r1.";
    reference
      "RFC 7027: The Transport Layer Security (TLS) Protocol
       Version 1.2";
  }

  identity brainpoolP512r1 {
    base elliptic-curve-base;
    description
      "Elliptic-curve brainpoolP512r1.";
    reference
      "RFC 7027: The Transport Layer Security (TLS) Protocol
       Version 1.2";
  }

  identity secp521r1 {
    base elliptic-curve-base;
    description
      "Elliptic-curve secp521r1.";
    reference
      "RFC 4992: The Transport Layer Security (TLS) Protocol
       Version 1.2";
  }

  identity secp256r1 {
    base elliptic-curve-base;
    description
      "Elliptic-curve secp256r1.";
    reference
      "RFC 4992: The Transport Layer Security (TLS) Protocol
        Version 1.2";
  }

  identity elliptic-curve-base {
    description
      "Base identity used to identify TLS elliptic curve.";
  }

  identity rsa-with-rc4-128-md5 {
    base ietf-tls:cipher-suite-base;
    description
      "Cipher suite RSA-WITH-RC4-128-MD5.";
    reference
      "RFC 5246: The Transport Layer Security (TLS) Protocol
       Version 1.2";
  }

  identity rsa-with-rc4-128-sha {
    base ietf-tls:cipher-suite-base;
    description
      "Cipher suite RSA-WITH-RC4-128-SHA.";
    reference
      "RFC 5246: The Transport Layer Security (TLS) Protocol
       Version 1.2";
  }

  identity rsa-with-aes-128-gcm-sha256 {
    base ietf-tls:cipher-suite-base;
    description
      "Cipher suite RSA-WITH-AES-128-GCM-SHA256.";
    reference
      "RFC 5246: The Transport Layer Security (TLS) Protocol
       Version 1.2";
  }

  identity ecdh-ecdsa-with-3des-ede-cbc-sha {
    base ietf-tls:cipher-suite-base;
    description
      "Cipher suite ECDH-ECDSA-WITH-3DES-EDE-CBC-SHA.";
    reference
      "RFC 4492: Elliptic Curve Cryptography (ECC) Cipher Suites
       for Transport Layer Security (TLS)";
  }

  identity ecdh-rsa-with-3des-ede-cbc-sha {
    base ietf-tls:cipher-suite-base;
    description
      "Cipher suite ECDH-RSA-WITH-3DES-EDE-CBC-SHA.";
    reference
      "RFC 4492: Elliptic Curve Cryptography (ECC) Cipher Suites
       for Transport Layer Security (TLS)";
  }

  identity ecdh-ecdsa-with-aes-128-cbc-sha {
    base ietf-tls:cipher-suite-base;
    description
      "Cipher suite ECDH-ECDSA-WITH-AES-128-CBC-SHA.";
    reference
      "RFC 4492: Elliptic Curve Cryptography (ECC) Cipher Suites
       for Transport Layer Security (TLS)";
  }

  identity ecdh-rsa-with-aes-128-cbc-sha {
    base ietf-tls:cipher-suite-base;
    description
      "Cipher suite ECDH-RSA-WITH-AES-128-CBC-SHA.";
    reference
      "RFC 4492: Elliptic Curve Cryptography (ECC) Cipher Suites
       for Transport Layer Security (TLS)";
  }

  identity ecdh-ecdsa-with-aes-128-cbc-sha256 {
    base ietf-tls:cipher-suite-base;
    description
      "Cipher suite ECDH-ECDSA-WITH-AES-128-CBC-SHA256.";
    reference
      "RFC 4492: Elliptic Curve Cryptography (ECC) Cipher Suites
       for Transport Layer Security (TLS)";
  }

  identity ecdh-rsa-with-aes-128-cbc-sha256 {
    base ietf-tls:cipher-suite-base;
    description
      "Cipher suite ECDH-RSA-WITH-AES-128-CBC-SHA256.";
    reference
      "RFC 4492: Elliptic Curve Cryptography (ECC) Cipher Suites
       for Transport Layer Security (TLS)";
  }

  identity ecdh-ecdsa-with-aes-128-gcm-sha256 {
    base ietf-tls:cipher-suite-base;
    description
      "Cipher suite ECDH-ECDSA-WITH-AES-128-GCM-SHA256.";
    reference
      "RFC 4492: Elliptic Curve Cryptography (ECC) Cipher Suites
       for Transport Layer Security (TLS)";
  }

  identity ecdh-rsa-with-aes-128-gcm-sha256 {
    base ietf-tls:cipher-suite-base;
    description
      "Cipher suite ECDH-RSA-WITH-AES-128-GCM-SHA256.";
    reference
      "RFC 4492: Elliptic Curve Cryptography (ECC) Cipher Suites
       for Transport Layer Security (TLS)";
  }

  identity dhe-dss-with-3des-ede-cbc-sha {
    base ietf-tls:cipher-suite-base;
    description
      "Cipher suite DHE-DSS-WITH-3DES-EDE-CBC-SHA.";
    reference
      "RFC 5246: The Transport Layer Security (TLS) Protocol
       Version 1.2";
  }

  identity dhe-rsa-with-3des-ede-cbc-sha {
    base ietf-tls:cipher-suite-base;
    description
      "Cipher suite DHE-RSA-WITH-3DES-EDE-CBC-SHA.";
    reference
      "RFC 5246: The Transport Layer Security (TLS) Protocol
       Version 1.2";
  }

  identity ecdhe-ecdsa-with-3des-ede-cbc-sha {
    base ietf-tls:cipher-suite-base;
    description
      "Cipher suite ECDHE-ECDSA-WITH-3DES-EDE-CBC-SHA.";
    reference
      "RFC 4492: Elliptic Curve Cryptography (ECC) Cipher Suites
       for Transport Layer Security (TLS)";
  }

  identity dhe-dss-with-aes-128-cbc-sha {
    base ietf-tls:cipher-suite-base;
    description
      "Cipher suite DHE-DSS-WITH-AES-128-CBC-SHA.";
    reference
      "RFC 5246: The Transport Layer Security (TLS) Protocol
       Version 1.2";
  }

  identity dhe-dss-with-aes-128-cbc-sha256 {
    base ietf-tls:cipher-suite-base;
    description
      "Cipher suite DHE-DSS-WITH-AES-128-CBC-SHA256.";
    reference
      "RFC 5246: The Transport Layer Security (TLS) Protocol
       Version 1.2";
  }

  identity dhe-rsa-with-aes-128-gcm-sha256 {
    base ietf-tls:cipher-suite-base;
    description
      "Cipher suite DHE-RSA-WITH-AES-128-GCM-SHA256.";
    reference
      "RFC 5246: The Transport Layer Security (TLS) Protocol
       Version 1.2";
  }

  identity dhe-dss-with-aes-128-gcm-sha256 {
    base ietf-tls:cipher-suite-base;
    description
      "Cipher suite DHE-DSS-WITH-AES-128-GCM-SHA256.";
    reference
      "RFC 5246: The Transport Layer Security (TLS) Protocol
        Version 1.2";
  }

  identity ecdhe-ecdsa-with-aes-128-cbc-sha {
    base ietf-tls:cipher-suite-base;
    description
      "Cipher suite ECDHE-ECDSA-WITH-AES-128-CBC-SHA.";
    reference
      "RFC 4492: Elliptic Curve Cryptography (ECC) Cipher Suites
       for Transport Layer Security (TLS)";
  }

  identity rsa-with-aes-256-gcm-sha384 {
    base ietf-tls:cipher-suite-base;
    description
      "Cipher suite RSA-WITH-AES-256-GCM-SHA384.";
    reference
      "RFC 5246: The Transport Layer Security (TLS) Protocol
       Version 1.2";
  }

  identity ecdh-ecdsa-with-aes-256-cbc-sha {
    base ietf-tls:cipher-suite-base;
    description
      "Cipher suite ECDH-ECDSA-WITH-AES-256-CBC-SHA.";
    reference
      "RFC 4492: Elliptic Curve Cryptography (ECC) Cipher Suites
       for Transport Layer Security (TLS)";
  }

  identity ecdh-rsa-with-aes-256-cbc-sha {
    base ietf-tls:cipher-suite-base;
    description
      "Cipher suite ECDH-RSA-WITH-AES-256-CBC-SHA.";
    reference
      "RFC 4492: Elliptic Curve Cryptography (ECC) Cipher Suites
       for Transport Layer Security (TLS)";
  }

  identity ecdh-ecdsa-with-aes-256-cbc-sha384 {
    base ietf-tls:cipher-suite-base;
    description
      "Cipher suite ECDH-ECDSA-WITH-AES-256-CBC-SHA384.";
    reference
      "RFC 4492: Elliptic Curve Cryptography (ECC) Cipher Suites
       for Transport Layer Security (TLS)";
  }

  identity ecdh-rsa-with-aes-256-cbc-sha384 {
    base ietf-tls:cipher-suite-base;
    description
      "Cipher suite ECDH-RSA-WITH-AES-256-CBC-SHA384.";
    reference
      "RFC 4492: Elliptic Curve Cryptography (ECC) Cipher Suites
       for Transport Layer Security (TLS)";
  }

  identity ecdh-ecdsa-with-aes-256-gcm-sha384 {
    base ietf-tls:cipher-suite-base;
    description
      "Cipher suite ECDH-ECDSA-WITH-AES-256-GCM-SHA384.";
    reference
      "RFC 4492: Elliptic Curve Cryptography (ECC) Cipher Suites
       for Transport Layer Security (TLS)";
  }

  identity ecdh-rsa-with-aes-256-gcm-sha384 {
    base ietf-tls:cipher-suite-base;
    description
      "Cipher suite ECDH-RSA-WITH-AES-256-GCM-SHA384.";
    reference
      "RFC 4492: Elliptic Curve Cryptography (ECC) Cipher Suites
       for Transport Layer Security (TLS)";
  }

  identity dhe-dss-with-aes-256-cbc-sha {
    base ietf-tls:cipher-suite-base;
    description
      "Cipher suite DHE-DSS-WITH-AES-256-CBC-SHA.";
    reference
      "RFC 5246: The Transport Layer Security (TLS) Protocol
       Version 1.2";
  }

  identity dhe-dss-with-aes-256-cbc-sha256 {
    base ietf-tls:cipher-suite-base;
    description
      "Cipher suite DHE-DSS-WITH-AES-256-CBC-SHA256.";
    reference
      "RFC 5246: The Transport Layer Security (TLS) Protocol
       Version 1.2";
  }

  identity dhe-rsa-with-aes-256-gcm-sha384 {
    base ietf-tls:cipher-suite-base;
    description
      "Cipher suite DHE-RSA-WITH-AES-256-GCM-SHA384.";
    reference
      "RFC 5246: The Transport Layer Security (TLS) Protocol
       Version 1.2";
  }

  identity dhe-dss-with-aes-256-gcm-sha384 {
    base ietf-tls:cipher-suite-base;
    description
      "Cipher suite DHE-DSS-WITH-AES-256-GCM-SHA384.";
    reference
      "RFC 5246: The Transport Layer Security (TLS) Protocol
       Version 1.2";
  }

  identity ecdhe-ecdsa-with-aes-256-cbc-sha {
    base ietf-tls:cipher-suite-base;
    description
      "Cipher suite ECDHE-ECDSA-WITH-AES-256-CBC-SHA.";
    reference
      "RFC 4492: Elliptic Curve Cryptography (ECC) Cipher Suites
       for Transport Layer Security (TLS)";
  }
}
