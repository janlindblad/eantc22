module ciena-bfd-ip-mh {
  // Generated by yanger -t ncs
  tailf:mount-id "ciena107-nc-1.0:ciena107-nc-1.0";
  tailf:ncs-device-type "netconf";

  namespace "http://ciena.com/ns/yang/ciena-bfd-ip-mh";
  prefix bfd-ip-mh;

  import ciena-bfd-types {
    prefix bfd-types;
  }
  import ciena-bfd {
    prefix bfd;
  }
  import openconfig-interfaces {
    prefix oc-if;
  }
  import ietf-inet-types {
    prefix inet;
  }
  import tailf-common {
    prefix tailf;
  }
  import tailf-ncs {
    prefix ncs;
  }

  organization
    "Ciena Corporation";
  contact
    "Web URL: http://www.ciena.com/
     E-mail:  yang@ciena.com
     Postal:  7035 Ridge Road
              Hanover, Maryland 21076
                  U.S.A.
     Phone:   +1 800-921-1144
     Fax:     +1 410-694-5750";
  description
    "This YANG module defines Ciena's BFD IP multi-hop protocol.
     Copyright (c) 2019  Ciena Corporation.  All rights
     reserved.
     All information contained herein is, and remains the
     property of Ciena Corporation. Dissemination of this
     information or reproduction of this material is strictly
     forbidden unless prior written permission is obtained
     from Ciena Corporation.";

  revision 2021-05-21 {
    description
      "Marking IP-MH bfd session config parameters as deprecated.
       BFD session parameters are now expected to be picked from
       profile.
       Session-groups-state's hierarchy is changed to support
       operational data fetch for IP-BFD without any dependency on
       static BFD configuration.";
  }
  revision 2020-08-24 {
    description
      "Added bfd client info per session.
       Added ppm triggered bfd fault per session in operational data.";
  }
  revision 2010-02-14 {
    description
      "Initial revision of BFD IP multi-hop data model.";
  }

  augment "/ncs:devices/ncs:template/ncs:ned-id/ncs:config/bfd:bfd" {
    description
      "BFD augmentation for IP multi-hop";
    container ip-mh {
      description
        "BFD IP multi-hop configuration and operational data.";
      container session-groups {
        description
          "BFD IP multi-hop sessions.";
        list session-group {
          // NCS patched for predictable order
          ordered-by user;
          key "interface dest-addr";
          description
            "List of IP multi-hop sessions.";
          leaf interface {
            type string;
            description
              "L3 interface on which the BFD session is running.";
          }
          leaf dest-addr {
            type string;
            description
              "IP address of the peer.";
          }
          leaf source-addr {
            type string;
            description
              "Local IP address.";
            // NCS drop mandatory statement
          }
          uses bfd-types:ncs_template_common-cfg-parms {
            status deprecated;
          }
        }
      }
      // NCS drop config false container 'session-groups-state'
    }
    // NCS drop config false container 'ip-mh-session-groups-state'
  }
  augment "/ncs:devices/ncs:device/ncs:live-status/bfd:bfd" {
    description
      "BFD augmentation for IP multi-hop";
    container ip-mh {
      tailf:ncs-device-type "netconf";
      tailf:display-when "not(../../../ncs:module) or ../../../ncs:module[ncs:name='ciena-bfd-ip-mh'] or (../../../ncs:live-status-protocol[not(ncs:capability)]) or (../../../ncs:live-status-protocol/ncs:capability/ncs:module[.='ciena-bfd-ip-mh'])";
      description
        "BFD IP multi-hop configuration and operational data.";
      container session-groups {
        description
          "BFD IP multi-hop sessions.";
        list session-group {
          key "interface dest-addr";
          description
            "List of IP multi-hop sessions.";
          leaf interface {
            type leafref {
              path "/ncs:devices/ncs:device/ncs:live-status/oc-if:interfaces/oc-if:interface/oc-if:name" {
                tailf:xpath-root 3;
              }
            }
            description
              "L3 interface on which the BFD session is running.";
          }
          leaf dest-addr {
            type inet:ip-address;
            description
              "IP address of the peer.";
          }
          leaf source-addr {
            type inet:ip-address;
            description
              "Local IP address.";
            // NCS drop mandatory statement
          }
          uses bfd-types:live_ncs_common-cfg-parms {
            status deprecated;
          }
        }
      }
      container session-groups-state {
        status deprecated;
        description
          "BFD IP multi-hop sessions state.";
        list session-group-state {
          key "interface dest-addr";
          description
            "List of IP multi-hop sessions.";
          leaf interface {
            type string;
            description
              "L3 interface on which the BFD session is running.";
          }
          leaf dest-addr {
            type inet:ip-address;
            description
              "IP address of the peer.";
          }
          leaf source-addr {
            type inet:ip-address;
            description
              "Local IP address.";
          }
          uses bfd-types:live_ncs_base-cfg-parms;
          uses bfd-types:live_ncs_all-session;
          uses bfd-types:live_ncs_bfd-client-info;
          leaf ppm-forced-bfd-down {
            type boolean;
            description
              "Indicates Programmable Policy Manager (PPM) triggered fault on BFD session.";
          }
        }
      }
    }
    container ip-mh-session-groups-state {
      tailf:ncs-device-type "netconf";
      tailf:display-when "not(../../../ncs:module) or ../../../ncs:module[ncs:name='ciena-bfd-ip-mh'] or (../../../ncs:live-status-protocol[not(ncs:capability)]) or (../../../ncs:live-status-protocol/ncs:capability/ncs:module[.='ciena-bfd-ip-mh'])";
      description
        "BFD IP multi-hop sessions state.";
      list session-group-state {
        key "interface dest-addr";
        description
          "List of IP multi-hop sessions.";
        leaf interface {
          type string;
          description
            "L3 interface on which the BFD session is running.";
        }
        leaf dest-addr {
          type inet:ip-address;
          description
            "IP address of the peer.";
        }
        leaf source-addr {
          type inet:ip-address;
          description
            "Local IP address.";
        }
        uses bfd-types:live_ncs_base-cfg-parms;
        uses bfd-types:live_ncs_all-session;
        uses bfd-types:live_ncs_bfd-client-info;
        leaf ppm-forced-bfd-down {
          type boolean;
          description
            "Indicates Programmable Policy Manager (PPM) triggered fault on BFD session.";
        }
      }
    }
  }
  augment "/ncs:devices/ncs:device/ncs:config/bfd:bfd" {
    description
      "BFD augmentation for IP multi-hop";
    container ip-mh {
      tailf:ncs-device-type "netconf";
      tailf:display-when "not(../../../ncs:module) or ../../../ncs:module[ncs:name='ciena-bfd-ip-mh']";
      description
        "BFD IP multi-hop configuration and operational data.";
      container session-groups {
        description
          "BFD IP multi-hop sessions.";
        list session-group {
          key "interface dest-addr";
          description
            "List of IP multi-hop sessions.";
          leaf interface {
            type leafref {
              path "/ncs:devices/ncs:device/ncs:config/oc-if:interfaces/oc-if:interface/oc-if:name" {
                tailf:xpath-root 3;
              }
            }
            description
              "L3 interface on which the BFD session is running.";
          }
          leaf dest-addr {
            type inet:ip-address;
            description
              "IP address of the peer.";
          }
          leaf source-addr {
            type inet:ip-address;
            description
              "Local IP address.";
            mandatory true;
          }
          uses bfd-types:common-cfg-parms {
            status deprecated;
          }
        }
      }
      // NCS drop config false container 'session-groups-state'
    }
    // NCS drop config false container 'ip-mh-session-groups-state'
  }
}
