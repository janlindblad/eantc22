module ciena-syslog-tls {
  // Generated by yanger -t ncs
  tailf:mount-id "ciena107-nc-1.0:ciena107-nc-1.0";
  tailf:ncs-device-type "netconf";

  namespace "http://www.ciena.com/ns/yang/ciena-syslog-tls";
  prefix ciena-syslog-tls;

  import ietf-yang-types {
    prefix yang;
  }
  import ietf-inet-types {
    prefix inet;
  }
  import ciena-types {
    prefix ciena-types;
  }
  import ietf-syslog {
    prefix syslog;
  }
  import ietf-syslog-types {
    prefix syslogtypes;
  }
  import ciena-tls-service-profile {
    prefix ciena-tsp;
  }
  import tailf-common {
    prefix tailf;
  }
  import tailf-ncs {
    prefix ncs;
  }

  organization
    "Ciena Corporation";
  contact
    "Web URL: http://www.ciena.com/
     E-mail:  yang@ciena.com
     Postal:  7035 Ridge Road
              Hanover, Maryland 21076
              U.S.A.
     Phone:   +1 800-921-1144
     Fax:     +1 410-694-5750";
  description
    "This module defines configuration and operational state data
     related to syslog over TLS protocol compliant to RFC5425.

     Copyright (c) 2020 Ciena Corporation.  All rights
     reserved.

     All information contained herein is, and remains
     the property of Ciena Corporation. Dissemination of this
     information or reproduction of this material is strictly
     forbidden unless prior written permission is obtained from
     Ciena Corporation.";

  revision 2020-09-24 {
    description
      "Initial version";
    reference "RFC 5425: Transport Layer Security (TLS) Transport Mapping for Syslog.";
  }

  augment "/ncs:devices/ncs:device/ncs:rpc" {
    container rpc-clear-syslog-tls-server-stats {
      tailf:ncs-device-type "netconf";
      tailf:display-when "not(../../ncs:module) or ../../ncs:module[ncs:name='ciena-syslog-tls']";
      tailf:action clear-syslog-tls-server-stats {
        tailf:actionpoint ncsproxy {
          tailf:internal;
        }
        description
          "Clears locally-cached syslog TLS server statistics.";
        input {
          choice clear-scope {
            mandatory true;
            description
              "Clear statistics for all or for a specific syslog TLS server.";
            case server {
              leaf address {
                type inet:host;
                description
                  "Syslog TLS destination target source address or hostname.";
              }
              description
                "Clear stats for this syslog TLS server.";
            }
            case all {
              leaf all {
                type empty;
              }
              description
                "Clear statistics for all syslog TLS servers.";
            }
          }
        }
        output {
          leaf status {
            type ciena-types:ncs_rpc_notif_status;
            description
              "Status of the clear statistics operation.";
          }
        }
      }
    }
  }
  augment "/ncs:devices/ncs:device-group/ncs:ned-id/ncs:rpc" {
    container rpc-clear-syslog-tls-server-stats {
      tailf:ncs-device-type "netconf";
      tailf:display-when "/ncs:devices/ncs:device[ncs:name=current()/../../../ncs:member]/ncs:module[ncs:name='ciena-syslog-tls']";
      tailf:action clear-syslog-tls-server-stats {
        tailf:actionpoint ncsproxy {
          tailf:internal;
        }
        description
          "Clears locally-cached syslog TLS server statistics.";
        input {
          choice clear-scope {
            mandatory true;
            description
              "Clear statistics for all or for a specific syslog TLS server.";
            case server {
              leaf address {
                type inet:host;
                description
                  "Syslog TLS destination target source address or hostname.";
              }
              description
                "Clear stats for this syslog TLS server.";
            }
            case all {
              leaf all {
                type empty;
              }
              description
                "Clear statistics for all syslog TLS servers.";
            }
          }
        }
        output {
          container "device" {
            leaf "name" {
              type string;
            }
            leaf "info" {
              type string;
            }
            container "result" {
              leaf status {
                type ciena-types:ncs_rpc_notif_status;
                description
                  "Status of the clear statistics operation.";
              }
            }
          }
        }
      }
    }
  }
  augment "/ncs:devices/ncs:template/ncs:ned-id/ncs:config/syslog:syslog/syslog:log-actions" {
    container remote-syslog-tls {
      description
        "This container describes  the syslog over TLS configuration for remote logginng.";
      leaf admin-state {
        type ciena-types:ncs_template_admin-state;
        // NCS drop default statement
        description
          "The administrative state of syslog TLS.";
      }
      leaf tls-service-profile {
        type string;
        description
          "The TLS Service Profile for accepting TLS connections.";
      }
      leaf timeout {
        type string;
        units "seconds";
        // NCS drop default statement
        description
          "Timeout for syslog TLS server response.";
      }
      list destination {
        // NCS patched for predictable order
        ordered-by user;
        key "address";
        // NCS drop max-elements statement
        description
          "This list describes a collection of remote syslog TLS destination targets.";
        leaf address {
          type string;
          description
            "Syslog TLS server IP address or a DNS domain name.";
        }
        leaf admin-state {
          type ciena-types:ncs_template_admin-state;
          // NCS drop default statement
          description
            "The administrative state of the Syslog TLS server.";
        }
        leaf port {
          type string;
          // NCS drop default statement
          description
            "Port number for syslog over TLS connection.";
        }
        leaf facility {
          type string;
          // NCS drop default statement
          description
            "Describes the syslog facility.";
        }
        leaf-list severity {
          // NCS patched for predictable order
          ordered-by user;
          type syslogtypes:ncs_template_severity;
          description
            "Set a list of severities for the facility.";
        }
        leaf custom-prefix {
          type string;
          description
            "Syslog message prefix.";
        }
      }
    }
  }
  augment "/ncs:devices/ncs:device/ncs:live-status/syslog:syslog/syslog:log-actions" {
    container remote-syslog-tls {
      tailf:ncs-device-type "netconf";
      tailf:display-when "not(../../../../ncs:module) or ../../../../ncs:module[ncs:name='ciena-syslog-tls'] or (../../../../ncs:live-status-protocol[not(ncs:capability)]) or (../../../../ncs:live-status-protocol/ncs:capability/ncs:module[.='ciena-syslog-tls'])";
      description
        "This container describes  the syslog over TLS configuration for remote logginng.";
      leaf admin-state {
        type ciena-types:live_ncs_admin-state;
        // NCS drop default statement
        description
          "The administrative state of syslog TLS.";
      }
      leaf tls-service-profile {
        type leafref {
          path "/ncs:devices/ncs:device/ncs:live-status/ciena-tsp:tls-service-profiles/ciena-tsp:tls-service-profile-name" {
            tailf:xpath-root 3;
          }
        }
        description
          "The TLS Service Profile for accepting TLS connections.";
      }
      leaf timeout {
        type uint8 {
          range "1..30";
        }
        units "seconds";
        // NCS drop default statement
        description
          "Timeout for syslog TLS server response.";
      }
      list destination {
        key "address";
        // NCS drop max-elements statement
        description
          "This list describes a collection of remote syslog TLS destination targets.";
        leaf address {
          type inet:host;
          description
            "Syslog TLS server IP address or a DNS domain name.";
        }
        leaf admin-state {
          type ciena-types:live_ncs_admin-state;
          // NCS drop default statement
          description
            "The administrative state of the Syslog TLS server.";
        }
        leaf port {
          type inet:port-number {
            range "1..65535";
          }
          // NCS drop default statement
          description
            "Port number for syslog over TLS connection.";
        }
        leaf facility {
          type identityref {
            base syslogtypes:syslog-facility;
          }
          // NCS drop default statement
          description
            "Describes the syslog facility.";
        }
        leaf-list severity {
          type syslogtypes:live_ncs_severity;
          description
            "Set a list of severities for the facility.";
        }
        leaf custom-prefix {
          type string {
            length "0..15";
          }
          description
            "Syslog message prefix.";
        }
      }
    }
  }
  augment "/ncs:devices/ncs:device/ncs:config/syslog:syslog/syslog:log-actions" {
    container remote-syslog-tls {
      tailf:ncs-device-type "netconf";
      tailf:display-when "not(../../../../ncs:module) or ../../../../ncs:module[ncs:name='ciena-syslog-tls']";
      description
        "This container describes  the syslog over TLS configuration for remote logginng.";
      leaf admin-state {
        type ciena-types:admin-state;
        default "enabled";
        description
          "The administrative state of syslog TLS.";
      }
      leaf tls-service-profile {
        type leafref {
          path "/ncs:devices/ncs:device/ncs:config/ciena-tsp:tls-service-profiles/ciena-tsp:tls-service-profile-name" {
            tailf:xpath-root 3;
          }
        }
        description
          "The TLS Service Profile for accepting TLS connections.";
      }
      leaf timeout {
        type uint8 {
          range "1..30";
        }
        units "seconds";
        default "6";
        description
          "Timeout for syslog TLS server response.";
      }
      list destination {
        key "address";
        max-elements 4;
        description
          "This list describes a collection of remote syslog TLS destination targets.";
        leaf address {
          type inet:host;
          description
            "Syslog TLS server IP address or a DNS domain name.";
        }
        leaf admin-state {
          type ciena-types:admin-state;
          default "enabled";
          description
            "The administrative state of the Syslog TLS server.";
        }
        leaf port {
          type inet:port-number {
            range "1..65535";
          }
          default "6514";
          description
            "Port number for syslog over TLS connection.";
        }
        leaf facility {
          type identityref {
            base syslogtypes:syslog-facility;
          }
          default "syslogtypes:local6";
          description
            "Describes the syslog facility.";
        }
        leaf-list severity {
          type syslogtypes:severity;
          description
            "Set a list of severities for the facility.";
        }
        leaf custom-prefix {
          type string {
            length "0..15";
          }
          description
            "Syslog message prefix.";
        }
      }
    }
  }
  augment "/ncs:devices/ncs:template/ncs:ned-id/ncs:config/syslog:syslog" {
    // NCS drop config false container 'syslog-tls-state'
  }
  augment "/ncs:devices/ncs:device/ncs:live-status/syslog:syslog" {
    container syslog-tls-state {
      tailf:ncs-device-type "netconf";
      tailf:display-when "not(../../../ncs:module) or ../../../ncs:module[ncs:name='ciena-syslog-tls'] or (../../../ncs:live-status-protocol[not(ncs:capability)]) or (../../../ncs:live-status-protocol/ncs:capability/ncs:module[.='ciena-syslog-tls'])";
      description
        "syslog over TLS state information.";
      leaf oper-state {
        type ciena-types:live_ncs_oper-state;
        description
          "Operational state of syslog over TLS functionality";
      }
      list statistics {
        key "address";
        description
          "A collection of TLS connection statistics.";
        leaf address {
          type inet:host;
          description
            "Syslog TLS server IP address or hostname.";
        }
        leaf oper-state {
          type ciena-types:live_ncs_oper-state;
          description
            "Operational state of syslog TLS server";
        }
        leaf connection-attempts {
          type yang:counter64;
          description
            "Number of connection attempted.";
        }
        leaf successful-connections {
          type yang:counter64;
          description
            "Number of successful connection with server.";
        }
        leaf failed-tcp-connections {
          type yang:counter64;
          description
            "TCP connection failure.";
        }
        leaf failed-tls-connections {
          type yang:counter64;
          description
            "TLS connection failure.";
        }
        leaf timed-out-connections {
          type yang:counter64;
          description
            "Timed out connection with server.";
        }
        leaf unexpected-close-connections {
          type yang:counter64;
          description
            "Unexpected closure of connection.";
        }
        leaf closed-connections {
          type yang:counter64;
          description
            "Number of closed connections.";
        }
        leaf last-transport-error {
          type string;
          description
            "Last transport error during TLS connection with server.";
        }
      }
    }
  }
  augment "/ncs:devices/ncs:device/ncs:config/syslog:syslog" {
    // NCS drop config false container 'syslog-tls-state'
  }
}
