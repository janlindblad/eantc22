module yumaworks-term-msg {
  // Generated by yanger -t ncs
  tailf:mount-id "ciena107-nc-1.0:ciena107-nc-1.0";
  tailf:ncs-device-type "netconf";

  namespace "http://yumaworks.com/ns/yumaworks-term-msg";
  prefix ytm;

  import tailf-common {
    prefix tailf;
  }
  import tailf-ncs {
    prefix ncs;
  }

  organization
    "YumaWorks, Inc.";
  contact
    "Support <support at yumaworks.com>";
  description
    "Notification event for terminal message feature.

     Copyright (c) 2019 YumaWorks, Inc. All rights reserved.

     Redistribution and use in source and binary forms, with or
     without modification, is permitted pursuant to, and subject
     to the license terms contained in, the BSD 3-Clause License
     http://opensource.org/licenses/BSD-3-Clause";

  revision 2019-05-05 {
    description
      "Initial version.";
  }

  augment "/ncs:devices/ncs:device/ncs:notifications/ncs:received-notifications/ncs:notification/ncs:data" {
    container term-msg {
      presence "";
      config false;
      description
        "Used to send terminal messages to the yp-shell client";
      leaf data {
        type string;
        // NCS drop mandatory statement
        description
          "Terminal message to display";
      }
    }
  }
  augment "/ncs:devices/ncs:device/ncs:netconf-notifications/ncs:received-notifications/ncs:notification/ncs:data" {
    container term-msg {
      presence "";
      config false;
      description
        "Used to send terminal messages to the yp-shell client";
      leaf data {
        type string;
        // NCS drop mandatory statement
        description
          "Terminal message to display";
      }
    }
  }
}
