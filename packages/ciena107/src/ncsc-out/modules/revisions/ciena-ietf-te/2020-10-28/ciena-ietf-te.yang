module ciena-ietf-te {
  // Generated by yanger -t ncs
  tailf:mount-id "ciena107-nc-1.0:ciena107-nc-1.0";
  tailf:ncs-device-type "netconf";

  namespace "http://ciena.com/ns/yang/ciena-ietf-te";
  prefix ciena-te;

  import ietf-te-types {
    prefix te-types;
  }
  import openconfig-interfaces {
    prefix oc-if;
  }
  import ciena-openconfig-interfaces {
    prefix cn-oc-if;
  }
  import tailf-common {
    prefix tailf;
  }
  import tailf-ncs {
    prefix ncs;
  }

  organization
    "Ciena Corporation";
  contact
    "Web URL: http://www.ciena.com/
     E-mail:  yang@ciena.com
     Postal:  7035 Ridge Road
     Hanover, Maryland 21076
     U.S.A.
     Phone:   +1 800-921-1144
     Fax:     +1 410-694-5750";
  description
    "This module contains the Ciena proprietary YANG deviations
     of the standard ietf-te and ietf-te-device YANG module.
     Copyright (c) 2016 Ciena Corporation.  All rights reserved.

     All information contained herein is, and remains
     the property of Ciena Corporation. Dissemination of this
     information or reproduction of this material is strictly
     forbidden unless prior written permission is obtained from
     Ciena Corporation.";

  revision 2020-10-28 {
    description
      "Initial version";
    reference
      "IETF-DRAFT: A YANG Data Model for Traffic Engineering Tunnels, Label Switched Paths and Interfaces
       and RFC 8795";
  }

  grouping ncs_template_max-link-bandwidth-config {
    description
      "Maximum bandwidth grouping";
    leaf max-link-bandwidth {
      type te-types:ncs_template_te-bandwidth;
      description
        "Maximum bandwidth that can be seen on this link in this
         direction.  It is a string containing a non-negative decimal or
         formatted as external hexadecimal-significant character
         sequences specified in IEEE 754 and ISO/IEC C99.
         Units are in bytes per second.";
    }
  }

  grouping ncs_template_max-resv-link-bandwidth-config {
    description
      "Maximum reservable bandwidth grouping";
    choice max-resv-link-bandwidth-type {
      description
        "Maximum reservable bandwidth type choice";
      case value {
        leaf max-resv-link-bandwidth {
          type te-types:ncs_template_te-bandwidth;
          description
            "Maximum amount of bandwidth that can be reserved in this
             direction in this link.  It is a string containing a non-negative
             decimal or formatted as external hexadecimal-significant
             character sequences specified in IEEE 754 and ISO/IEC C99.
             Units are in bytes per second.";
        }
      }
      case percent {
        leaf max-resv-link-bandwidth-percent {
          type string;
          description
            "Percentage of max-link-bandwidth that can be reserved in this
             direction in this link.";
        }
      }
    }
  }

  grouping ncs_template_te-delay-metric-config {
    description
      "Delay metric grouping";
    leaf te-delay-metric {
      type string;
      units "microseconds";
      description
        "Traffic Engineering unidirectional delay metric.";
    }
  }

  grouping ncs_template_te-metric-extensions-threshold-config {
    description
      "Configurable thresholds for advertising TE Metric Extensions.";
    leaf delay-maximum-threshold {
      type string;
      units "microseconds";
      description
        "Maximum threshold exceeding which Unidirectional delay is considered anomalous.
         Value greater than zero.";
    }
  }

  grouping ncs_template_te-metric-config {
    description
      "TE interface metric grouping.";
    leaf te-metric {
      type te-types:ncs_template_te-metric;
      description
        "TE interface metric.";
    }
  }

  grouping ncs_template_te-admin-groups-config {
    description
      "TE interface affinities grouping.";
    choice admin-group-type {
      description
        "TE interface administrative groups
         representation type.";
      case named-admin-groups {
        list named-admin-groups {
          // NCS patched for predictable order
          ordered-by user;
          // NCS drop if-feature statement
          // NCS drop if-feature statement
          key "named-admin-group";
          description
            "A list of named admin-group entries.";
          leaf named-admin-group {
            type string;
            description
              "A named admin-group entry.";
          }
        }
      }
    }
  }

  grouping ncs_template_te-srlgs-config {
    description
      "TE interface SRLG grouping.";
    choice srlg-type {
      description
        "Choice of SRLG configuration.";
      case value-srlgs {
        list srlg-values {
          // NCS patched for predictable order
          ordered-by user;
          key "value";
          description
            "List of SRLG values that
             this link is part of.";
          leaf value {
            type string;
            description
              "Value of the SRLG";
          }
        }
      }
    }
  }

  grouping ncs_template_te-attributes {
    description
      "TE attributes configuration grouping.";
    uses ncs_template_te-metric-config;
    uses ncs_template_te-delay-metric-config;
    uses ncs_template_te-admin-groups-config;
    uses ncs_template_te-srlgs-config;
    uses ncs_template_max-link-bandwidth-config;
    uses ncs_template_max-resv-link-bandwidth-config;
    uses ncs_template_te-metric-extensions-threshold-config;
  }

  grouping ncs_template_interfaces-grouping {
    description
      "TE interface configuration data grouping.";
    container interfaces {
      description
        "Configuration data model for TE interfaces.";
      list interface {
        // NCS patched for predictable order
        ordered-by user;
        key "interface";
        description
          "TE interfaces.";
        leaf interface {
          type string;
          // NCS drop must statement
          description
            "TE interface name.";
        }
        leaf admin-status {
          type te-types:ncs_template_te-admin-status;
          // NCS drop default statement
          description
            "The administrative state of the link.
             If status is down then no TE attribute will be signalled";
        }
        uses ncs_template_te-attributes;
      }
    }
  }

  grouping ncs_template_named-admin-groups-properties {
    description
      "Global named administrative groups configuration
       grouping.";
    leaf name {
      type string;
      description
        "A string name that uniquely identifies a TE
         interface named admin-group.";
    }
    leaf bit-position {
      type string;
      // NCS drop mandatory statement
      description
        "Bit position representing the administrative group.";
      reference "RFC3209 and RFC7308";
    }
  }

  grouping ncs_template_named-admin-groups {
    description
      "Global named administrative groups configuration
       grouping.";
    container named-admin-groups {
      description
        "TE named admin groups container.";
      list named-admin-group {
        // NCS patched for predictable order
        ordered-by user;
        // NCS drop if-feature statement
        // NCS drop if-feature statement
        key "name";
        description
          "List of named TE admin-groups.";
        uses ncs_template_named-admin-groups-properties;
      }
    }
  }

  grouping ncs_template_globals-grouping {
    description
      "Globals TE system-wide configuration data grouping.";
    container globals {
      description
        "Globals TE system-wide configuration data container.";
      uses ncs_template_named-admin-groups;
    }
  }

  grouping ncs_rpc_notif_max-link-bandwidth-config {
    description
      "Maximum bandwidth grouping";
    leaf max-link-bandwidth {
      type te-types:ncs_rpc_notif_te-bandwidth;
      description
        "Maximum bandwidth that can be seen on this link in this
         direction.  It is a string containing a non-negative decimal or
         formatted as external hexadecimal-significant character
         sequences specified in IEEE 754 and ISO/IEC C99.
         Units are in bytes per second.";
    }
  }

  grouping ncs_rpc_notif_max-resv-link-bandwidth-config {
    description
      "Maximum reservable bandwidth grouping";
    choice max-resv-link-bandwidth-type {
      description
        "Maximum reservable bandwidth type choice";
      case value {
        leaf max-resv-link-bandwidth {
          type te-types:ncs_rpc_notif_te-bandwidth;
          description
            "Maximum amount of bandwidth that can be reserved in this
             direction in this link.  It is a string containing a non-negative
             decimal or formatted as external hexadecimal-significant
             character sequences specified in IEEE 754 and ISO/IEC C99.
             Units are in bytes per second.";
        }
      }
      case percent {
        leaf max-resv-link-bandwidth-percent {
          type uint32 {
            range "1..100";
          }
          description
            "Percentage of max-link-bandwidth that can be reserved in this
             direction in this link.";
        }
      }
    }
  }

  grouping ncs_rpc_notif_te-delay-metric-config {
    description
      "Delay metric grouping";
    leaf te-delay-metric {
      type uint32 {
        range "1..16777215";
      }
      units "microseconds";
      description
        "Traffic Engineering unidirectional delay metric.";
    }
  }

  grouping ncs_rpc_notif_te-metric-extensions-threshold-config {
    description
      "Configurable thresholds for advertising TE Metric Extensions.";
    leaf delay-maximum-threshold {
      type uint32;
      units "microseconds";
      description
        "Maximum threshold exceeding which Unidirectional delay is considered anomalous.
         Value greater than zero.";
    }
  }

  grouping ncs_rpc_notif_te-metric-config {
    description
      "TE interface metric grouping.";
    leaf te-metric {
      type te-types:ncs_rpc_notif_te-metric;
      description
        "TE interface metric.";
    }
  }

  grouping ncs_rpc_notif_te-admin-groups-config {
    description
      "TE interface affinities grouping.";
    choice admin-group-type {
      description
        "TE interface administrative groups
         representation type.";
      case named-admin-groups {
        list named-admin-groups {
          tailf:display-when "not(../../ncs:module) or boolean(/ncs:devices/ncs:device[ncs:name=current()/../../ncs:name]/capability/feature='te-types:extended-admin-groups')";
          tailf:display-when "not(../../ncs:module) or boolean(/ncs:devices/ncs:device[ncs:name=current()/../../ncs:name]/capability/feature='te-types:named-extended-admin-groups')";
          key "named-admin-group";
          description
            "A list of named admin-group entries.";
          leaf named-admin-group {
            type string;
            description
              "A named admin-group entry.";
          }
        }
      }
    }
  }

  grouping ncs_rpc_notif_te-srlgs-config {
    description
      "TE interface SRLG grouping.";
    choice srlg-type {
      description
        "Choice of SRLG configuration.";
      case value-srlgs {
        list srlg-values {
          key "value";
          description
            "List of SRLG values that
             this link is part of.";
          leaf value {
            type uint32 {
              range "0..4294967295";
            }
            description
              "Value of the SRLG";
          }
        }
      }
    }
  }

  grouping ncs_rpc_notif_te-attributes {
    description
      "TE attributes configuration grouping.";
    uses ncs_rpc_notif_te-metric-config;
    uses ncs_rpc_notif_te-delay-metric-config;
    uses ncs_rpc_notif_te-admin-groups-config;
    uses ncs_rpc_notif_te-srlgs-config;
    uses ncs_rpc_notif_max-link-bandwidth-config;
    uses ncs_rpc_notif_max-resv-link-bandwidth-config;
    uses ncs_rpc_notif_te-metric-extensions-threshold-config;
  }

  grouping ncs_rpc_notif_interfaces-grouping {
    description
      "TE interface configuration data grouping.";
    container interfaces {
      description
        "Configuration data model for TE interfaces.";
      list interface {
        key "interface";
        description
          "TE interfaces.";
        leaf interface {
          type string;
          must "/oc-if:interfaces/oc-if:interface[oc-if:name=current()]/oc-if:config/cn-oc-if:type[.='ip' or .='ip-unnumbered' or .='point-to-point']" {
            tailf:xpath-root 3;
            error-message "TE properties can be set only on 'ip', 'ip-unnumbered' and 'point-to-point' interface";
          }
          description
            "TE interface name.";
        }
        leaf admin-status {
          type te-types:ncs_rpc_notif_te-admin-status;
          default "up";
          description
            "The administrative state of the link.
             If status is down then no TE attribute will be signalled";
        }
        uses ncs_rpc_notif_te-attributes;
      }
    }
  }

  grouping ncs_rpc_notif_named-admin-groups-properties {
    description
      "Global named administrative groups configuration
       grouping.";
    leaf name {
      type string {
        length "1..31";
      }
      description
        "A string name that uniquely identifies a TE
         interface named admin-group.";
    }
    leaf bit-position {
      type uint32 {
        range "0..31";
      }
      mandatory true;
      description
        "Bit position representing the administrative group.";
      reference "RFC3209 and RFC7308";
    }
  }

  grouping ncs_rpc_notif_named-admin-groups {
    description
      "Global named administrative groups configuration
       grouping.";
    container named-admin-groups {
      description
        "TE named admin groups container.";
      list named-admin-group {
        tailf:display-when "not(../ncs:module) or boolean(/ncs:devices/ncs:device[ncs:name=current()/../ncs:name]/capability/feature='te-types:extended-admin-groups')";
        tailf:display-when "not(../ncs:module) or boolean(/ncs:devices/ncs:device[ncs:name=current()/../ncs:name]/capability/feature='te-types:named-extended-admin-groups')";
        key "name";
        description
          "List of named TE admin-groups.";
        uses ncs_rpc_notif_named-admin-groups-properties;
      }
    }
  }

  grouping ncs_rpc_notif_globals-grouping {
    description
      "Globals TE system-wide configuration data grouping.";
    container globals {
      description
        "Globals TE system-wide configuration data container.";
      uses ncs_rpc_notif_named-admin-groups;
    }
  }

  grouping live_ncs_max-link-bandwidth-config {
    description
      "Maximum bandwidth grouping";
    leaf max-link-bandwidth {
      type te-types:live_ncs_te-bandwidth;
      description
        "Maximum bandwidth that can be seen on this link in this
         direction.  It is a string containing a non-negative decimal or
         formatted as external hexadecimal-significant character
         sequences specified in IEEE 754 and ISO/IEC C99.
         Units are in bytes per second.";
    }
  }

  grouping live_ncs_max-resv-link-bandwidth-config {
    description
      "Maximum reservable bandwidth grouping";
    choice max-resv-link-bandwidth-type {
      description
        "Maximum reservable bandwidth type choice";
      case value {
        leaf max-resv-link-bandwidth {
          type te-types:live_ncs_te-bandwidth;
          description
            "Maximum amount of bandwidth that can be reserved in this
             direction in this link.  It is a string containing a non-negative
             decimal or formatted as external hexadecimal-significant
             character sequences specified in IEEE 754 and ISO/IEC C99.
             Units are in bytes per second.";
        }
      }
      case percent {
        leaf max-resv-link-bandwidth-percent {
          type uint32 {
            range "1..100";
          }
          description
            "Percentage of max-link-bandwidth that can be reserved in this
             direction in this link.";
        }
      }
    }
  }

  grouping live_ncs_te-delay-metric-config {
    description
      "Delay metric grouping";
    leaf te-delay-metric {
      type uint32 {
        range "1..16777215";
      }
      units "microseconds";
      description
        "Traffic Engineering unidirectional delay metric.";
    }
  }

  grouping live_ncs_te-metric-extensions-threshold-config {
    description
      "Configurable thresholds for advertising TE Metric Extensions.";
    leaf delay-maximum-threshold {
      type uint32;
      units "microseconds";
      description
        "Maximum threshold exceeding which Unidirectional delay is considered anomalous.
         Value greater than zero.";
    }
  }

  grouping live_ncs_te-metric-config {
    description
      "TE interface metric grouping.";
    leaf te-metric {
      type te-types:live_ncs_te-metric;
      description
        "TE interface metric.";
    }
  }

  grouping live_ncs_te-admin-groups-config {
    description
      "TE interface affinities grouping.";
    choice admin-group-type {
      description
        "TE interface administrative groups
         representation type.";
      case named-admin-groups {
        list named-admin-groups {
          // NCS drop if-feature statement
          // NCS drop if-feature statement
          key "named-admin-group";
          description
            "A list of named admin-group entries.";
          leaf named-admin-group {
            type leafref {
              path "/ncs:devices/ncs:device/ncs:live-status/ciena-te:te/ciena-te:globals/ciena-te:named-admin-groups/ciena-te:named-admin-group/ciena-te:name" {
                tailf:xpath-root 3;
              }
            }
            description
              "A named admin-group entry.";
          }
        }
      }
    }
  }

  grouping live_ncs_te-srlgs-config {
    description
      "TE interface SRLG grouping.";
    choice srlg-type {
      description
        "Choice of SRLG configuration.";
      case value-srlgs {
        list srlg-values {
          key "value";
          description
            "List of SRLG values that
             this link is part of.";
          leaf value {
            type uint32 {
              range "0..4294967295";
            }
            description
              "Value of the SRLG";
          }
        }
      }
    }
  }

  grouping live_ncs_te-attributes {
    description
      "TE attributes configuration grouping.";
    uses live_ncs_te-metric-config;
    uses live_ncs_te-delay-metric-config;
    uses live_ncs_te-admin-groups-config;
    uses live_ncs_te-srlgs-config;
    uses live_ncs_max-link-bandwidth-config;
    uses live_ncs_max-resv-link-bandwidth-config;
    uses live_ncs_te-metric-extensions-threshold-config;
  }

  grouping live_ncs_interfaces-grouping {
    description
      "TE interface configuration data grouping.";
    container interfaces {
      description
        "Configuration data model for TE interfaces.";
      list interface {
        key "interface";
        description
          "TE interfaces.";
        leaf interface {
          type leafref {
            path "/ncs:devices/ncs:device/ncs:live-status/oc-if:interfaces/oc-if:interface/oc-if:name" {
              tailf:xpath-root 3;
            }
          }
          // NCS drop must statement
          description
            "TE interface name.";
        }
        leaf admin-status {
          type te-types:live_ncs_te-admin-status;
          // NCS drop default statement
          description
            "The administrative state of the link.
             If status is down then no TE attribute will be signalled";
        }
        uses live_ncs_te-attributes;
      }
    }
  }

  grouping live_ncs_named-admin-groups-properties {
    description
      "Global named administrative groups configuration
       grouping.";
    leaf name {
      type string {
        length "1..31";
      }
      description
        "A string name that uniquely identifies a TE
         interface named admin-group.";
    }
    leaf bit-position {
      type uint32 {
        range "0..31";
      }
      // NCS drop mandatory statement
      description
        "Bit position representing the administrative group.";
      reference "RFC3209 and RFC7308";
    }
  }

  grouping live_ncs_named-admin-groups {
    description
      "Global named administrative groups configuration
       grouping.";
    container named-admin-groups {
      description
        "TE named admin groups container.";
      list named-admin-group {
        // NCS drop if-feature statement
        // NCS drop if-feature statement
        key "name";
        description
          "List of named TE admin-groups.";
        uses live_ncs_named-admin-groups-properties;
      }
    }
  }

  grouping live_ncs_globals-grouping {
    description
      "Globals TE system-wide configuration data grouping.";
    container globals {
      description
        "Globals TE system-wide configuration data container.";
      uses live_ncs_named-admin-groups;
    }
  }

  grouping max-link-bandwidth-config {
    description
      "Maximum bandwidth grouping";
    leaf max-link-bandwidth {
      type te-types:te-bandwidth;
      description
        "Maximum bandwidth that can be seen on this link in this
         direction.  It is a string containing a non-negative decimal or
         formatted as external hexadecimal-significant character
         sequences specified in IEEE 754 and ISO/IEC C99.
         Units are in bytes per second.";
    }
  }

  grouping max-resv-link-bandwidth-config {
    description
      "Maximum reservable bandwidth grouping";
    choice max-resv-link-bandwidth-type {
      description
        "Maximum reservable bandwidth type choice";
      case value {
        leaf max-resv-link-bandwidth {
          type te-types:te-bandwidth;
          description
            "Maximum amount of bandwidth that can be reserved in this
             direction in this link.  It is a string containing a non-negative
             decimal or formatted as external hexadecimal-significant
             character sequences specified in IEEE 754 and ISO/IEC C99.
             Units are in bytes per second.";
        }
      }
      case percent {
        leaf max-resv-link-bandwidth-percent {
          type uint32 {
            range "1..100";
          }
          description
            "Percentage of max-link-bandwidth that can be reserved in this
             direction in this link.";
        }
      }
    }
  }

  grouping te-delay-metric-config {
    description
      "Delay metric grouping";
    leaf te-delay-metric {
      type uint32 {
        range "1..16777215";
      }
      units "microseconds";
      description
        "Traffic Engineering unidirectional delay metric.";
    }
  }

  grouping te-metric-extensions-threshold-config {
    description
      "Configurable thresholds for advertising TE Metric Extensions.";
    leaf delay-maximum-threshold {
      type uint32;
      units "microseconds";
      description
        "Maximum threshold exceeding which Unidirectional delay is considered anomalous.
         Value greater than zero.";
    }
  }

  grouping te-metric-config {
    description
      "TE interface metric grouping.";
    leaf te-metric {
      type te-types:te-metric {
        range "1..16777215";
      }
      description
        "TE interface metric.";
    }
  }

  grouping te-admin-groups-config {
    description
      "TE interface affinities grouping.";
    choice admin-group-type {
      description
        "TE interface administrative groups
         representation type.";
      case named-admin-groups {
        list named-admin-groups {
          tailf:display-when "not(../../ncs:module) or boolean(/ncs:devices/ncs:device[ncs:name=current()/../../ncs:name]/capability/feature='te-types:extended-admin-groups')";
          tailf:display-when "not(../../ncs:module) or boolean(/ncs:devices/ncs:device[ncs:name=current()/../../ncs:name]/capability/feature='te-types:named-extended-admin-groups')";
          key "named-admin-group";
          description
            "A list of named admin-group entries.";
          leaf named-admin-group {
            type leafref {
              path "/ncs:devices/ncs:device/ncs:config/ciena-te:te/ciena-te:globals/ciena-te:named-admin-groups/ciena-te:named-admin-group/ciena-te:name" {
                tailf:xpath-root 3;
              }
            }
            description
              "A named admin-group entry.";
          }
        }
      }
    }
  }

  grouping te-srlgs-config {
    description
      "TE interface SRLG grouping.";
    choice srlg-type {
      description
        "Choice of SRLG configuration.";
      case value-srlgs {
        list srlg-values {
          key "value";
          description
            "List of SRLG values that
             this link is part of.";
          leaf value {
            type uint32 {
              range "0..4294967295";
            }
            description
              "Value of the SRLG";
          }
        }
      }
    }
  }

  grouping te-attributes {
    description
      "TE attributes configuration grouping.";
    uses te-metric-config;
    uses te-delay-metric-config;
    uses te-admin-groups-config;
    uses te-srlgs-config;
    uses max-link-bandwidth-config;
    uses max-resv-link-bandwidth-config;
    uses te-metric-extensions-threshold-config;
  }

  grouping interfaces-grouping {
    description
      "TE interface configuration data grouping.";
    container interfaces {
      description
        "Configuration data model for TE interfaces.";
      list interface {
        key "interface";
        description
          "TE interfaces.";
        leaf interface {
          type leafref {
            path "/ncs:devices/ncs:device/ncs:config/oc-if:interfaces/oc-if:interface/oc-if:name" {
              tailf:xpath-root 3;
            }
          }
          must "/oc-if:interfaces/oc-if:interface[oc-if:name=current()]/oc-if:config/cn-oc-if:type[.='ip' or .='ip-unnumbered' or .='point-to-point']" {
            tailf:xpath-root 3;
            error-message "TE properties can be set only on 'ip', 'ip-unnumbered' and 'point-to-point' interface";
          }
          description
            "TE interface name.";
        }
        leaf admin-status {
          type te-types:te-admin-status;
          default "up";
          description
            "The administrative state of the link.
             If status is down then no TE attribute will be signalled";
        }
        uses te-attributes;
      }
    }
  }

  grouping named-admin-groups-properties {
    description
      "Global named administrative groups configuration
       grouping.";
    leaf name {
      type string {
        length "1..31";
      }
      description
        "A string name that uniquely identifies a TE
         interface named admin-group.";
    }
    leaf bit-position {
      type uint32 {
        range "0..31";
      }
      mandatory true;
      description
        "Bit position representing the administrative group.";
      reference "RFC3209 and RFC7308";
    }
  }

  grouping named-admin-groups {
    description
      "Global named administrative groups configuration
       grouping.";
    container named-admin-groups {
      description
        "TE named admin groups container.";
      list named-admin-group {
        tailf:display-when "not(../ncs:module) or boolean(/ncs:devices/ncs:device[ncs:name=current()/../ncs:name]/capability/feature='te-types:extended-admin-groups')";
        tailf:display-when "not(../ncs:module) or boolean(/ncs:devices/ncs:device[ncs:name=current()/../ncs:name]/capability/feature='te-types:named-extended-admin-groups')";
        key "name";
        description
          "List of named TE admin-groups.";
        uses named-admin-groups-properties;
      }
    }
  }

  grouping globals-grouping {
    description
      "Globals TE system-wide configuration data grouping.";
    container globals {
      description
        "Globals TE system-wide configuration data container.";
      uses named-admin-groups;
    }
  }

  augment "/ncs:devices/ncs:device/ncs:config" {
    container te {
      tailf:ncs-device-type "netconf";
      tailf:display-when "not(../../ncs:module) or ../../ncs:module[ncs:name='ciena-ietf-te']";
      description
        "TE global container.";
      uses globals-grouping;
      uses interfaces-grouping;
    }
    // NCS drop config false container 'te-state'
  }
  augment "/ncs:devices/ncs:device/ncs:live-status" {
    container te {
      tailf:ncs-device-type "netconf";
      tailf:display-when "not(../../ncs:module) or ../../ncs:module[ncs:name='ciena-ietf-te'] or (../../ncs:live-status-protocol[not(ncs:capability)]) or (../../ncs:live-status-protocol/ncs:capability/ncs:module[.='ciena-ietf-te'])";
      description
        "TE global container.";
      uses live_ncs_globals-grouping;
      uses live_ncs_interfaces-grouping;
    }
    container te-state {
      tailf:ncs-device-type "netconf";
      tailf:display-when "not(../../ncs:module) or ../../ncs:module[ncs:name='ciena-ietf-te'] or (../../ncs:live-status-protocol[not(ncs:capability)]) or (../../ncs:live-status-protocol/ncs:capability/ncs:module[.='ciena-ietf-te'])";
      description
        "TE global container information.";
      container interfaces {
        description
          "Configuration data model for TE interfaces.";
        list interface {
          key "interface";
          description
            "TE interfaces.";
          leaf interface {
            type leafref {
              path "/ncs:devices/ncs:device/ncs:live-status/oc-if:interfaces/oc-if:interface/oc-if:name" {
                tailf:xpath-root 3;
              }
            }
            description
              "TE interface name.";
          }
          leaf link-index {
            type uint64;
            description
              "The link identifier represents a unique value, which is
               locally defined in a router.";
          }
        }
      }
    }
  }
  augment "/ncs:devices/ncs:template/ncs:ned-id/ncs:config" {
    container te {
      description
        "TE global container.";
      uses ncs_template_globals-grouping;
      uses ncs_template_interfaces-grouping;
    }
    // NCS drop config false container 'te-state'
  }
}
