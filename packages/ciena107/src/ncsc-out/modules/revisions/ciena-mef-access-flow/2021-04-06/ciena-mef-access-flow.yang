module ciena-mef-access-flow {
  // Generated by yanger -t ncs
  tailf:mount-id "ciena107-nc-1.0:ciena107-nc-1.0";
  tailf:ncs-device-type "netconf";

  namespace "urn:ciena:params:xml:ns:yang:ciena-pn::ciena-mef-access-flow";
  prefix acl;

  import ciena-mef-classifier {
    prefix classifier;
  }
  import ciena-mef-logical-port {
    prefix mef-logical-port;
  }
  import ciena-mef-fp {
    prefix mef-fp;
  }
  import tailf-common {
    prefix tailf;
  }
  import tailf-ncs {
    prefix ncs;
  }

  organization
    "Ciena Corporation";
  contact
    "Web URL: http://www.ciena.com/
     E-mail:  yang@ciena.com
     Postal:  7035 Ridge Road
     Hanover, Maryland 21076
     U.S.A.
     Phone:   +1 800-921-1144
     Fax:     +1 410-694-5750";
  description
    "This YANG module defines Access Flows and Access Profiles.";

  revision 2021-04-06 {
    description
      "Added descriptions";
  }
  revision 2020-02-17 {
    description
      "Refactored access-profiles container to use access-flow-config
       and classifier-group groupings.";
  }
  revision 2016-02-03 {
    description
      "Initial revision";
  }

  typedef ncs_template_access-flow-ref {
    type string;
    description
      "This type is used by the data models that needs to reference
       configured Access flows.";
  }

  typedef ncs_template_acl-action-ref {
    type string;
    description
      "This type is used by the data models that needs to reference
       configured ACL actions.";
  }

  typedef ncs_template_custom-destination-ref {
    type string;
    description
      "This type is used by the data models that needs to reference
       custom destinations for ACLs.";
  }

  typedef ncs_template_access-profile-ref {
    type string;
    description
      "This type is used by the data models that need to reference
       configured Access profiles.";
  }

  typedef ncs_rpc_notif_access-flow-ref {
    type string;
    description
      "This type is used by the data models that needs to reference
       configured Access flows.";
  }

  typedef ncs_rpc_notif_acl-action-ref {
    type string;
    description
      "This type is used by the data models that needs to reference
       configured ACL actions.";
  }

  typedef ncs_rpc_notif_custom-destination-ref {
    type string;
    description
      "This type is used by the data models that needs to reference
       custom destinations for ACLs.";
  }

  typedef ncs_rpc_notif_access-profile-ref {
    type string;
    description
      "This type is used by the data models that need to reference
       configured Access profiles.";
  }

  typedef live_ncs_access-flow-ref {
    type leafref {
      path "/ncs:devices/ncs:device/ncs:live-status/acl:access-flows/acl:access-flow/acl:name" {
        tailf:xpath-root 3;
      }
    }
    description
      "This type is used by the data models that needs to reference
       configured Access flows.";
  }

  typedef live_ncs_acl-action-ref {
    type leafref {
      path "/ncs:devices/ncs:device/ncs:live-status/acl:acl-actions/acl:acl-action/acl:name" {
        tailf:xpath-root 3;
      }
    }
    description
      "This type is used by the data models that needs to reference
       configured ACL actions.";
  }

  typedef live_ncs_custom-destination-ref {
    type leafref {
      path "/ncs:devices/ncs:device/ncs:live-status/acl:acl-custom-destinations/acl:acl-custom-destination/acl:name" {
        tailf:xpath-root 3;
      }
    }
    description
      "This type is used by the data models that needs to reference
       custom destinations for ACLs.";
  }

  typedef live_ncs_access-profile-ref {
    type leafref {
      path "/ncs:devices/ncs:device/ncs:live-status/acl:access-profiles/acl:access-profile/acl:name" {
        tailf:xpath-root 3;
      }
    }
    description
      "This type is used by the data models that need to reference
       configured Access profiles.";
  }

  typedef access-flow-ref {
    type leafref {
      path "/ncs:devices/ncs:device/ncs:config/acl:access-flows/acl:access-flow/acl:name" {
        tailf:xpath-root 3;
      }
    }
    description
      "This type is used by the data models that needs to reference
       configured Access flows.";
  }

  typedef acl-action-ref {
    type leafref {
      path "/ncs:devices/ncs:device/ncs:config/acl:acl-actions/acl:acl-action/acl:name" {
        tailf:xpath-root 3;
      }
    }
    description
      "This type is used by the data models that needs to reference
       configured ACL actions.";
  }

  typedef custom-destination-ref {
    type leafref {
      path "/ncs:devices/ncs:device/ncs:config/acl:acl-custom-destinations/acl:acl-custom-destination/acl:name" {
        tailf:xpath-root 3;
      }
    }
    description
      "This type is used by the data models that needs to reference
       custom destinations for ACLs.";
  }

  typedef access-profile-ref {
    type leafref {
      path "/ncs:devices/ncs:device/ncs:config/acl:access-profiles/acl:access-profile/acl:name" {
        tailf:xpath-root 3;
      }
    }
    description
      "This type is used by the data models that need to reference
       configured Access profiles.";
  }

  grouping ncs_template_acl-destination {
    choice destination {
      case logical-port-list {
        leaf-list logical-port {
          // NCS patched for predictable order
          ordered-by user;
          type mef-logical-port:ncs_template_logical-port-ref;
          description
            "One or more logical-ports which act as destination for the acl-action (e.g. mirror/redirect)";
        }
        description
          "One or more logical-ports which act as destination for the acl-action (e.g. mirror/redirect)";
      }
      case flow-point-list {
        leaf-list flow-point {
          // NCS patched for predictable order
          ordered-by user;
          type mef-fp:ncs_template_fp-ref;
          description
            "One or more flow-points which act as destination for the acl-action (e.g. mirror/redirect)";
        }
        description
          "One or more flow-points which act as destination for the acl-action (e.g. mirror/redirect)";
      }
      case custom-list {
        leaf-list custom {
          // NCS patched for predictable order
          ordered-by user;
          type acl:ncs_template_custom-destination-ref;
          description
            "One or more custom destinations which act as destination for the acl-action (e.g. mirror/redirect)";
        }
        description
          "One or more custom destinations which act as destination for the acl-action (e.g. mirror/redirect)";
      }
    }
  }

  grouping ncs_template_custom-acl-action {
    list acl-action {
      // NCS patched for predictable order
      ordered-by user;
      key "name";
      description
        "A list of ACL-actions, where each ACL-action specifies the action of the classified flow.";
      leaf name {
        type string;
        description
          "A unique string that is either system assigned or assigned
           by the user but does not change over its life.";
      }
      leaf description {
        type string;
        description
          "A more detailed description that an operator can use
           to describe the action.";
      }
      leaf action {
        type string;
        description
          "Specifies an action for this acl action";
      }
      uses acl:ncs_template_acl-destination;
    }
  }

  grouping ncs_template_access-flow-config {
    leaf description {
      type string;
      description
        "A more detailed description that an operator can use
         to describe the flow.";
    }
    leaf classifier-list-precedence {
      type string;
      description
        "A precedence value for the access flow. Lower values take
         precedence over higher values";
    }
    leaf filter-action {
      type string;
      description
        "Specifies the filter-action for this Access-Flow/ACL-Rule";
    }
    leaf stats-collection {
      type string;
      description
        "Determines whether stats collection will be turned on or not for an access-flow";
    }
  }

  grouping ncs_rpc_notif_acl-destination {
    choice destination {
      case logical-port-list {
        leaf-list logical-port {
          type mef-logical-port:ncs_rpc_notif_logical-port-ref;
          description
            "One or more logical-ports which act as destination for the acl-action (e.g. mirror/redirect)";
        }
        description
          "One or more logical-ports which act as destination for the acl-action (e.g. mirror/redirect)";
      }
      case flow-point-list {
        leaf-list flow-point {
          type mef-fp:ncs_rpc_notif_fp-ref;
          description
            "One or more flow-points which act as destination for the acl-action (e.g. mirror/redirect)";
        }
        description
          "One or more flow-points which act as destination for the acl-action (e.g. mirror/redirect)";
      }
      case custom-list {
        leaf-list custom {
          type acl:ncs_rpc_notif_custom-destination-ref;
          description
            "One or more custom destinations which act as destination for the acl-action (e.g. mirror/redirect)";
        }
        description
          "One or more custom destinations which act as destination for the acl-action (e.g. mirror/redirect)";
      }
    }
  }

  grouping ncs_rpc_notif_custom-acl-action {
    list acl-action {
      key "name";
      description
        "A list of ACL-actions, where each ACL-action specifies the action of the classified flow.";
      leaf name {
        type string;
        description
          "A unique string that is either system assigned or assigned
           by the user but does not change over its life.";
      }
      leaf description {
        type string;
        description
          "A more detailed description that an operator can use
           to describe the action.";
      }
      leaf action {
        type enumeration {
          enum "redirect" {
            description
              "Redirect the classified flow to one or more ports/flow-points etc.";
          }
          enum "ingress-mirror" {
            description
              "Ingress-Mirror the classified flow to one or more ports/flow-points etc.";
          }
        }
        description
          "Specifies an action for this acl action";
      }
      uses acl:ncs_rpc_notif_acl-destination;
    }
  }

  grouping ncs_rpc_notif_access-flow-config {
    leaf description {
      type string;
      description
        "A more detailed description that an operator can use
         to describe the flow.";
    }
    leaf classifier-list-precedence {
      type uint32;
      description
        "A precedence value for the access flow. Lower values take
         precedence over higher values";
    }
    leaf filter-action {
      type enumeration {
        enum "deny" {
          description
            "Drop traffic for traffic that matches this specific access-flow-rule.
             This may be augmented with specific actions in the action list for this traffic flow";
        }
        enum "allow" {
          description
            "Do not drop traffic for traffic that matches this specific access-flow-rule.
             This may be augmented with specific actions in the action list for this traffic flow";
        }
      }
      description
        "Specifies the filter-action for this Access-Flow/ACL-Rule";
    }
    leaf stats-collection {
      type enumeration {
        enum "on" {
          description
            "Stats collection turned on";
        }
        enum "off" {
          description
            "Stats collection turned off";
        }
      }
      description
        "Determines whether stats collection will be turned on or not for an access-flow";
    }
  }

  grouping live_ncs_acl-destination {
    choice destination {
      case logical-port-list {
        leaf-list logical-port {
          type mef-logical-port:live_ncs_logical-port-ref;
          description
            "One or more logical-ports which act as destination for the acl-action (e.g. mirror/redirect)";
        }
        description
          "One or more logical-ports which act as destination for the acl-action (e.g. mirror/redirect)";
      }
      case flow-point-list {
        leaf-list flow-point {
          type mef-fp:live_ncs_fp-ref;
          description
            "One or more flow-points which act as destination for the acl-action (e.g. mirror/redirect)";
        }
        description
          "One or more flow-points which act as destination for the acl-action (e.g. mirror/redirect)";
      }
      case custom-list {
        leaf-list custom {
          type acl:live_ncs_custom-destination-ref;
          description
            "One or more custom destinations which act as destination for the acl-action (e.g. mirror/redirect)";
        }
        description
          "One or more custom destinations which act as destination for the acl-action (e.g. mirror/redirect)";
      }
    }
  }

  grouping live_ncs_custom-acl-action {
    list acl-action {
      key "name";
      description
        "A list of ACL-actions, where each ACL-action specifies the action of the classified flow.";
      leaf name {
        type string;
        description
          "A unique string that is either system assigned or assigned
           by the user but does not change over its life.";
      }
      leaf description {
        type string;
        description
          "A more detailed description that an operator can use
           to describe the action.";
      }
      leaf action {
        type enumeration {
          enum "redirect" {
            description
              "Redirect the classified flow to one or more ports/flow-points etc.";
          }
          enum "ingress-mirror" {
            description
              "Ingress-Mirror the classified flow to one or more ports/flow-points etc.";
          }
        }
        description
          "Specifies an action for this acl action";
      }
      uses acl:live_ncs_acl-destination;
    }
  }

  grouping live_ncs_access-flow-config {
    leaf description {
      type string;
      description
        "A more detailed description that an operator can use
         to describe the flow.";
    }
    leaf classifier-list-precedence {
      type uint32;
      description
        "A precedence value for the access flow. Lower values take
         precedence over higher values";
    }
    leaf filter-action {
      type enumeration {
        enum "deny" {
          description
            "Drop traffic for traffic that matches this specific access-flow-rule.
             This may be augmented with specific actions in the action list for this traffic flow";
        }
        enum "allow" {
          description
            "Do not drop traffic for traffic that matches this specific access-flow-rule.
             This may be augmented with specific actions in the action list for this traffic flow";
        }
      }
      description
        "Specifies the filter-action for this Access-Flow/ACL-Rule";
    }
    leaf stats-collection {
      type enumeration {
        enum "on" {
          description
            "Stats collection turned on";
        }
        enum "off" {
          description
            "Stats collection turned off";
        }
      }
      description
        "Determines whether stats collection will be turned on or not for an access-flow";
    }
  }

  grouping acl-destination {
    choice destination {
      case logical-port-list {
        leaf-list logical-port {
          type mef-logical-port:logical-port-ref;
          description
            "One or more logical-ports which act as destination for the acl-action (e.g. mirror/redirect)";
        }
        description
          "One or more logical-ports which act as destination for the acl-action (e.g. mirror/redirect)";
      }
      case flow-point-list {
        leaf-list flow-point {
          type mef-fp:fp-ref;
          description
            "One or more flow-points which act as destination for the acl-action (e.g. mirror/redirect)";
        }
        description
          "One or more flow-points which act as destination for the acl-action (e.g. mirror/redirect)";
      }
      case custom-list {
        leaf-list custom {
          type acl:custom-destination-ref;
          description
            "One or more custom destinations which act as destination for the acl-action (e.g. mirror/redirect)";
        }
        description
          "One or more custom destinations which act as destination for the acl-action (e.g. mirror/redirect)";
      }
    }
  }

  grouping custom-acl-action {
    list acl-action {
      key "name";
      description
        "A list of ACL-actions, where each ACL-action specifies the action of the classified flow.";
      leaf name {
        type string;
        description
          "A unique string that is either system assigned or assigned
           by the user but does not change over its life.";
      }
      leaf description {
        type string;
        description
          "A more detailed description that an operator can use
           to describe the action.";
      }
      leaf action {
        type enumeration {
          enum "redirect" {
            description
              "Redirect the classified flow to one or more ports/flow-points etc.";
          }
          enum "ingress-mirror" {
            description
              "Ingress-Mirror the classified flow to one or more ports/flow-points etc.";
          }
        }
        description
          "Specifies an action for this acl action";
      }
      uses acl:acl-destination;
    }
  }

  grouping access-flow-config {
    leaf description {
      type string;
      description
        "A more detailed description that an operator can use
         to describe the flow.";
    }
    leaf classifier-list-precedence {
      type uint32;
      description
        "A precedence value for the access flow. Lower values take
         precedence over higher values";
    }
    leaf filter-action {
      type enumeration {
        enum "deny" {
          description
            "Drop traffic for traffic that matches this specific access-flow-rule.
             This may be augmented with specific actions in the action list for this traffic flow";
        }
        enum "allow" {
          description
            "Do not drop traffic for traffic that matches this specific access-flow-rule.
             This may be augmented with specific actions in the action list for this traffic flow";
        }
      }
      description
        "Specifies the filter-action for this Access-Flow/ACL-Rule";
    }
    leaf stats-collection {
      type enumeration {
        enum "on" {
          description
            "Stats collection turned on";
        }
        enum "off" {
          description
            "Stats collection turned off";
        }
      }
      description
        "Determines whether stats collection will be turned on or not for an access-flow";
    }
  }

  augment "/ncs:devices/ncs:device/ncs:config" {
    container acl-custom-destinations {
      tailf:ncs-device-type "netconf";
      tailf:display-when "not(../../ncs:module) or ../../ncs:module[ncs:name='ciena-mef-access-flow']";
      description
        "List of custom destinations. A given ACL rule may be redirecting/mirroring to one or more destinations.";
      list acl-custom-destination {
        key "name";
        description
          "A list of ACL-customized-destinations that the classified flows may be directed to.";
        leaf name {
          type string;
          description
            "A unique string that is either system assigned or assigned
             by the user but does not change over its life.";
        }
        leaf description {
          type string;
          description
            "A more detailed description that an operator can use
             to describe the custom destination.";
        }
        leaf destination {
          type enumeration {
            enum "voltha-agent" {
              description
                "Redirect the classified flow to a voltha-agent application.";
            }
          }
          description
            "Specifies an application name for this acl destination";
        }
      }
    }
    container acl-actions {
      tailf:ncs-device-type "netconf";
      tailf:display-when "not(../../ncs:module) or ../../ncs:module[ncs:name='ciena-mef-access-flow']";
      uses acl:custom-acl-action;
      description
        "List of ACL actions.";
    }
    container access-flows {
      tailf:ncs-device-type "netconf";
      tailf:display-when "not(../../ncs:module) or ../../ncs:module[ncs:name='ciena-mef-access-flow']";
      description
        "List of access-flow configuration entries. Each entry defines an ACL rule specific to an interface.";
      list access-flow {
        key "name";
        description
          "List of access-flow configuration entries. Each entry defines an ACL rule specific to an interface.";
        leaf name {
          type string;
          description
            "A unique string that is either system assigned or assigned
             by the user but does not change over its life.";
        }
        uses access-flow-config;
        leaf-list classifier-list {
          type classifier:classifier-ref;
          description
            "A reference to a list of classifier entries.";
        }
        choice parent-interface {
          case none {
            leaf none {
              type empty;
              description
                "When the Access-Flow is an ACL rule in an Access-Profile, use none.
                 In this case, the access-profile is referenced by a parent-interface instead.";
            }
            description
              "When the Access-Flow is an ACL rule in an Access-Profile, use none.
               In this case, the access-profile is referenced by a parent-interface instead.";
          }
          case logical-port {
            leaf-list parent-port {
              type mef-logical-port:logical-port-ref;
              description
                "This is used when the Access-Flow is an ACL rule that is not part of an Access-Profile.
                 In this case, the parent-interface defines the port that the Access-Flow applies to";
            }
            description
              "This is used when the Access-Flow is an ACL rule that is not part of an Access-Profile.
               In this case, the parent-interface defines the port that the Access-Flow applies to";
          }
          case flow-point {
            leaf-list parent-fp {
              type mef-fp:fp-ref;
              description
                "This is used when the Access-Flow is an ACL rule that is not part of an Access-Profile.
                 In this case, the parent-interface defines the flow-point that the Access-Flow applies to";
            }
            description
              "This is used when the Access-Flow is an ACL rule that is not part of an Access-Profile.
               In this case, the parent-interface defines the flow-point that the Access-Flow applies to";
          }
        }
        leaf-list augment-action {
          type acl:acl-action-ref;
          description
            "A list of Actions that may augment the filter-action of the Access-Flow/ACL-Rule.";
        }
      }
    }
    container access-profiles {
      tailf:ncs-device-type "netconf";
      tailf:display-when "not(../../ncs:module) or ../../ncs:module[ncs:name='ciena-mef-access-flow']";
      description
        "List of access-profile configuration templates.
         Each profile defines a list of ACL rules that can be applied to multiple interfaces.";
      list access-profile {
        key "name";
        leaf name {
          type string;
          description
            "A unique string that is either system assigned or assigned
             by the user but does not change over its life.";
        }
        leaf description {
          type string;
          description
            "A more detailed description that an operator can use
             to describe the profile.";
        }
        leaf base-access-profile {
          type acl:access-profile-ref;
          description
            "An Access Profile should be able to refer to another Access Profile and inherit its properties";
        }
        leaf type {
          type enumeration {
            enum "flow-point" {
              description
                "This access-profile will attach to a flow-point";
            }
            enum "IP-interface" {
              description
                "This access-profile will attach to an IP interface";
            }
          }
          description
            "Type of interface this access-profile will attach to";
        }
        leaf default-filter-action {
          type enumeration {
            enum "deny" {
              description
                "Drop traffic for all other traffic that does not match a specific access-flow-rule but
                 classifies to this Access-Profile";
            }
            enum "allow" {
              description
                "Do not drop traffic for all other traffic that does not match a specific access-flow-rule but
                 classifies to this Access-Profile";
            }
          }
          description
            "Specifies the default filter-action for this Access-Profile";
        }
        leaf stats-collection {
          type enumeration {
            enum "on";
            enum "off";
          }
          description
            "Determines whether stats collection will be turned on or not for an instance of access-profile";
        }
        list access-flow {
          key "name";
          leaf name {
            type string;
            description
              "Access-Flow name";
          }
          uses access-flow-config;
          uses classifier:classifier-group;
          description
            "A list of ACL rules, Access-Flows that are part of an access-profile.
             Each ACL-rule/Access-Flow specifies classifiers, precedence and actions independently";
        }
        description
          "A list of all access-profile configuration entries.";
      }
    }
    // NCS drop config false container 'access-flows-state'
  }
  augment "/ncs:devices/ncs:device/ncs:live-status" {
    container acl-custom-destinations {
      tailf:ncs-device-type "netconf";
      tailf:display-when "not(../../ncs:module) or ../../ncs:module[ncs:name='ciena-mef-access-flow'] or (../../ncs:live-status-protocol[not(ncs:capability)]) or (../../ncs:live-status-protocol/ncs:capability/ncs:module[.='ciena-mef-access-flow'])";
      description
        "List of custom destinations. A given ACL rule may be redirecting/mirroring to one or more destinations.";
      list acl-custom-destination {
        key "name";
        description
          "A list of ACL-customized-destinations that the classified flows may be directed to.";
        leaf name {
          type string;
          description
            "A unique string that is either system assigned or assigned
             by the user but does not change over its life.";
        }
        leaf description {
          type string;
          description
            "A more detailed description that an operator can use
             to describe the custom destination.";
        }
        leaf destination {
          type enumeration {
            enum "voltha-agent" {
              description
                "Redirect the classified flow to a voltha-agent application.";
            }
          }
          description
            "Specifies an application name for this acl destination";
        }
      }
    }
    container acl-actions {
      tailf:ncs-device-type "netconf";
      tailf:display-when "not(../../ncs:module) or ../../ncs:module[ncs:name='ciena-mef-access-flow'] or (../../ncs:live-status-protocol[not(ncs:capability)]) or (../../ncs:live-status-protocol/ncs:capability/ncs:module[.='ciena-mef-access-flow'])";
      uses acl:live_ncs_custom-acl-action;
      description
        "List of ACL actions.";
    }
    container access-flows {
      tailf:ncs-device-type "netconf";
      tailf:display-when "not(../../ncs:module) or ../../ncs:module[ncs:name='ciena-mef-access-flow'] or (../../ncs:live-status-protocol[not(ncs:capability)]) or (../../ncs:live-status-protocol/ncs:capability/ncs:module[.='ciena-mef-access-flow'])";
      description
        "List of access-flow configuration entries. Each entry defines an ACL rule specific to an interface.";
      list access-flow {
        key "name";
        description
          "List of access-flow configuration entries. Each entry defines an ACL rule specific to an interface.";
        leaf name {
          type string;
          description
            "A unique string that is either system assigned or assigned
             by the user but does not change over its life.";
        }
        uses live_ncs_access-flow-config;
        leaf-list classifier-list {
          type classifier:live_ncs_classifier-ref;
          description
            "A reference to a list of classifier entries.";
        }
        choice parent-interface {
          case none {
            leaf none {
              type empty;
              description
                "When the Access-Flow is an ACL rule in an Access-Profile, use none.
                 In this case, the access-profile is referenced by a parent-interface instead.";
            }
            description
              "When the Access-Flow is an ACL rule in an Access-Profile, use none.
               In this case, the access-profile is referenced by a parent-interface instead.";
          }
          case logical-port {
            leaf-list parent-port {
              type mef-logical-port:live_ncs_logical-port-ref;
              description
                "This is used when the Access-Flow is an ACL rule that is not part of an Access-Profile.
                 In this case, the parent-interface defines the port that the Access-Flow applies to";
            }
            description
              "This is used when the Access-Flow is an ACL rule that is not part of an Access-Profile.
               In this case, the parent-interface defines the port that the Access-Flow applies to";
          }
          case flow-point {
            leaf-list parent-fp {
              type mef-fp:live_ncs_fp-ref;
              description
                "This is used when the Access-Flow is an ACL rule that is not part of an Access-Profile.
                 In this case, the parent-interface defines the flow-point that the Access-Flow applies to";
            }
            description
              "This is used when the Access-Flow is an ACL rule that is not part of an Access-Profile.
               In this case, the parent-interface defines the flow-point that the Access-Flow applies to";
          }
        }
        leaf-list augment-action {
          type acl:live_ncs_acl-action-ref;
          description
            "A list of Actions that may augment the filter-action of the Access-Flow/ACL-Rule.";
        }
      }
    }
    container access-profiles {
      tailf:ncs-device-type "netconf";
      tailf:display-when "not(../../ncs:module) or ../../ncs:module[ncs:name='ciena-mef-access-flow'] or (../../ncs:live-status-protocol[not(ncs:capability)]) or (../../ncs:live-status-protocol/ncs:capability/ncs:module[.='ciena-mef-access-flow'])";
      description
        "List of access-profile configuration templates.
         Each profile defines a list of ACL rules that can be applied to multiple interfaces.";
      list access-profile {
        key "name";
        leaf name {
          type string;
          description
            "A unique string that is either system assigned or assigned
             by the user but does not change over its life.";
        }
        leaf description {
          type string;
          description
            "A more detailed description that an operator can use
             to describe the profile.";
        }
        leaf base-access-profile {
          type acl:live_ncs_access-profile-ref;
          description
            "An Access Profile should be able to refer to another Access Profile and inherit its properties";
        }
        leaf type {
          type enumeration {
            enum "flow-point" {
              description
                "This access-profile will attach to a flow-point";
            }
            enum "IP-interface" {
              description
                "This access-profile will attach to an IP interface";
            }
          }
          description
            "Type of interface this access-profile will attach to";
        }
        leaf default-filter-action {
          type enumeration {
            enum "deny" {
              description
                "Drop traffic for all other traffic that does not match a specific access-flow-rule but
                 classifies to this Access-Profile";
            }
            enum "allow" {
              description
                "Do not drop traffic for all other traffic that does not match a specific access-flow-rule but
                 classifies to this Access-Profile";
            }
          }
          description
            "Specifies the default filter-action for this Access-Profile";
        }
        leaf stats-collection {
          type enumeration {
            enum "on";
            enum "off";
          }
          description
            "Determines whether stats collection will be turned on or not for an instance of access-profile";
        }
        list access-flow {
          key "name";
          leaf name {
            type string;
            description
              "Access-Flow name";
          }
          uses live_ncs_access-flow-config;
          uses classifier:live_ncs_classifier-group;
          description
            "A list of ACL rules, Access-Flows that are part of an access-profile.
             Each ACL-rule/Access-Flow specifies classifiers, precedence and actions independently";
        }
        description
          "A list of all access-profile configuration entries.";
      }
    }
    container access-flows-state {
      tailf:ncs-device-type "netconf";
      tailf:display-when "not(../../ncs:module) or ../../ncs:module[ncs:name='ciena-mef-access-flow'] or (../../ncs:live-status-protocol[not(ncs:capability)]) or (../../ncs:live-status-protocol/ncs:capability/ncs:module[.='ciena-mef-access-flow'])";
      description
        "Access Flow operational data for all Access Flows.";
      list access-flow {
        key "name";
        description
          "The operational data for this Access-Flow.";
        leaf name {
          type string;
          description
            "A string that identifies the Access-Flow.";
        }
        leaf hitBytes {
          type uint64;
          description
            "Byte count of frames that hit the Access-Flow";
        }
        leaf hitFrames {
          type uint64;
          description
            "Frame count of frames that hit the Access-Flow";
        }
      }
    }
  }
  augment "/ncs:devices/ncs:template/ncs:ned-id/ncs:config" {
    container acl-custom-destinations {
      description
        "List of custom destinations. A given ACL rule may be redirecting/mirroring to one or more destinations.";
      list acl-custom-destination {
        // NCS patched for predictable order
        ordered-by user;
        key "name";
        description
          "A list of ACL-customized-destinations that the classified flows may be directed to.";
        leaf name {
          type string;
          description
            "A unique string that is either system assigned or assigned
             by the user but does not change over its life.";
        }
        leaf description {
          type string;
          description
            "A more detailed description that an operator can use
             to describe the custom destination.";
        }
        leaf destination {
          type string;
          description
            "Specifies an application name for this acl destination";
        }
      }
    }
    container acl-actions {
      uses acl:ncs_template_custom-acl-action;
      description
        "List of ACL actions.";
    }
    container access-flows {
      description
        "List of access-flow configuration entries. Each entry defines an ACL rule specific to an interface.";
      list access-flow {
        // NCS patched for predictable order
        ordered-by user;
        key "name";
        description
          "List of access-flow configuration entries. Each entry defines an ACL rule specific to an interface.";
        leaf name {
          type string;
          description
            "A unique string that is either system assigned or assigned
             by the user but does not change over its life.";
        }
        uses ncs_template_access-flow-config;
        leaf-list classifier-list {
          // NCS patched for predictable order
          ordered-by user;
          type classifier:ncs_template_classifier-ref;
          description
            "A reference to a list of classifier entries.";
        }
        choice parent-interface {
          case none {
            leaf none {
              type empty;
              description
                "When the Access-Flow is an ACL rule in an Access-Profile, use none.
                 In this case, the access-profile is referenced by a parent-interface instead.";
            }
            description
              "When the Access-Flow is an ACL rule in an Access-Profile, use none.
               In this case, the access-profile is referenced by a parent-interface instead.";
          }
          case logical-port {
            leaf-list parent-port {
              // NCS patched for predictable order
              ordered-by user;
              type mef-logical-port:ncs_template_logical-port-ref;
              description
                "This is used when the Access-Flow is an ACL rule that is not part of an Access-Profile.
                 In this case, the parent-interface defines the port that the Access-Flow applies to";
            }
            description
              "This is used when the Access-Flow is an ACL rule that is not part of an Access-Profile.
               In this case, the parent-interface defines the port that the Access-Flow applies to";
          }
          case flow-point {
            leaf-list parent-fp {
              // NCS patched for predictable order
              ordered-by user;
              type mef-fp:ncs_template_fp-ref;
              description
                "This is used when the Access-Flow is an ACL rule that is not part of an Access-Profile.
                 In this case, the parent-interface defines the flow-point that the Access-Flow applies to";
            }
            description
              "This is used when the Access-Flow is an ACL rule that is not part of an Access-Profile.
               In this case, the parent-interface defines the flow-point that the Access-Flow applies to";
          }
        }
        leaf-list augment-action {
          // NCS patched for predictable order
          ordered-by user;
          type acl:ncs_template_acl-action-ref;
          description
            "A list of Actions that may augment the filter-action of the Access-Flow/ACL-Rule.";
        }
      }
    }
    container access-profiles {
      description
        "List of access-profile configuration templates.
         Each profile defines a list of ACL rules that can be applied to multiple interfaces.";
      list access-profile {
        // NCS patched for predictable order
        ordered-by user;
        key "name";
        leaf name {
          type string;
          description
            "A unique string that is either system assigned or assigned
             by the user but does not change over its life.";
        }
        leaf description {
          type string;
          description
            "A more detailed description that an operator can use
             to describe the profile.";
        }
        leaf base-access-profile {
          type acl:ncs_template_access-profile-ref;
          description
            "An Access Profile should be able to refer to another Access Profile and inherit its properties";
        }
        leaf type {
          type string;
          description
            "Type of interface this access-profile will attach to";
        }
        leaf default-filter-action {
          type string;
          description
            "Specifies the default filter-action for this Access-Profile";
        }
        leaf stats-collection {
          type string;
          description
            "Determines whether stats collection will be turned on or not for an instance of access-profile";
        }
        list access-flow {
          // NCS patched for predictable order
          ordered-by user;
          key "name";
          leaf name {
            type string;
            description
              "Access-Flow name";
          }
          uses ncs_template_access-flow-config;
          uses classifier:ncs_template_classifier-group;
          description
            "A list of ACL rules, Access-Flows that are part of an access-profile.
             Each ACL-rule/Access-Flow specifies classifiers, precedence and actions independently";
        }
        description
          "A list of all access-profile configuration entries.";
      }
    }
    // NCS drop config false container 'access-flows-state'
  }
}
