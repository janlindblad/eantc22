module mef-soam-pm-deviation {
  // Generated by yanger -t ncs
  tailf:mount-id "ciena107-nc-1.0:ciena107-nc-1.0";
  tailf:ncs-device-type "netconf";

  namespace "http://www.ciena.com/ns/yang/mef-soam-pm-dev";
  prefix mef-soam-pm-dev;

  import ietf-yang-types {
    prefix yang;
  }
  import mef-cfm {
    prefix cfm;
  }
  import mef-soam-pm {
    prefix mef-soam-pm;
  }
  import tailf-common {
    prefix tailf;
  }
  import tailf-ncs {
    prefix ncs;
  }

  revision 2020-12-04 {
    description
      "Removed the frame-delay-two-way, inter-frame-delay-variation-two-way,
       inter-frame-delay-variation-forward and inter-frame-delay-variation-backward
       leaf deviations from delay-measurement to support the measured stats";
  }
  revision 2020-06-02 {
    description
      "Removed the older ietf-inet-types yang's import revision number.
       Marked measurement-id leaf from threshold-crossing-alarm as not-supported";
  }
  revision 2018-04-23 {
    description
      "Added deviations to mef-soam-pm.yang model.";
  }
  revision 2016-03-09 {
    description
      "Initial revision";
  }

  deviation "/ncs:devices/ncs:template/ncs:ned-id/ncs:config/cfm:maintenance-domain/cfm:maintenance-association/cfm:maintenance-association-end-point/mef-soam-pm:loss-single-ended-responder" {
    // NCS drop config false deviate replace
  }
  deviation "/ncs:devices/ncs:device/ncs:live-status/cfm:maintenance-domain/cfm:maintenance-association/cfm:maintenance-association-end-point/mef-soam-pm:loss-single-ended-responder" {
    deviate replace;
  }
  deviation "/ncs:devices/ncs:device/ncs:config/cfm:maintenance-domain/cfm:maintenance-association/cfm:maintenance-association-end-point/mef-soam-pm:loss-single-ended-responder" {
    // NCS drop config false deviate replace
  }
  deviation "/ncs:devices/ncs:template/ncs:ned-id/ncs:config/cfm:maintenance-domain/cfm:maintenance-association/cfm:maintenance-association-end-point/mef-soam-pm:synthetic-loss-single-ended-responder" {
    // NCS drop config false deviate replace
  }
  deviation "/ncs:devices/ncs:device/ncs:live-status/cfm:maintenance-domain/cfm:maintenance-association/cfm:maintenance-association-end-point/mef-soam-pm:synthetic-loss-single-ended-responder" {
    deviate replace;
  }
  deviation "/ncs:devices/ncs:device/ncs:config/cfm:maintenance-domain/cfm:maintenance-association/cfm:maintenance-association-end-point/mef-soam-pm:synthetic-loss-single-ended-responder" {
    // NCS drop config false deviate replace
  }
  deviation "/ncs:devices/ncs:template/ncs:ned-id/ncs:config/cfm:maintenance-domain/cfm:maintenance-association/cfm:maintenance-association-end-point/mef-soam-pm:delay-single-ended-responder" {
    // NCS drop config false deviate replace
  }
  deviation "/ncs:devices/ncs:device/ncs:live-status/cfm:maintenance-domain/cfm:maintenance-association/cfm:maintenance-association-end-point/mef-soam-pm:delay-single-ended-responder" {
    deviate replace;
  }
  deviation "/ncs:devices/ncs:device/ncs:config/cfm:maintenance-domain/cfm:maintenance-association/cfm:maintenance-association-end-point/mef-soam-pm:delay-single-ended-responder" {
    // NCS drop config false deviate replace
  }
  deviation "/ncs:devices/ncs:device/ncs:live-status/cfm:maintenance-domain/cfm:maintenance-association/cfm:maintenance-association-end-point/mef-soam-pm:loss-measurements/mef-soam-pm:loss-measurement/mef-soam-pm:measurement-type" {
    deviate replace {
      type enumeration {
        enum "slm" {
          description
            "SLM SOAM PDU generated and received SLR responses tracked.";
        }
        enum "lmm-proprietary" {
          description
            "LMM SOAM PDU generated and received LMR responses tracked.";
        }
      }
    }
  }
  deviation "/ncs:devices/ncs:device/ncs:live-status/cfm:maintenance-domain/cfm:maintenance-association/cfm:maintenance-association-end-point/mef-soam-pm:loss-measurements/mef-soam-pm:loss-measurement/mef-soam-pm:enabled-counters" {
    deviate replace {
      type bits {
        bit forward-transmitted-frames;
        bit forward-received-frames;
        bit forward-min-flr;
        bit forward-max-flr;
        bit forward-average-flr;
        bit backward-transmitted-frames;
        bit backward-received-frames;
        bit backward-min-flr;
        bit backward-max-flr;
        bit backward-average-flr;
        bit soam-pdus-sent;
        bit soam-pdus-received;
        bit measured-stats-forward-measured-flr;
        bit measured-stats-backward-measured-flr;
      }
    }
  }
  deviation "/ncs:devices/ncs:device/ncs:live-status/cfm:maintenance-domain/cfm:maintenance-association/cfm:maintenance-association-end-point/mef-soam-pm:loss-measurements/mef-soam-pm:loss-measurement/mef-soam-pm:data-pattern" {
    deviate not-supported;
  }
  deviation "/ncs:devices/ncs:device/ncs:live-status/cfm:maintenance-domain/cfm:maintenance-association/cfm:maintenance-association-end-point/mef-soam-pm:loss-measurements/mef-soam-pm:loss-measurement/mef-soam-pm:test-tlv-included" {
    deviate not-supported;
  }
  deviation "/ncs:devices/ncs:device/ncs:live-status/cfm:maintenance-domain/cfm:maintenance-association/cfm:maintenance-association-end-point/mef-soam-pm:loss-measurements/mef-soam-pm:loss-measurement/mef-soam-pm:test-tlv-pattern" {
    deviate not-supported;
  }
  deviation "/ncs:devices/ncs:device/ncs:live-status/cfm:maintenance-domain/cfm:maintenance-association/cfm:maintenance-association-end-point/mef-soam-pm:loss-measurements/mef-soam-pm:loss-measurement/mef-soam-pm:thresholds" {
    deviate not-supported;
  }
  deviation "/ncs:devices/ncs:device/ncs:live-status/cfm:maintenance-domain/cfm:maintenance-association/cfm:maintenance-association-end-point/mef-soam-pm:delay-measurements/mef-soam-pm:delay-measurement/mef-soam-pm:measurement-type" {
    deviate not-supported;
    description
      "Only type dmm is supported and hence no config is possible";
  }
  deviation "/ncs:devices/ncs:device/ncs:live-status/cfm:maintenance-domain/cfm:maintenance-association/cfm:maintenance-association-end-point/mef-soam-pm:delay-measurements/mef-soam-pm:delay-measurement/mef-soam-pm:measurement-enable" {
    deviate replace {
      type bits {
        bit soam-pdus-sent;
        bit soam-pdus-received;
        bit frame-delay-two-way-bins;
        bit frame-delay-two-way-min;
        bit frame-delay-two-way-max;
        bit frame-delay-two-way-average;
        bit inter-frame-delay-variation-forward-bins;
        bit inter-frame-delay-variation-forward-min;
        bit inter-frame-delay-variation-forward-max;
        bit inter-frame-delay-variation-forward-average;
        bit inter-frame-delay-variation-backward-bins;
        bit inter-frame-delay-variation-backward-min;
        bit inter-frame-delay-variation-backward-max;
        bit inter-frame-delay-variation-backward-average;
        bit inter-frame-delay-variation-two-way-bins;
        bit inter-frame-delay-variation-two-way-min;
        bit inter-frame-delay-variation-two-way-max;
        bit inter-frame-delay-variation-two-way-average;
        bit frame-delay-range-two-way-bins;
        bit frame-delay-range-two-way-max;
        bit frame-delay-range-two-way-average;
      }
    }
  }
  deviation "/ncs:devices/ncs:device/ncs:live-status/cfm:maintenance-domain/cfm:maintenance-association/cfm:maintenance-association-end-point/mef-soam-pm:delay-measurements/mef-soam-pm:delay-measurement/mef-soam-pm:data-pattern" {
    deviate not-supported;
  }
  deviation "/ncs:devices/ncs:device/ncs:live-status/cfm:maintenance-domain/cfm:maintenance-association/cfm:maintenance-association-end-point/mef-soam-pm:delay-measurements/mef-soam-pm:delay-measurement/mef-soam-pm:test-tlv-included" {
    deviate not-supported;
  }
  deviation "/ncs:devices/ncs:device/ncs:live-status/cfm:maintenance-domain/cfm:maintenance-association/cfm:maintenance-association-end-point/mef-soam-pm:delay-measurements/mef-soam-pm:delay-measurement/mef-soam-pm:test-tlv-pattern" {
    deviate not-supported;
  }
  deviation "/ncs:devices/ncs:device/ncs:live-status/cfm:maintenance-domain/cfm:maintenance-association/cfm:maintenance-association-end-point/mef-soam-pm:delay-measurements/mef-soam-pm:delay-measurement/mef-soam-pm:ifdv-selection-offset" {
    deviate not-supported;
  }
  deviation "/ncs:devices/ncs:device/ncs:live-status/cfm:maintenance-domain/cfm:maintenance-association/cfm:maintenance-association-end-point/mef-soam-pm:delay-measurements/mef-soam-pm:delay-measurement/mef-soam-pm:thresholds" {
    deviate not-supported;
  }
  deviation "/ncs:devices/ncs:device/ncs:live-status/cfm:maintenance-domain/cfm:maintenance-association/cfm:maintenance-association-end-point/mef-soam-pm:delay-measurements/mef-soam-pm:delay-measurement/mef-soam-pm:source-mac-address" {
    deviate replace;
  }
  deviation "/ncs:devices/ncs:device/ncs:live-status/cfm:maintenance-domain/cfm:maintenance-association/cfm:maintenance-association-end-point/mef-soam-pm:delay-measurements/mef-soam-pm:delay-measurement/mef-soam-pm:frame-delay-forward" {
    deviate not-supported;
  }
  deviation "/ncs:devices/ncs:device/ncs:live-status/cfm:maintenance-domain/cfm:maintenance-association/cfm:maintenance-association-end-point/mef-soam-pm:delay-measurements/mef-soam-pm:delay-measurement/mef-soam-pm:frame-delay-backward" {
    deviate not-supported;
  }
  deviation "/ncs:devices/ncs:device/ncs:live-status/cfm:maintenance-domain/cfm:maintenance-association/cfm:maintenance-association-end-point/mef-soam-pm:delay-measurements/mef-soam-pm:delay-measurement/mef-soam-pm:current-stats/mef-soam-pm:frame-delay-forward-min" {
    deviate not-supported;
  }
  deviation "/ncs:devices/ncs:device/ncs:live-status/cfm:maintenance-domain/cfm:maintenance-association/cfm:maintenance-association-end-point/mef-soam-pm:delay-measurements/mef-soam-pm:delay-measurement/mef-soam-pm:current-stats/mef-soam-pm:frame-delay-forward-max" {
    deviate not-supported;
  }
  deviation "/ncs:devices/ncs:device/ncs:live-status/cfm:maintenance-domain/cfm:maintenance-association/cfm:maintenance-association-end-point/mef-soam-pm:delay-measurements/mef-soam-pm:delay-measurement/mef-soam-pm:current-stats/mef-soam-pm:frame-delay-forward-average" {
    deviate not-supported;
  }
  deviation "/ncs:devices/ncs:device/ncs:live-status/cfm:maintenance-domain/cfm:maintenance-association/cfm:maintenance-association-end-point/mef-soam-pm:delay-measurements/mef-soam-pm:delay-measurement/mef-soam-pm:current-stats/mef-soam-pm:frame-delay-backward-min" {
    deviate not-supported;
  }
  deviation "/ncs:devices/ncs:device/ncs:live-status/cfm:maintenance-domain/cfm:maintenance-association/cfm:maintenance-association-end-point/mef-soam-pm:delay-measurements/mef-soam-pm:delay-measurement/mef-soam-pm:current-stats/mef-soam-pm:frame-delay-backward-max" {
    deviate not-supported;
  }
  deviation "/ncs:devices/ncs:device/ncs:live-status/cfm:maintenance-domain/cfm:maintenance-association/cfm:maintenance-association-end-point/mef-soam-pm:delay-measurements/mef-soam-pm:delay-measurement/mef-soam-pm:current-stats/mef-soam-pm:frame-delay-backward-average" {
    deviate not-supported;
  }
  deviation "/ncs:devices/ncs:device/ncs:live-status/cfm:maintenance-domain/cfm:maintenance-association/cfm:maintenance-association-end-point/mef-soam-pm:delay-measurements/mef-soam-pm:delay-measurement/mef-soam-pm:current-stats/mef-soam-pm:frame-delay-range-forward-max" {
    deviate not-supported;
  }
  deviation "/ncs:devices/ncs:device/ncs:live-status/cfm:maintenance-domain/cfm:maintenance-association/cfm:maintenance-association-end-point/mef-soam-pm:delay-measurements/mef-soam-pm:delay-measurement/mef-soam-pm:current-stats/mef-soam-pm:frame-delay-range-forward-average" {
    deviate not-supported;
  }
  deviation "/ncs:devices/ncs:device/ncs:live-status/cfm:maintenance-domain/cfm:maintenance-association/cfm:maintenance-association-end-point/mef-soam-pm:delay-measurements/mef-soam-pm:delay-measurement/mef-soam-pm:current-stats/mef-soam-pm:frame-delay-range-backward-max" {
    deviate not-supported;
  }
  deviation "/ncs:devices/ncs:device/ncs:live-status/cfm:maintenance-domain/cfm:maintenance-association/cfm:maintenance-association-end-point/mef-soam-pm:delay-measurements/mef-soam-pm:delay-measurement/mef-soam-pm:current-stats/mef-soam-pm:frame-delay-range-backward-average" {
    deviate not-supported;
  }
  deviation "/ncs:devices/ncs:device/ncs:live-status/cfm:maintenance-domain/cfm:maintenance-association/cfm:maintenance-association-end-point/mef-soam-pm:delay-measurements/mef-soam-pm:delay-measurement/mef-soam-pm:history-stats/mef-soam-pm:frame-delay-forward-min" {
    deviate not-supported;
  }
  deviation "/ncs:devices/ncs:device/ncs:live-status/cfm:maintenance-domain/cfm:maintenance-association/cfm:maintenance-association-end-point/mef-soam-pm:delay-measurements/mef-soam-pm:delay-measurement/mef-soam-pm:history-stats/mef-soam-pm:frame-delay-forward-max" {
    deviate not-supported;
  }
  deviation "/ncs:devices/ncs:device/ncs:live-status/cfm:maintenance-domain/cfm:maintenance-association/cfm:maintenance-association-end-point/mef-soam-pm:delay-measurements/mef-soam-pm:delay-measurement/mef-soam-pm:history-stats/mef-soam-pm:frame-delay-forward-average" {
    deviate not-supported;
  }
  deviation "/ncs:devices/ncs:device/ncs:live-status/cfm:maintenance-domain/cfm:maintenance-association/cfm:maintenance-association-end-point/mef-soam-pm:delay-measurements/mef-soam-pm:delay-measurement/mef-soam-pm:history-stats/mef-soam-pm:frame-delay-backward-min" {
    deviate not-supported;
  }
  deviation "/ncs:devices/ncs:device/ncs:live-status/cfm:maintenance-domain/cfm:maintenance-association/cfm:maintenance-association-end-point/mef-soam-pm:delay-measurements/mef-soam-pm:delay-measurement/mef-soam-pm:history-stats/mef-soam-pm:frame-delay-backward-max" {
    deviate not-supported;
  }
  deviation "/ncs:devices/ncs:device/ncs:live-status/cfm:maintenance-domain/cfm:maintenance-association/cfm:maintenance-association-end-point/mef-soam-pm:delay-measurements/mef-soam-pm:delay-measurement/mef-soam-pm:history-stats/mef-soam-pm:frame-delay-backward-average" {
    deviate not-supported;
  }
  deviation "/ncs:devices/ncs:device/ncs:live-status/cfm:maintenance-domain/cfm:maintenance-association/cfm:maintenance-association-end-point/mef-soam-pm:delay-measurements/mef-soam-pm:delay-measurement/mef-soam-pm:history-stats/mef-soam-pm:frame-delay-range-forward-max" {
    deviate not-supported;
  }
  deviation "/ncs:devices/ncs:device/ncs:live-status/cfm:maintenance-domain/cfm:maintenance-association/cfm:maintenance-association-end-point/mef-soam-pm:delay-measurements/mef-soam-pm:delay-measurement/mef-soam-pm:history-stats/mef-soam-pm:frame-delay-range-forward-average" {
    deviate not-supported;
  }
  deviation "/ncs:devices/ncs:device/ncs:live-status/cfm:maintenance-domain/cfm:maintenance-association/cfm:maintenance-association-end-point/mef-soam-pm:delay-measurements/mef-soam-pm:delay-measurement/mef-soam-pm:history-stats/mef-soam-pm:frame-delay-range-backward-max" {
    deviate not-supported;
  }
  deviation "/ncs:devices/ncs:device/ncs:live-status/cfm:maintenance-domain/cfm:maintenance-association/cfm:maintenance-association-end-point/mef-soam-pm:delay-measurements/mef-soam-pm:delay-measurement/mef-soam-pm:history-stats/mef-soam-pm:frame-delay-range-backward-average" {
    deviate not-supported;
  }
  deviation "/ncs:devices/ncs:device/ncs:rpc/mef-soam-pm:rpc-create-loss-measurement/mef-soam-pm:create-loss-measurement" {
    deviate not-supported;
  }
  deviation "/ncs:devices/ncs:device/ncs:rpc/mef-soam-pm:rpc-create-delay-measurement/mef-soam-pm:create-delay-measurement" {
    deviate not-supported;
  }
  deviation "/ncs:devices/ncs:device/ncs:rpc/mef-soam-pm:rpc-abort-loss-measurement/mef-soam-pm:abort-loss-measurement" {
    deviate not-supported;
  }
  deviation "/ncs:devices/ncs:device/ncs:rpc/mef-soam-pm:rpc-abort-delay-measurement/mef-soam-pm:abort-delay-measurement" {
    deviate not-supported;
  }
  deviation "/ncs:devices/ncs:device/ncs:rpc/mef-soam-pm:rpc-clear-loss-history-stats/mef-soam-pm:clear-loss-history-stats" {
    deviate not-supported;
  }
  deviation "/ncs:devices/ncs:device/ncs:rpc/mef-soam-pm:rpc-clear-delay-history-stats/mef-soam-pm:clear-delay-history-stats" {
    deviate not-supported;
  }
  deviation "/ncs:devices/ncs:device/ncs:notifications/ncs:received-notifications/ncs:notification/ncs:data/mef-soam-pm:availability-change-alarm" {
    deviate not-supported;
  }
  deviation "/ncs:devices/ncs:device/ncs:netconf-notifications/ncs:received-notifications/ncs:notification/ncs:data/mef-soam-pm:availability-change-alarm" {
    deviate not-supported;
  }
  deviation "/ncs:devices/ncs:device/ncs:notifications/ncs:received-notifications/ncs:notification/ncs:data/mef-soam-pm:threshold-crossing-alarm/mef-soam-pm:suspect" {
    deviate not-supported;
  }
  deviation "/ncs:devices/ncs:device/ncs:netconf-notifications/ncs:received-notifications/ncs:notification/ncs:data/mef-soam-pm:threshold-crossing-alarm/mef-soam-pm:suspect" {
    deviate not-supported;
  }
  deviation "/ncs:devices/ncs:device/ncs:notifications/ncs:received-notifications/ncs:notification/ncs:data/mef-soam-pm:threshold-crossing-alarm/mef-soam-pm:measurement-id" {
    deviate not-supported;
  }
  deviation "/ncs:devices/ncs:device/ncs:netconf-notifications/ncs:received-notifications/ncs:notification/ncs:data/mef-soam-pm:threshold-crossing-alarm/mef-soam-pm:measurement-id" {
    deviate not-supported;
  }
}
