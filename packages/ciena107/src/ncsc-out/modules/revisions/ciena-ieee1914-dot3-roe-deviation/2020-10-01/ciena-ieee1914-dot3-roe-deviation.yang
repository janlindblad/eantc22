module ciena-ieee1914-dot3-roe-deviation {
  // Generated by yanger -t ncs
  tailf:mount-id "ciena107-nc-1.0:ciena107-nc-1.0";
  tailf:ncs-device-type "netconf";

  namespace "http://www.ciena.com/ns/yang/ciena-ieee1914-dot3-roe-dev";
  prefix ciena-ieee1914-dot3-roe-dev;

  import ietf-interfaces {
    prefix if;
  }
  import ieee1914-dot3-roe {
    prefix ieee1914-dot3-roe;
  }
  import tailf-common {
    prefix tailf;
  }
  import tailf-ncs {
    prefix ncs;
  }

  organization
    "Ciena Corporation";
  contact
    "Web URL: http://www.ciena.com/
     E-mail:  yang@ciena.com
     Postal:  7035 Ridge Road
              Hanover, Maryland 21076
              U.S.A.
     Phone:   +1 800-921-1144
     Fax:     +1 410-694-5750";
  description
    "This YANG module defines Ciena's deviations from the ieee1914-dot3-roe model.

      Copyright (c) 2020 Ciena Corporation.  All rights
      reserved.

      All information contained herein is, and remains
      the property of Ciena Corporation. Dissemination of this
      information or reproduction of this material is strictly
      forbidden unless prior written permission is obtained from
      Ciena Corporation.";

  revision 2020-10-01 {
    description
      "Initial version";
    reference
      "RFC 6020: YANG - A Data Modeling Language for
       the Network Configuration Protocol (NETCONF).
       No specific reference; standard not available.";
  }

  deviation "/ncs:devices/ncs:template/ncs:ned-id/ncs:config/if:interfaces/if:interface/if:description" {
    deviate not-supported;
  }
  deviation "/ncs:devices/ncs:device/ncs:live-status/if:interfaces/if:interface/if:description" {
    deviate not-supported;
  }
  deviation "/ncs:devices/ncs:device/ncs:config/if:interfaces/if:interface/if:description" {
    deviate not-supported;
  }
  deviation "/ncs:devices/ncs:template/ncs:ned-id/ncs:config/if:interfaces/if:interface/if:enabled" {
    deviate not-supported;
  }
  deviation "/ncs:devices/ncs:device/ncs:live-status/if:interfaces/if:interface/if:enabled" {
    deviate not-supported;
  }
  deviation "/ncs:devices/ncs:device/ncs:config/if:interfaces/if:interface/if:enabled" {
    deviate not-supported;
  }
  deviation "/ncs:devices/ncs:template/ncs:ned-id/ncs:config/if:interfaces/if:interface/if:link-up-down-trap-enable" {
    deviate not-supported;
  }
  deviation "/ncs:devices/ncs:device/ncs:live-status/if:interfaces/if:interface/if:link-up-down-trap-enable" {
    deviate not-supported;
  }
  deviation "/ncs:devices/ncs:device/ncs:config/if:interfaces/if:interface/if:link-up-down-trap-enable" {
    deviate not-supported;
  }
  deviation "/ncs:devices/ncs:device/ncs:live-status/if:interfaces/if:interface/if:admin-status" {
    deviate not-supported;
  }
  deviation "/ncs:devices/ncs:device/ncs:live-status/if:interfaces/if:interface/if:oper-status" {
    deviate not-supported;
  }
  deviation "/ncs:devices/ncs:device/ncs:live-status/if:interfaces/if:interface/if:last-change" {
    deviate not-supported;
  }
  deviation "/ncs:devices/ncs:device/ncs:live-status/if:interfaces/if:interface/if:if-index" {
    deviate not-supported;
  }
  deviation "/ncs:devices/ncs:device/ncs:live-status/if:interfaces/if:interface/if:phys-address" {
    deviate not-supported;
  }
  deviation "/ncs:devices/ncs:device/ncs:live-status/if:interfaces/if:interface/if:higher-layer-if" {
    deviate not-supported;
  }
  deviation "/ncs:devices/ncs:device/ncs:live-status/if:interfaces/if:interface/if:lower-layer-if" {
    deviate not-supported;
  }
  deviation "/ncs:devices/ncs:device/ncs:live-status/if:interfaces/if:interface/if:speed" {
    deviate not-supported;
  }
  deviation "/ncs:devices/ncs:template/ncs:ned-id/ncs:config/if:interfaces/if:interface/ieee1914-dot3-roe:roe-interface/ieee1914-dot3-roe:cpri-port" {
    deviate not-supported;
  }
  deviation "/ncs:devices/ncs:device/ncs:live-status/if:interfaces/if:interface/ieee1914-dot3-roe:roe-interface/ieee1914-dot3-roe:cpri-port" {
    deviate not-supported;
  }
  deviation "/ncs:devices/ncs:device/ncs:config/if:interfaces/if:interface/ieee1914-dot3-roe:roe-interface/ieee1914-dot3-roe:cpri-port" {
    deviate not-supported;
  }
  deviation "/ncs:devices/ncs:template/ncs:ned-id/ncs:config/if:interfaces/if:interface/ieee1914-dot3-roe:roe-interface/ieee1914-dot3-roe:mapper-demapper/ieee1914-dot3-roe:src-id" {
    deviate not-supported;
  }
  deviation "/ncs:devices/ncs:device/ncs:live-status/if:interfaces/if:interface/ieee1914-dot3-roe:roe-interface/ieee1914-dot3-roe:mapper-demapper/ieee1914-dot3-roe:src-id" {
    deviate not-supported;
  }
  deviation "/ncs:devices/ncs:device/ncs:config/if:interfaces/if:interface/ieee1914-dot3-roe:roe-interface/ieee1914-dot3-roe:mapper-demapper/ieee1914-dot3-roe:src-id" {
    deviate not-supported;
  }
  deviation "/ncs:devices/ncs:template/ncs:ned-id/ncs:config/if:interfaces/if:interface/ieee1914-dot3-roe:roe-interface/ieee1914-dot3-roe:mapper-demapper/ieee1914-dot3-roe:dest-id" {
    deviate not-supported;
  }
  deviation "/ncs:devices/ncs:device/ncs:live-status/if:interfaces/if:interface/ieee1914-dot3-roe:roe-interface/ieee1914-dot3-roe:mapper-demapper/ieee1914-dot3-roe:dest-id" {
    deviate not-supported;
  }
  deviation "/ncs:devices/ncs:device/ncs:config/if:interfaces/if:interface/ieee1914-dot3-roe:roe-interface/ieee1914-dot3-roe:mapper-demapper/ieee1914-dot3-roe:dest-id" {
    deviate not-supported;
  }
  deviation "/ncs:devices/ncs:template/ncs:ned-id/ncs:config/if:interfaces/if:interface/ieee1914-dot3-roe:roe-interface/ieee1914-dot3-roe:ethernet-link" {
    deviate not-supported;
  }
  deviation "/ncs:devices/ncs:device/ncs:live-status/if:interfaces/if:interface/ieee1914-dot3-roe:roe-interface/ieee1914-dot3-roe:ethernet-link" {
    deviate not-supported;
  }
  deviation "/ncs:devices/ncs:device/ncs:config/if:interfaces/if:interface/ieee1914-dot3-roe:roe-interface/ieee1914-dot3-roe:ethernet-link" {
    deviate not-supported;
  }
}
