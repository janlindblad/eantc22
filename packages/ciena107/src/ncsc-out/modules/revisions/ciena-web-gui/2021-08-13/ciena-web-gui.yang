module ciena-web-gui {
  // Generated by yanger -t ncs
  tailf:mount-id "ciena107-nc-1.0:ciena107-nc-1.0";
  tailf:ncs-device-type "netconf";

  namespace "http://www.ciena.com/ns/yang/ciena-web-gui";
  prefix webguimgmt;

  import ietf-yang-types {
    prefix yang;
  }
  import ciena-types {
    prefix cn-types;
  }
  import ietf-inet-types {
    prefix inet;
  }
  import ciena-tls-service-profile {
    prefix ciena-tsp;
  }
  import tailf-common {
    prefix tailf;
  }
  import tailf-ncs {
    prefix ncs;
  }

  organization
    "Ciena Corporation";
  contact
    "Web URL: http://www.ciena.com/
     E-mail:  yang@ciena.com
     Postal:  7035 Ridge Road
     Hanover, Maryland 21076
     U.S.A.
     Phone:   +1 800-921-1144
     Fax:     +1 410-694-5750";
  description
    "This YANG module is used to show operational data of WebGUI
     and clear active session(s).

     Copyright (c) 2021  Ciena Corporation.  All rights
     reserved.

     All information contained herein is, and remains the
     property of Ciena Corporation. Dissemination of this
     information or reproduction of this material is strictly
     forbidden unless prior written permission is obtained
     from Ciena Corporation.";

  revision 2021-08-13 {
    description
      "Added basic support of TLS/PKIX to WebGUI HTTPs connections.";
  }
  revision 2021-06-20 {
    description
      "Initial revision.";
  }

  typedef ncs_template_server-certificate-type {
    description
      "Type of certificate to be used in HTTPs connections.";
    type string;
  }

  typedef ncs_rpc_notif_server-certificate-type {
    description
      "Type of certificate to be used in HTTPs connections.";
    type enumeration {
      enum "self-signed-cert" {
        description
          "Self signed certificate";
      }
      enum "profile-cert" {
        description
          "Valid certificate attached to TLS service profile";
      }
    }
  }

  typedef live_ncs_server-certificate-type {
    description
      "Type of certificate to be used in HTTPs connections.";
    type enumeration {
      enum "self-signed-cert" {
        description
          "Self signed certificate";
      }
      enum "profile-cert" {
        description
          "Valid certificate attached to TLS service profile";
      }
    }
  }

  typedef server-certificate-type {
    description
      "Type of certificate to be used in HTTPs connections.";
    type enumeration {
      enum "self-signed-cert" {
        description
          "Self signed certificate";
      }
      enum "profile-cert" {
        description
          "Valid certificate attached to TLS service profile";
      }
    }
  }

  augment "/ncs:devices/ncs:device/ncs:rpc" {
    container rpc-web-gui-clear-sessions {
      tailf:ncs-device-type "netconf";
      tailf:display-when "not(../../ncs:module) or ../../ncs:module[ncs:name='ciena-web-gui']";
      tailf:action web-gui-clear-sessions {
        tailf:actionpoint ncsproxy {
          tailf:internal;
        }
        description
          "RPC to clear either all the active WebGUI sessions or with
           specific ID. In case, no input is provided then
           all sessions will be cleared.";
        input {
          leaf id {
            type uint32;
            description
              "ID of the WebGUI Session which is to be cleared.";
          }
        }
        output {
          leaf response-status {
            type cn-types:ncs_rpc_notif_status;
            description
              "Status can be either success or failure";
          }
          leaf response {
            type string;
            description
              "The response can be either a success message or
               the reason for failure, based on the response status.";
          }
        }
      }
    }
  }
  augment "/ncs:devices/ncs:device-group/ncs:ned-id/ncs:rpc" {
    container rpc-web-gui-clear-sessions {
      tailf:ncs-device-type "netconf";
      tailf:display-when "/ncs:devices/ncs:device[ncs:name=current()/../../../ncs:member]/ncs:module[ncs:name='ciena-web-gui']";
      tailf:action web-gui-clear-sessions {
        tailf:actionpoint ncsproxy {
          tailf:internal;
        }
        description
          "RPC to clear either all the active WebGUI sessions or with
           specific ID. In case, no input is provided then
           all sessions will be cleared.";
        input {
          leaf id {
            type uint32;
            description
              "ID of the WebGUI Session which is to be cleared.";
          }
        }
        output {
          container "device" {
            leaf "name" {
              type string;
            }
            leaf "info" {
              type string;
            }
            container "result" {
              leaf response-status {
                type cn-types:ncs_rpc_notif_status;
                description
                  "Status can be either success or failure";
              }
              leaf response {
                type string;
                description
                  "The response can be either a success message or
                   the reason for failure, based on the response status.";
              }
            }
          }
        }
      }
    }
  }
  augment "/ncs:devices/ncs:device/ncs:config" {
    container web-gui {
      tailf:ncs-device-type "netconf";
      tailf:display-when "not(../../ncs:module) or ../../ncs:module[ncs:name='ciena-web-gui']";
      description
        "This container describes the WebGUI configuration.";
      leaf tls-service-profile {
        type leafref {
          path "/ncs:devices/ncs:device/ncs:config/ciena-tsp:tls-service-profiles/ciena-tsp:tls-service-profile-name" {
            tailf:xpath-root 3;
          }
        }
        description
          "The TLS service profile for accepting TLS connections.";
      }
    }
    // NCS drop config false container 'web-gui-state'
  }
  augment "/ncs:devices/ncs:device/ncs:live-status" {
    container web-gui {
      tailf:ncs-device-type "netconf";
      tailf:display-when "not(../../ncs:module) or ../../ncs:module[ncs:name='ciena-web-gui'] or (../../ncs:live-status-protocol[not(ncs:capability)]) or (../../ncs:live-status-protocol/ncs:capability/ncs:module[.='ciena-web-gui'])";
      description
        "This container describes the WebGUI configuration.";
      leaf tls-service-profile {
        type leafref {
          path "/ncs:devices/ncs:device/ncs:live-status/ciena-tsp:tls-service-profiles/ciena-tsp:tls-service-profile-name" {
            tailf:xpath-root 3;
          }
        }
        description
          "The TLS service profile for accepting TLS connections.";
      }
    }
    container web-gui-state {
      tailf:ncs-device-type "netconf";
      tailf:display-when "not(../../ncs:module) or ../../ncs:module[ncs:name='ciena-web-gui'] or (../../ncs:live-status-protocol[not(ncs:capability)]) or (../../ncs:live-status-protocol/ncs:capability/ncs:module[.='ciena-web-gui'])";
      description
        "Information on operational state and sessions.";
      leaf oper-state {
        description
          "Operational state of WebGUI.";
        type cn-types:live_ncs_state;
      }
      list session {
        key "id";
        description
          "Active sessions of WebGUI.";
        leaf id {
          description
            "Connection ID.";
          type uint32;
        }
        leaf client {
          description
            "Client IP address string either v4 or v6.";
          type inet:ip-address;
        }
        leaf user {
          description
            "User connected to this session.";
          type string;
        }
        leaf last-access {
          description
            "Last access time.";
          type yang:date-and-time;
        }
      }
      container tls-state {
        description
          "Detailed information related to attached TLS Service Profile.";
        leaf type-of-cert-in-use {
          description
            "Either attached TLS service profile's valid certificate
             or Self signed certificate that is currently in use for
             WebGUI HTTPs connections.";
          type live_ncs_server-certificate-type;
        }
      }
    }
  }
  augment "/ncs:devices/ncs:template/ncs:ned-id/ncs:config" {
    container web-gui {
      description
        "This container describes the WebGUI configuration.";
      leaf tls-service-profile {
        type string;
        description
          "The TLS service profile for accepting TLS connections.";
      }
    }
    // NCS drop config false container 'web-gui-state'
  }
}
