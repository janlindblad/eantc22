module ciena-openconfig-telemetry {
  // Generated by yanger -t ncs
  tailf:mount-id "ciena107-nc-1.0:ciena107-nc-1.0";
  tailf:ncs-device-type "netconf";

  namespace "http://www.ciena.com/ns/yang/ciena-openconfig-telemetry";
  prefix ciena-oc-tmet;

  import openconfig-telemetry {
    prefix oc-telemetry;
  }
  import ciena-tls-service-profile {
    prefix ciena-tsp;
  }
  import ietf-inet-types {
    prefix inet;
  }
  import tailf-common {
    prefix tailf;
  }
  import tailf-ncs {
    prefix ncs;
  }

  organization
    "Ciena Corporation";
  contact
    "Web URL: http://www.ciena.com/
     E-mail:  yang@ciena.com
     Postal:  7035 Ridge Road
             Hanover, Maryland 21076
             U.S.A.
     Phone:   +1 800-921-1144
     Fax:     +1 410-694-5750";
  description
    "This YANG module defines Ciena's global
     configuration for telemetry.

     Copyright (c) 2018 Ciena Corporation.  All rights
     reserved.

     All information contained herein is, and remains
     the property of Ciena Corporation. Dissemination of this
     information or reproduction of this material is strictly
     forbidden unless prior written permission is obtained from
     Ciena Corporation.";

  revision 2021-08-11 {
    description
      "Add sensor service mode.";
    reference "openconfig-telemetry.yang";
  }
  revision 2020-03-13 {
    description
      "Add sensor and subscription interfaces.";
    reference "openconfig-telemetry.yang";
  }
  revision 2018-03-26 {
    description
      "Initial version";
    reference
      "RFC 6020: YANG - A Data Modeling Language for
       the Network Configuration Protocol (NETCONF).
       No specific reference; standard not available.";
  }

  typedef ncs_template_tmet-sub-submode {
    description
      "This typedef defines submode of telemetry
       stream subscription.";
    type string;
  }

  typedef ncs_template_tmet-sensor-sub-svcmode {
    description
      "This typedef defines the sensor service mode to support
       telemetry stream subscription.";
    type string;
  }

  typedef ncs_template_tmet-sub-mode {
    description
      "This typedef defines telemetry subscription mode.";
    type string;
  }

  typedef ncs_rpc_notif_tmet-sub-submode {
    description
      "This typedef defines submode of telemetry
       stream subscription.";
    type enumeration {
      enum "target-defined" {
        description
          "gNMI telemetry subscription stream mode of
           sub mode as target-defined.";
      }
      enum "onchange" {
        description
          "gNMI telemetry subscription stream mode of
           sub mode as on-change.";
      }
      enum "sample" {
        description
          "gNMI telemetry subscription stream mode of
           sub mode as sample.";
      }
    }
  }

  typedef ncs_rpc_notif_tmet-sensor-sub-svcmode {
    description
      "This typedef defines the sensor service mode to support
       telemetry stream subscription.";
    type enumeration {
      enum "unavailable" {
        description
          "Sensor registration for a gNMI telemetry subscription
           is unavailable.";
      }
      enum "onchange" {
        description
          "Sensor registration for a gNMI telemetry subscription
           is an onchange service.";
      }
      enum "sample" {
        description
          "Sensor registration for a gNMI telemetry subscription
           is a sample service.";
      }
    }
  }

  typedef ncs_rpc_notif_tmet-sub-mode {
    description
      "This typedef defines telemetry subscription mode.";
    type enumeration {
      enum "stream" {
        description
          "gNMI telemetry subscription mode - stream.";
      }
    }
  }

  typedef live_ncs_tmet-sub-submode {
    description
      "This typedef defines submode of telemetry
       stream subscription.";
    type enumeration {
      enum "target-defined" {
        description
          "gNMI telemetry subscription stream mode of
           sub mode as target-defined.";
      }
      enum "onchange" {
        description
          "gNMI telemetry subscription stream mode of
           sub mode as on-change.";
      }
      enum "sample" {
        description
          "gNMI telemetry subscription stream mode of
           sub mode as sample.";
      }
    }
  }

  typedef live_ncs_tmet-sensor-sub-svcmode {
    description
      "This typedef defines the sensor service mode to support
       telemetry stream subscription.";
    type enumeration {
      enum "unavailable" {
        description
          "Sensor registration for a gNMI telemetry subscription
           is unavailable.";
      }
      enum "onchange" {
        description
          "Sensor registration for a gNMI telemetry subscription
           is an onchange service.";
      }
      enum "sample" {
        description
          "Sensor registration for a gNMI telemetry subscription
           is a sample service.";
      }
    }
  }

  typedef live_ncs_tmet-sub-mode {
    description
      "This typedef defines telemetry subscription mode.";
    type enumeration {
      enum "stream" {
        description
          "gNMI telemetry subscription mode - stream.";
      }
    }
  }

  typedef tmet-sub-submode {
    description
      "This typedef defines submode of telemetry
       stream subscription.";
    type enumeration {
      enum "target-defined" {
        description
          "gNMI telemetry subscription stream mode of
           sub mode as target-defined.";
      }
      enum "onchange" {
        description
          "gNMI telemetry subscription stream mode of
           sub mode as on-change.";
      }
      enum "sample" {
        description
          "gNMI telemetry subscription stream mode of
           sub mode as sample.";
      }
    }
  }

  typedef tmet-sensor-sub-svcmode {
    description
      "This typedef defines the sensor service mode to support
       telemetry stream subscription.";
    type enumeration {
      enum "unavailable" {
        description
          "Sensor registration for a gNMI telemetry subscription
           is unavailable.";
      }
      enum "onchange" {
        description
          "Sensor registration for a gNMI telemetry subscription
           is an onchange service.";
      }
      enum "sample" {
        description
          "Sensor registration for a gNMI telemetry subscription
           is a sample service.";
      }
    }
  }

  typedef tmet-sub-mode {
    description
      "This typedef defines telemetry subscription mode.";
    type enumeration {
      enum "stream" {
        description
          "gNMI telemetry subscription mode - stream.";
      }
    }
  }

  grouping ncs_template_telemetry-server-config {
    description
      "Configuration data for the
       telemetry server.";
    leaf enable {
      type string;
      // NCS drop default statement
      description
        "Enables the telemetry server.";
    }
    leaf tls-service-profile {
      type string;
      description
        "The TLS Service Profile to be used when accepting
         TLS connections.";
    }
  }

  grouping ncs_template_telemetry-subscription-mode {
    description
      "Subscription mode settings.";
    leaf subscription-mode {
      type ncs_template_tmet-sub-mode;
      description
        "The subscription mode specified by
         a client in the subscription request.";
    }
    leaf update-only {
      type string;
      // NCS drop default statement
      description
        "The updates_only flag specified by a client in
         the subscription request.";
    }
  }

  grouping ncs_template_telemetry-subscription-stream-submode {
    description
      "Stream subscription submode.";
    leaf stream-sub-submode {
      type ncs_template_tmet-sub-submode;
      description
        "The sub-submode used within the subscription request
         of type stream mode.";
    }
  }

  grouping ncs_template_telemetry-sensor-subscription-svcmode {
    description
      "Sensor service mode for stream subscription.";
    leaf sensor-sub-svcmode {
      type ncs_template_tmet-sensor-sub-svcmode;
      description
        "The sensor service mode used for the subscription request
         of type stream mode.";
    }
  }

  grouping ncs_template_telemetry-sensor-supported-stream-submode {
    description
      "Grouping for sensor supported stream subscription submode.";
    leaf sensor-supported-stream-submode {
      type ncs_template_tmet-sub-submode;
      description
        "The sub-submode used within the subscription request
         of type stream mode.";
    }
  }

  grouping ncs_template_telemetry-sensor-path-element {
    description
      "Grouping for path elements.";
    // NCS drop config false list 'xpath-elements'
  }

  grouping ncs_template_telemetry-compound-key {
    description
      "Grouping for compound key support.";
    // NCS drop config false list 'compound-keys'
  }

  grouping ncs_template_telemetry-user-info {
    description
      "Grouping for user information";
    leaf user-name {
      type string;
      description
        "User name used for authentication to establish a gNMI
         telemetry subscription session";
    }
    leaf telemetry-server-port {
      type string;
      description
        "The port number of the device on which an external gNMI client
         established a gNMI telemetry subscription session.";
    }
    leaf telemetry-client-ip-address {
      type string;
      description
        "The source IP address from which the external gNMI client
         originates a gNMI telemetry subscription session.";
    }
  }

  grouping ncs_template_telemetry-sensor-id {
    description
      "A grouping to contain unique identifier
       which is used to identify an internal sensor
       assocaited with subscription xpathtmet generates a
       identifier that can uniquely identify a sensor.";
    leaf sensor-id {
      type string;
      description
        "A unique sensor id to identify a sensor.";
    }
  }

  grouping ncs_template_telemetry-subscriptions {
    description
      "Grouping for a list of subscriptions";
    list subscriptions {
      // NCS patched for predictable order
      ordered-by user;
      key "id";
      leaf id {
        type string;
        description
          "GRPC generated identifier to  uniquely identify a gNMI
           telemetry subscription request";
      }
      // NCS drop config false container 'subscription-state'
      // NCS drop config false container subscription
    }
  }

  grouping ncs_template_telemetry-sensors-top {
    description
      "Top level grouping for avaialbe sensors registered for the device.";
    // NCS drop config false container 'telemetry-registered-sensors'
  }

  grouping ncs_template_telemetry-subscriptions-top {
    description
      "Telemetry Subscription stats.";
    // NCS drop config false container 'telemetry-client-subscriptions'
  }

  grouping ncs_rpc_notif_telemetry-server-config {
    description
      "Configuration data for the
       telemetry server.";
    leaf enable {
      type boolean;
      default "true";
      description
        "Enables the telemetry server.";
    }
    leaf tls-service-profile {
      type string;
      description
        "The TLS Service Profile to be used when accepting
         TLS connections.";
    }
  }

  grouping ncs_rpc_notif_telemetry-subscription-mode {
    description
      "Subscription mode settings.";
    leaf subscription-mode {
      type ncs_rpc_notif_tmet-sub-mode;
      description
        "The subscription mode specified by
         a client in the subscription request.";
    }
    leaf update-only {
      type boolean;
      default "false";
      description
        "The updates_only flag specified by a client in
         the subscription request.";
    }
  }

  grouping ncs_rpc_notif_telemetry-subscription-stream-submode {
    description
      "Stream subscription submode.";
    leaf stream-sub-submode {
      type ncs_rpc_notif_tmet-sub-submode;
      description
        "The sub-submode used within the subscription request
         of type stream mode.";
    }
  }

  grouping ncs_rpc_notif_telemetry-sensor-subscription-svcmode {
    description
      "Sensor service mode for stream subscription.";
    leaf sensor-sub-svcmode {
      type ncs_rpc_notif_tmet-sensor-sub-svcmode;
      description
        "The sensor service mode used for the subscription request
         of type stream mode.";
    }
  }

  grouping ncs_rpc_notif_telemetry-sensor-supported-stream-submode {
    description
      "Grouping for sensor supported stream subscription submode.";
    leaf sensor-supported-stream-submode {
      type ncs_rpc_notif_tmet-sub-submode;
      description
        "The sub-submode used within the subscription request
         of type stream mode.";
    }
  }

  grouping ncs_rpc_notif_telemetry-sensor-path-element {
    description
      "Grouping for path elements.";
    list xpath-elements {
      key "path-element";
      config false;
      description
        "Path elements are tokens from the
         registered xpath.";
      leaf path-element {
        type string;
        description
          "Path tokens generated by a registered xpath.";
      }
      leaf filter-name {
        type string;
        description
          "Valid filter name used to filter response from
           Grpc server.";
      }
      leaf filter-value {
        type string;
        description
          "Filter value provided by the client.";
      }
    }
  }

  grouping ncs_rpc_notif_telemetry-compound-key {
    description
      "Grouping for compound key support.";
    list compound-keys {
      key "compound-key";
      config false;
      description
        "List of compound keys and path elements that
         generated them.";
      leaf compound-key {
        type string;
        description
          "Value of a compound key which is generated by
           its list of correlated path elements.";
      }
      uses ncs_rpc_notif_telemetry-sensor-path-element;
    }
  }

  grouping ncs_rpc_notif_telemetry-user-info {
    description
      "Grouping for user information";
    leaf user-name {
      type string;
      description
        "User name used for authentication to establish a gNMI
         telemetry subscription session";
    }
    leaf telemetry-server-port {
      type inet:port-number;
      description
        "The port number of the device on which an external gNMI client
         established a gNMI telemetry subscription session.";
    }
    leaf telemetry-client-ip-address {
      type inet:ip-address;
      description
        "The source IP address from which the external gNMI client
         originates a gNMI telemetry subscription session.";
    }
  }

  grouping ncs_rpc_notif_telemetry-sensor-id {
    description
      "A grouping to contain unique identifier
       which is used to identify an internal sensor
       assocaited with subscription xpathtmet generates a
       identifier that can uniquely identify a sensor.";
    leaf sensor-id {
      type uint64;
      description
        "A unique sensor id to identify a sensor.";
    }
  }

  grouping ncs_rpc_notif_telemetry-subscriptions {
    description
      "Grouping for a list of subscriptions";
    list subscriptions {
      key "id";
      leaf id {
        type string;
        description
          "GRPC generated identifier to  uniquely identify a gNMI
           telemetry subscription request";
      }
      container subscription-state {
        config false;
        description
          "State parameters relating to the telemetry
           subscriptions on the local device.";
        uses ncs_rpc_notif_telemetry-user-info;
        uses ncs_rpc_notif_telemetry-subscription-mode;
        uses oc-telemetry:ncs_rpc_notif_telemetry-stream-frequency-config;
      }
      container subscription {
        config false;
        description
          "Describes a set of paths that is to be subscribed to by a
           client.";
        list telemetry-sensor-paths {
          key "telemetry-sensor-path";
          description
            "A list of sensor paths and exclude filters which comprise
             a sensor grouping";
          leaf telemetry-sensor-path {
            type string;
            description
              "The sensor path is a path to a portion of operational
               state of interest in the data model";
          }
          uses ncs_rpc_notif_telemetry-sensor-id;
          uses ncs_rpc_notif_telemetry-subscription-stream-submode;
          uses ncs_rpc_notif_telemetry-sensor-subscription-svcmode;
        }
      }
    }
  }

  grouping ncs_rpc_notif_telemetry-sensors-top {
    description
      "Top level grouping for avaialbe sensors registered for the device.";
    container telemetry-registered-sensors {
      config false;
      container stream-sensors {
        description
          "List of stream sensors that are registered
           for the device's telemetry system.";
        list telemetry-sensor-paths {
          key "telemetry-sensor-path";
          description
            "A list of sensor paths and exclude filters which comprise
             a sensor grouping";
          leaf telemetry-sensor-path {
            type string;
            description
              "The sensor path is a path to a portion of operational
               state of interest in the data model";
          }
          uses ncs_rpc_notif_telemetry-sensor-id;
          uses ncs_rpc_notif_telemetry-sensor-supported-stream-submode;
        }
      }
    }
  }

  grouping ncs_rpc_notif_telemetry-subscriptions-top {
    description
      "Telemetry Subscription stats.";
    container telemetry-client-subscriptions {
      config false;
      uses ncs_rpc_notif_telemetry-subscriptions;
    }
  }

  grouping live_ncs_telemetry-server-config {
    description
      "Configuration data for the
       telemetry server.";
    leaf enable {
      type boolean;
      // NCS drop default statement
      description
        "Enables the telemetry server.";
    }
    leaf tls-service-profile {
      type leafref {
        path "/ncs:devices/ncs:device/ncs:live-status/ciena-tsp:tls-service-profiles/ciena-tsp:tls-service-profile-name" {
          tailf:xpath-root 3;
        }
      }
      description
        "The TLS Service Profile to be used when accepting
         TLS connections.";
    }
  }

  grouping live_ncs_telemetry-subscription-mode {
    description
      "Subscription mode settings.";
    leaf subscription-mode {
      type live_ncs_tmet-sub-mode;
      description
        "The subscription mode specified by
         a client in the subscription request.";
    }
    leaf update-only {
      type boolean;
      // NCS drop default statement
      description
        "The updates_only flag specified by a client in
         the subscription request.";
    }
  }

  grouping live_ncs_telemetry-subscription-stream-submode {
    description
      "Stream subscription submode.";
    leaf stream-sub-submode {
      type live_ncs_tmet-sub-submode;
      description
        "The sub-submode used within the subscription request
         of type stream mode.";
    }
  }

  grouping live_ncs_telemetry-sensor-subscription-svcmode {
    description
      "Sensor service mode for stream subscription.";
    leaf sensor-sub-svcmode {
      type live_ncs_tmet-sensor-sub-svcmode;
      description
        "The sensor service mode used for the subscription request
         of type stream mode.";
    }
  }

  grouping live_ncs_telemetry-sensor-supported-stream-submode {
    description
      "Grouping for sensor supported stream subscription submode.";
    leaf sensor-supported-stream-submode {
      type live_ncs_tmet-sub-submode;
      description
        "The sub-submode used within the subscription request
         of type stream mode.";
    }
  }

  grouping live_ncs_telemetry-sensor-path-element {
    description
      "Grouping for path elements.";
    list xpath-elements {
      key "path-element";
      description
        "Path elements are tokens from the
         registered xpath.";
      leaf path-element {
        type string;
        description
          "Path tokens generated by a registered xpath.";
      }
      leaf filter-name {
        type string;
        description
          "Valid filter name used to filter response from
           Grpc server.";
      }
      leaf filter-value {
        type string;
        description
          "Filter value provided by the client.";
      }
    }
  }

  grouping live_ncs_telemetry-compound-key {
    description
      "Grouping for compound key support.";
    list compound-keys {
      key "compound-key";
      description
        "List of compound keys and path elements that
         generated them.";
      leaf compound-key {
        type string;
        description
          "Value of a compound key which is generated by
           its list of correlated path elements.";
      }
      uses live_ncs_telemetry-sensor-path-element;
    }
  }

  grouping live_ncs_telemetry-user-info {
    description
      "Grouping for user information";
    leaf user-name {
      type string;
      description
        "User name used for authentication to establish a gNMI
         telemetry subscription session";
    }
    leaf telemetry-server-port {
      type inet:port-number;
      description
        "The port number of the device on which an external gNMI client
         established a gNMI telemetry subscription session.";
    }
    leaf telemetry-client-ip-address {
      type inet:ip-address;
      description
        "The source IP address from which the external gNMI client
         originates a gNMI telemetry subscription session.";
    }
  }

  grouping live_ncs_telemetry-sensor-id {
    description
      "A grouping to contain unique identifier
       which is used to identify an internal sensor
       assocaited with subscription xpathtmet generates a
       identifier that can uniquely identify a sensor.";
    leaf sensor-id {
      type uint64;
      description
        "A unique sensor id to identify a sensor.";
    }
  }

  grouping live_ncs_telemetry-subscriptions {
    description
      "Grouping for a list of subscriptions";
    list subscriptions {
      key "id";
      leaf id {
        type string;
        description
          "GRPC generated identifier to  uniquely identify a gNMI
           telemetry subscription request";
      }
      container subscription-state {
        description
          "State parameters relating to the telemetry
           subscriptions on the local device.";
        uses live_ncs_telemetry-user-info;
        uses live_ncs_telemetry-subscription-mode;
        uses oc-telemetry:live_ncs_telemetry-stream-frequency-config;
      }
      container subscription {
        description
          "Describes a set of paths that is to be subscribed to by a
           client.";
        list telemetry-sensor-paths {
          key "telemetry-sensor-path";
          description
            "A list of sensor paths and exclude filters which comprise
             a sensor grouping";
          leaf telemetry-sensor-path {
            type string;
            description
              "The sensor path is a path to a portion of operational
               state of interest in the data model";
          }
          uses live_ncs_telemetry-sensor-id;
          uses live_ncs_telemetry-subscription-stream-submode;
          uses live_ncs_telemetry-sensor-subscription-svcmode;
        }
      }
    }
  }

  grouping live_ncs_telemetry-sensors-top {
    description
      "Top level grouping for avaialbe sensors registered for the device.";
    container telemetry-registered-sensors {
      container stream-sensors {
        description
          "List of stream sensors that are registered
           for the device's telemetry system.";
        list telemetry-sensor-paths {
          key "telemetry-sensor-path";
          description
            "A list of sensor paths and exclude filters which comprise
             a sensor grouping";
          leaf telemetry-sensor-path {
            type string;
            description
              "The sensor path is a path to a portion of operational
               state of interest in the data model";
          }
          uses live_ncs_telemetry-sensor-id;
          uses live_ncs_telemetry-sensor-supported-stream-submode;
        }
      }
    }
  }

  grouping live_ncs_telemetry-subscriptions-top {
    description
      "Telemetry Subscription stats.";
    container telemetry-client-subscriptions {
      uses live_ncs_telemetry-subscriptions;
    }
  }

  grouping telemetry-server-config {
    description
      "Configuration data for the
       telemetry server.";
    leaf enable {
      type boolean;
      default "true";
      description
        "Enables the telemetry server.";
    }
    leaf tls-service-profile {
      type leafref {
        path "/ncs:devices/ncs:device/ncs:config/ciena-tsp:tls-service-profiles/ciena-tsp:tls-service-profile-name" {
          tailf:xpath-root 3;
        }
      }
      description
        "The TLS Service Profile to be used when accepting
         TLS connections.";
    }
  }

  grouping telemetry-subscription-mode {
    description
      "Subscription mode settings.";
    leaf subscription-mode {
      type tmet-sub-mode;
      description
        "The subscription mode specified by
         a client in the subscription request.";
    }
    leaf update-only {
      type boolean;
      default "false";
      description
        "The updates_only flag specified by a client in
         the subscription request.";
    }
  }

  grouping telemetry-subscription-stream-submode {
    description
      "Stream subscription submode.";
    leaf stream-sub-submode {
      type tmet-sub-submode;
      description
        "The sub-submode used within the subscription request
         of type stream mode.";
    }
  }

  grouping telemetry-sensor-subscription-svcmode {
    description
      "Sensor service mode for stream subscription.";
    leaf sensor-sub-svcmode {
      type tmet-sensor-sub-svcmode;
      description
        "The sensor service mode used for the subscription request
         of type stream mode.";
    }
  }

  grouping telemetry-sensor-supported-stream-submode {
    description
      "Grouping for sensor supported stream subscription submode.";
    leaf sensor-supported-stream-submode {
      type tmet-sub-submode;
      description
        "The sub-submode used within the subscription request
         of type stream mode.";
    }
  }

  grouping telemetry-sensor-path-element {
    description
      "Grouping for path elements.";
    // NCS drop config false list 'xpath-elements'
  }

  grouping telemetry-compound-key {
    description
      "Grouping for compound key support.";
    // NCS drop config false list 'compound-keys'
  }

  grouping telemetry-user-info {
    description
      "Grouping for user information";
    leaf user-name {
      type string;
      description
        "User name used for authentication to establish a gNMI
         telemetry subscription session";
    }
    leaf telemetry-server-port {
      type inet:port-number;
      description
        "The port number of the device on which an external gNMI client
         established a gNMI telemetry subscription session.";
    }
    leaf telemetry-client-ip-address {
      type inet:ip-address;
      description
        "The source IP address from which the external gNMI client
         originates a gNMI telemetry subscription session.";
    }
  }

  grouping telemetry-sensor-id {
    description
      "A grouping to contain unique identifier
       which is used to identify an internal sensor
       assocaited with subscription xpathtmet generates a
       identifier that can uniquely identify a sensor.";
    leaf sensor-id {
      type uint64;
      description
        "A unique sensor id to identify a sensor.";
    }
  }

  grouping telemetry-subscriptions {
    description
      "Grouping for a list of subscriptions";
    list subscriptions {
      key "id";
      leaf id {
        type string;
        description
          "GRPC generated identifier to  uniquely identify a gNMI
           telemetry subscription request";
      }
      // NCS drop config false container 'subscription-state'
      // NCS drop config false container subscription
    }
  }

  grouping telemetry-sensors-top {
    description
      "Top level grouping for avaialbe sensors registered for the device.";
    // NCS drop config false container 'telemetry-registered-sensors'
  }

  grouping telemetry-subscriptions-top {
    description
      "Telemetry Subscription stats.";
    // NCS drop config false container 'telemetry-client-subscriptions'
  }

  augment "/ncs:devices/ncs:device/ncs:rpc" {
    container rpc-gnmi-subscribe {
      tailf:ncs-device-type "netconf";
      tailf:display-when "not(../../ncs:module) or ../../ncs:module[ncs:name='ciena-openconfig-telemetry']";
      tailf:action gnmi-subscribe {
        tailf:actionpoint ncsproxy {
          tailf:internal;
        }
        description
          "Represents the gNMI Subscribe RPC used by
           gNMI clients when requesting a subscription from
           telemetry. Clients may use this RPC to define NACM
           rules limiting access to the telemetry subscribe operation.
           Since telemetry subscriptions are only supported over
           telemetry connections, attempting to invoke it via NETCONF
           will always return an error.";
      }
    }
  }
  augment "/ncs:devices/ncs:device-group/ncs:ned-id/ncs:rpc" {
    container rpc-gnmi-subscribe {
      tailf:ncs-device-type "netconf";
      tailf:display-when "/ncs:devices/ncs:device[ncs:name=current()/../../../ncs:member]/ncs:module[ncs:name='ciena-openconfig-telemetry']";
      tailf:action gnmi-subscribe {
        tailf:actionpoint ncsproxy {
          tailf:internal;
        }
        description
          "Represents the gNMI Subscribe RPC used by
           gNMI clients when requesting a subscription from
           telemetry. Clients may use this RPC to define NACM
           rules limiting access to the telemetry subscribe operation.
           Since telemetry subscriptions are only supported over
           telemetry connections, attempting to invoke it via NETCONF
           will always return an error.";
      }
    }
  }
  augment "/ncs:devices/ncs:device/ncs:config" {
    uses telemetry-sensors-top;
    uses telemetry-subscriptions-top;
  }
  augment "/ncs:devices/ncs:device/ncs:live-status" {
    uses live_ncs_telemetry-sensors-top {
      refine telemetry-registered-sensors {
        tailf:ncs-device-type "netconf";
        tailf:display-when "not(../../ncs:module) or ../../ncs:module[ncs:name='ciena-openconfig-telemetry'] or (../../ncs:live-status-protocol[not(ncs:capability)]) or (../../ncs:live-status-protocol/ncs:capability/ncs:module[.='ciena-openconfig-telemetry'])";
      }
    }
    uses live_ncs_telemetry-subscriptions-top {
      refine telemetry-client-subscriptions {
        tailf:ncs-device-type "netconf";
        tailf:display-when "not(../../ncs:module) or ../../ncs:module[ncs:name='ciena-openconfig-telemetry'] or (../../ncs:live-status-protocol[not(ncs:capability)]) or (../../ncs:live-status-protocol/ncs:capability/ncs:module[.='ciena-openconfig-telemetry'])";
      }
    }
  }
  augment "/ncs:devices/ncs:template/ncs:ned-id/ncs:config" {
    uses ncs_template_telemetry-sensors-top;
    uses ncs_template_telemetry-subscriptions-top;
  }
  augment "/ncs:devices/ncs:template/ncs:ned-id/ncs:config/oc-telemetry:telemetry-system" {
    description
      "Addition for configuring the telemetry server";
    container server {
      description
        "Top-level container for telemetry server";
      container config {
        description
          "Configuration parameters for the
           telemetry server.";
        uses ncs_template_telemetry-server-config;
      }
    }
  }
  augment "/ncs:devices/ncs:device/ncs:live-status/oc-telemetry:telemetry-system" {
    description
      "Addition for configuring the telemetry server";
    container server {
      tailf:ncs-device-type "netconf";
      tailf:display-when "not(../../../ncs:module) or ../../../ncs:module[ncs:name='ciena-openconfig-telemetry'] or (../../../ncs:live-status-protocol[not(ncs:capability)]) or (../../../ncs:live-status-protocol/ncs:capability/ncs:module[.='ciena-openconfig-telemetry'])";
      description
        "Top-level container for telemetry server";
      container config {
        description
          "Configuration parameters for the
           telemetry server.";
        uses live_ncs_telemetry-server-config;
      }
    }
  }
  augment "/ncs:devices/ncs:device/ncs:config/oc-telemetry:telemetry-system" {
    description
      "Addition for configuring the telemetry server";
    container server {
      tailf:ncs-device-type "netconf";
      tailf:display-when "not(../../../ncs:module) or ../../../ncs:module[ncs:name='ciena-openconfig-telemetry']";
      description
        "Top-level container for telemetry server";
      container config {
        description
          "Configuration parameters for the
           telemetry server.";
        uses telemetry-server-config;
      }
    }
  }
}
