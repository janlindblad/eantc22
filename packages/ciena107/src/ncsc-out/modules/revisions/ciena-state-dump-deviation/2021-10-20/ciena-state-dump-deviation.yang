module ciena-state-dump-deviation {
  // Generated by yanger -t ncs
  tailf:mount-id "ciena107-nc-1.0:ciena107-nc-1.0";
  tailf:ncs-device-type "netconf";

  namespace "http://www.ciena.com/ns/yang/ciena-state-dump-dev";
  prefix ciena-state-dump-dev;

  import ciena-state-dump {
    prefix state-dump;
  }
  import tailf-common {
    prefix tailf;
  }
  import tailf-ncs {
    prefix ncs;
  }

  revision 2021-10-20 {
    description
      "Deviate unsupported attributes";
  }
  revision 2020-02-03 {
    description
      "Initial revision";
  }

  deviation "/ncs:devices/ncs:device/ncs:rpc/state-dump:rpc-state-dump/state-dump:state-dump/state-dump:input/state-dump:tls-service-profile" {
    deviate not-supported;
  }
  deviation "/ncs:devices/ncs:device/ncs:rpc/state-dump:rpc-state-dump/state-dump:state-dump/state-dump:input/state-dump:file-transfer-syntax/state-dump:component/state-dump:port" {
    deviate not-supported;
  }
}
