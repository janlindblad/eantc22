module yuma-types {
  // Generated by yanger -t ncs
  tailf:mount-id "ciena107-nc-1.0:ciena107-nc-1.0";
  tailf:ncs-device-type "netconf";

  yang-version 1;
  namespace "http://netconfcentral.org/ns/yuma-types";
  prefix yt;

  import tailf-common {
    prefix tailf;
  }
  import tailf-ncs {
    prefix ncs;
  }

  organization
    "Netconf Central";
  contact
    "Andy Bierman <andy at netconfcentral.org>";
  description
    "Yuma Common Data Types

     Copyright (c) 2008 - 2012 Andy Bierman and the persons
     identified as authors of the code.  All rights reserved.

     Redistribution and use in source and binary forms, with or
     without modification, is permitted pursuant to, and subject
     to the license terms contained in, the BSD 3-Clause License
     http://opensource.org/licenses/BSD-3-Clause";

  revision 2019-11-29 {
    description
      "Fix NcxName, NcxQName, and yang-identifier patterns";
  }
  revision 2015-09-25 {
    description
      "Added typedef NcxDeviceName.";
  }
  revision 2012-06-01 {
    description
      "Added new NcDebugType enum (sysLogLevel).
       Added yang-identifier data type.";
  }
  revision 2011-12-18 {
    description
      "Added TransactionId data type.";
  }
  revision 2010-11-28 {
    description
      "Change default indent from 3 to 2.";
  }
  revision 2010-01-25 {
    description
      "Adjust name lengths in ranges and patterns.";
  }
  revision 2008-11-21 {
    description
      "Renamed ncxtypes to yuma-types.";
  }
  revision 2008-07-20 {
    description
      "Converted from ncxtypes.ncx.";
  }

  typedef ncs_template_int {
    description
      "Changed int base type to int32 for YANG";
    type string;
  }

  typedef ncs_template_uint {
    description
      "Changed uint base type to uint32 for YANG";
    type string;
  }

  typedef ncs_template_long {
    description
      "Changed long base type to int64 for YANG";
    type string;
  }

  typedef ncs_template_ulong {
    description
      "Changed ulong base type to uint64 for YANG";
    type string;
  }

  typedef ncs_template_ustring {
    description
      "Changed ustring base type to binary for YANG";
    type string;
  }

  typedef ncs_template_NcxName {
    description
      "General Purpose NCX Name string.";
    type string;
  }

  typedef ncs_template_NcxQName {
    description
      "Qualified Name:
        module-name:NcxName OR owner-name:NcxName.";
    type string;
  }

  typedef ncs_template_NcxIdentifier {
    description
      "Union of all the Identifier types.";
    type string;
  }

  typedef ncs_template_yang-identifier {
    description
      "YANG identifier string.";
    type string;
  }

  typedef ncs_template_NcxSessionId {
    description
      "NCX Session ID number";
    type string;
  }

  typedef ncs_template_NcxLineLength {
    description
      "Requested Maximum Line Length";
    type string;
  }

  typedef ncs_template_NcxDeviceName {
    description
      "NCX Device Name string.";
    type ncs_template_NcxName;
  }

  typedef ncs_template_NcxUserName {
    description
      "NCX User Name string.";
    type ncs_template_NcxName;
  }

  typedef ncs_template_NcxGroupName {
    description
      "NCX Group Name string.";
    type ncs_template_NcxName;
  }

  typedef ncs_template_NcAccessControlType {
    description
      "NCX System access control mode.";
    type string;
    // NCS drop default statement
  }

  typedef ncs_template_NcxRpcType {
    description
      "NCX RPC Type Classifications";
    type string;
  }

  typedef ncs_template_NcDebugType {
    description
      "NCX Session debug logging control enumeration.
       Each successive value includes all the previous
       messages from lower value enumeration values,
       plus the messages for the specified value.

       off == no logging is done
       write == log write  messages (NOT SUPPORTED IN YUMA)
       dev0 == log developer level 0 messages (NOT SUPPORTED
                 IN YUMA)
       error == log error messages
       warn == log warning messages
       info == log info messages
       dev1    == log developer level 1 messages (NOT SUPPORTED
                  IN YUMA)
       debug  == log debug level 1 messages
       debug2 == log debug level 2 messages
       debug3 == log debug level 3 messages
       debug4 == log debug level 4 messages";
    type string;
    // NCS drop default statement
  }

  typedef ncs_template_NcPortNumber {
    description
      "Transport layer port number.";
    type string;
  }

  typedef ncs_template_NcIndex {
    description
      "Non-negative index value";
    type string;
  }

  typedef ncs_template_NcPathList {
    description
      "PATHSPEC formatted string indicating the machine-dependent
       search path for the NCX programs to use.  Parameters
       with this data type can be used to override the
       default search order, and insert special work
       directories in the search path.

       Each component in the string is an absolute or
       relative directory path specification.
       The colon char ':' is used to separate the path strings.
       Whitespace is not allowed in the string at all.

       For example, the following string contains 3 paths
       that would be used in the order given:

       /home/users/testbed1/yang:/home/users/yang:/usr/share/yang";
    type string;
  }

  typedef ncs_template_NcModuleSpec {
    description
      "A string which specifies a module name, or a filespec
       which represents a module, with an optional revision date.

             If this string represents a filespec,
             containing any path separation characters, and/or
             ending with the '.yang' or '.yin' extension,
             then only that file location will be checked.

             If this string represents a module name, then
             the module search path will be checked for
             a file with the module name and the '.yang'
             or '.yin.' extension.

             If this string contains a module name
             followed by an 'at sign' character (@),
             followed by a revision string (e.g., foo@2010-01-01),
             then that specific version of the module will be used.

             If this string begins with a '~' character,
             then a username is expected to follow or
             a directory separator character.  If it begins
             with a '$' character, then an environment variable
             name is expected to follow.

             ~/some/path ==> <my-home-dir>/some/path

             ~fred/some/path ==> <fred-home-dir>/some/path

             $workdir/some/path ==> <workdir-env-var>/some/path
          ";
    type string;
  }

  typedef ncs_template_NcPathSpec {
    description
      "A string which specifies a directory name.";
    type string;
  }

  typedef ncs_template_IndentType {
    description
      "Requested indent amount.
       Only a limited range of line indent values are allowed.";
    type string;
    // NCS drop default statement
  }

  typedef ncs_template_Timeout {
    description
      "Number of seconds to wait for a response
       from the NETCONF peer before declaring a timeout.
       Zero means no timeout at all.";
    type string;
    units "seconds";
    // NCS drop default statement
  }

  typedef ncs_template_Date {
    type string;
    description
      "Represents a specific date in YYYY-MM-DD format.";
  }

  typedef ncs_template_FeatureSpec {
    description
      "Represents a feature specifier, which consists
       of a module-name, colon character ':' and then
       a feature name (e.g., 'foo:bar')";
    type ncs_template_NcxQName;
  }

  typedef ncs_template_TransactionId {
    description
      "Database edit transaction identifier.
       This is not a permanent identifier, and should only
       be used for 'equal or not-equal' comparison tests.
       The value will wrap after the maximum value is reached.";
    type string;
  }

  typedef ncs_rpc_notif_int {
    description
      "Changed int base type to int32 for YANG";
    type int32;
  }

  typedef ncs_rpc_notif_uint {
    description
      "Changed uint base type to uint32 for YANG";
    type uint32;
  }

  typedef ncs_rpc_notif_long {
    description
      "Changed long base type to int64 for YANG";
    type int64;
  }

  typedef ncs_rpc_notif_ulong {
    description
      "Changed ulong base type to uint64 for YANG";
    type uint64;
  }

  typedef ncs_rpc_notif_ustring {
    description
      "Changed ustring base type to binary for YANG";
    type binary;
  }

  typedef ncs_rpc_notif_NcxName {
    description
      "General Purpose NCX Name string.";
    type string {
      length "1..64";
      pattern '[a-zA-Z_][a-zA-Z0-9\-_\.]{0,63}';
    }
  }

  typedef ncs_rpc_notif_NcxQName {
    description
      "Qualified Name:
        module-name:NcxName OR owner-name:NcxName.";
    type string {
      length "1..129";
      pattern '(([a-zA-Z_][a-zA-Z0-9\-_\.]{0,63}):)?([a-zA-Z][a-zA-Z0-9\-_\.]{0,63})';
    }
  }

  typedef ncs_rpc_notif_NcxIdentifier {
    description
      "Union of all the Identifier types.";
    type union {
      type ncs_rpc_notif_NcxName;
      type ncs_rpc_notif_NcxQName;
    }
  }

  typedef ncs_rpc_notif_yang-identifier {
    description
      "YANG identifier string.";
    type string {
      length "1..max";
      pattern '[a-zA-Z_][a-zA-Z0-9\-_\.]*';
    }
  }

  typedef ncs_rpc_notif_NcxSessionId {
    description
      "NCX Session ID number";
    type uint32 {
      range "1..max";
    }
  }

  typedef ncs_rpc_notif_NcxLineLength {
    description
      "Requested Maximum Line Length";
    type uint32 {
      range "32..65535";
    }
  }

  typedef ncs_rpc_notif_NcxDeviceName {
    description
      "NCX Device Name string.";
    type ncs_rpc_notif_NcxName;
  }

  typedef ncs_rpc_notif_NcxUserName {
    description
      "NCX User Name string.";
    type ncs_rpc_notif_NcxName;
  }

  typedef ncs_rpc_notif_NcxGroupName {
    description
      "NCX Group Name string.";
    type ncs_rpc_notif_NcxName;
  }

  typedef ncs_rpc_notif_NcAccessControlType {
    description
      "NCX System access control mode.";
    type enumeration {
      enum "open" {
        description
          "no access control checking enforced";
      }
      enum "loose" {
        description
          "any RPC method in the netconf namespace can
           be invoked;  read-only data allowed for all";
      }
      enum "strict" {
        description
          "RPC entry must be present to invoke
           an RPC method; ncxacl Data entry must be present
           to access any data. (Except for user == 'root'.)";
      }
    }
    default "strict";
  }

  typedef ncs_rpc_notif_NcxRpcType {
    description
      "NCX RPC Type Classifications";
    type enumeration {
      enum "other";
      enum "config";
      enum "exec";
      enum "monitor";
      enum "debug";
    }
  }

  typedef ncs_rpc_notif_NcDebugType {
    description
      "NCX Session debug logging control enumeration.
       Each successive value includes all the previous
       messages from lower value enumeration values,
       plus the messages for the specified value.

       off == no logging is done
       write == log write  messages (NOT SUPPORTED IN YUMA)
       dev0 == log developer level 0 messages (NOT SUPPORTED
                 IN YUMA)
       error == log error messages
       warn == log warning messages
       info == log info messages
       dev1    == log developer level 1 messages (NOT SUPPORTED
                  IN YUMA)
       debug  == log debug level 1 messages
       debug2 == log debug level 2 messages
       debug3 == log debug level 3 messages
       debug4 == log debug level 4 messages";
    type enumeration {
      enum "off";
      enum "write";
      enum "dev0";
      enum "error";
      enum "warn";
      enum "info";
      enum "dev1";
      enum "debug";
      enum "debug2";
      enum "debug3";
      enum "debug4";
    }
    default "info";
  }

  typedef ncs_rpc_notif_NcPortNumber {
    description
      "Transport layer port number.";
    type uint32 {
      range "1 .. 65535";
    }
  }

  typedef ncs_rpc_notif_NcIndex {
    description
      "Non-negative index value";
    type uint32 {
      range "1..max";
    }
  }

  typedef ncs_rpc_notif_NcPathList {
    description
      "PATHSPEC formatted string indicating the machine-dependent
       search path for the NCX programs to use.  Parameters
       with this data type can be used to override the
       default search order, and insert special work
       directories in the search path.

       Each component in the string is an absolute or
       relative directory path specification.
       The colon char ':' is used to separate the path strings.
       Whitespace is not allowed in the string at all.

       For example, the following string contains 3 paths
       that would be used in the order given:

       /home/users/testbed1/yang:/home/users/yang:/usr/share/yang";
    type string {
      length "1 .. max";
    }
  }

  typedef ncs_rpc_notif_NcModuleSpec {
    description
      "A string which specifies a module name, or a filespec
       which represents a module, with an optional revision date.

             If this string represents a filespec,
             containing any path separation characters, and/or
             ending with the '.yang' or '.yin' extension,
             then only that file location will be checked.

             If this string represents a module name, then
             the module search path will be checked for
             a file with the module name and the '.yang'
             or '.yin.' extension.

             If this string contains a module name
             followed by an 'at sign' character (@),
             followed by a revision string (e.g., foo@2010-01-01),
             then that specific version of the module will be used.

             If this string begins with a '~' character,
             then a username is expected to follow or
             a directory separator character.  If it begins
             with a '$' character, then an environment variable
             name is expected to follow.

             ~/some/path ==> <my-home-dir>/some/path

             ~fred/some/path ==> <fred-home-dir>/some/path

             $workdir/some/path ==> <workdir-env-var>/some/path
          ";
    type string {
      length "1 .. 4095";
    }
  }

  typedef ncs_rpc_notif_NcPathSpec {
    description
      "A string which specifies a directory name.";
    type string {
      length "1 .. 4095";
    }
  }

  typedef ncs_rpc_notif_IndentType {
    description
      "Requested indent amount.
       Only a limited range of line indent values are allowed.";
    type uint32 {
      range "0..9";
    }
    default "2";
  }

  typedef ncs_rpc_notif_Timeout {
    description
      "Number of seconds to wait for a response
       from the NETCONF peer before declaring a timeout.
       Zero means no timeout at all.";
    type uint32;
    units "seconds";
    default "30";
  }

  typedef ncs_rpc_notif_Date {
    type string {
      pattern '\d{4}-\d{2}-\d{2}';
    }
    description
      "Represents a specific date in YYYY-MM-DD format.";
  }

  typedef ncs_rpc_notif_FeatureSpec {
    description
      "Represents a feature specifier, which consists
       of a module-name, colon character ':' and then
       a feature name (e.g., 'foo:bar')";
    type ncs_rpc_notif_NcxQName;
  }

  typedef ncs_rpc_notif_TransactionId {
    description
      "Database edit transaction identifier.
       This is not a permanent identifier, and should only
       be used for 'equal or not-equal' comparison tests.
       The value will wrap after the maximum value is reached.";
    type uint64 {
      range "1 .. max";
    }
  }

  typedef live_ncs_int {
    description
      "Changed int base type to int32 for YANG";
    type int32;
  }

  typedef live_ncs_uint {
    description
      "Changed uint base type to uint32 for YANG";
    type uint32;
  }

  typedef live_ncs_long {
    description
      "Changed long base type to int64 for YANG";
    type int64;
  }

  typedef live_ncs_ulong {
    description
      "Changed ulong base type to uint64 for YANG";
    type uint64;
  }

  typedef live_ncs_ustring {
    description
      "Changed ustring base type to binary for YANG";
    type binary;
  }

  typedef live_ncs_NcxName {
    description
      "General Purpose NCX Name string.";
    type string {
      length "1..64";
      pattern '[a-zA-Z_][a-zA-Z0-9\-_\.]{0,63}';
    }
  }

  typedef live_ncs_NcxQName {
    description
      "Qualified Name:
        module-name:NcxName OR owner-name:NcxName.";
    type string {
      length "1..129";
      pattern '(([a-zA-Z_][a-zA-Z0-9\-_\.]{0,63}):)?([a-zA-Z][a-zA-Z0-9\-_\.]{0,63})';
    }
  }

  typedef live_ncs_NcxIdentifier {
    description
      "Union of all the Identifier types.";
    type union {
      type live_ncs_NcxName;
      type live_ncs_NcxQName;
    }
  }

  typedef live_ncs_yang-identifier {
    description
      "YANG identifier string.";
    type string {
      length "1..max";
      pattern '[a-zA-Z_][a-zA-Z0-9\-_\.]*';
    }
  }

  typedef live_ncs_NcxSessionId {
    description
      "NCX Session ID number";
    type uint32 {
      range "1..max";
    }
  }

  typedef live_ncs_NcxLineLength {
    description
      "Requested Maximum Line Length";
    type uint32 {
      range "32..65535";
    }
  }

  typedef live_ncs_NcxDeviceName {
    description
      "NCX Device Name string.";
    type live_ncs_NcxName;
  }

  typedef live_ncs_NcxUserName {
    description
      "NCX User Name string.";
    type live_ncs_NcxName;
  }

  typedef live_ncs_NcxGroupName {
    description
      "NCX Group Name string.";
    type live_ncs_NcxName;
  }

  typedef live_ncs_NcAccessControlType {
    description
      "NCX System access control mode.";
    type enumeration {
      enum "open" {
        description
          "no access control checking enforced";
      }
      enum "loose" {
        description
          "any RPC method in the netconf namespace can
           be invoked;  read-only data allowed for all";
      }
      enum "strict" {
        description
          "RPC entry must be present to invoke
           an RPC method; ncxacl Data entry must be present
           to access any data. (Except for user == 'root'.)";
      }
    }
    // NCS drop default statement
  }

  typedef live_ncs_NcxRpcType {
    description
      "NCX RPC Type Classifications";
    type enumeration {
      enum "other";
      enum "config";
      enum "exec";
      enum "monitor";
      enum "debug";
    }
  }

  typedef live_ncs_NcDebugType {
    description
      "NCX Session debug logging control enumeration.
       Each successive value includes all the previous
       messages from lower value enumeration values,
       plus the messages for the specified value.

       off == no logging is done
       write == log write  messages (NOT SUPPORTED IN YUMA)
       dev0 == log developer level 0 messages (NOT SUPPORTED
                 IN YUMA)
       error == log error messages
       warn == log warning messages
       info == log info messages
       dev1    == log developer level 1 messages (NOT SUPPORTED
                  IN YUMA)
       debug  == log debug level 1 messages
       debug2 == log debug level 2 messages
       debug3 == log debug level 3 messages
       debug4 == log debug level 4 messages";
    type enumeration {
      enum "off";
      enum "write";
      enum "dev0";
      enum "error";
      enum "warn";
      enum "info";
      enum "dev1";
      enum "debug";
      enum "debug2";
      enum "debug3";
      enum "debug4";
    }
    // NCS drop default statement
  }

  typedef live_ncs_NcPortNumber {
    description
      "Transport layer port number.";
    type uint32 {
      range "1 .. 65535";
    }
  }

  typedef live_ncs_NcIndex {
    description
      "Non-negative index value";
    type uint32 {
      range "1..max";
    }
  }

  typedef live_ncs_NcPathList {
    description
      "PATHSPEC formatted string indicating the machine-dependent
       search path for the NCX programs to use.  Parameters
       with this data type can be used to override the
       default search order, and insert special work
       directories in the search path.

       Each component in the string is an absolute or
       relative directory path specification.
       The colon char ':' is used to separate the path strings.
       Whitespace is not allowed in the string at all.

       For example, the following string contains 3 paths
       that would be used in the order given:

       /home/users/testbed1/yang:/home/users/yang:/usr/share/yang";
    type string {
      length "1 .. max";
    }
  }

  typedef live_ncs_NcModuleSpec {
    description
      "A string which specifies a module name, or a filespec
       which represents a module, with an optional revision date.

             If this string represents a filespec,
             containing any path separation characters, and/or
             ending with the '.yang' or '.yin' extension,
             then only that file location will be checked.

             If this string represents a module name, then
             the module search path will be checked for
             a file with the module name and the '.yang'
             or '.yin.' extension.

             If this string contains a module name
             followed by an 'at sign' character (@),
             followed by a revision string (e.g., foo@2010-01-01),
             then that specific version of the module will be used.

             If this string begins with a '~' character,
             then a username is expected to follow or
             a directory separator character.  If it begins
             with a '$' character, then an environment variable
             name is expected to follow.

             ~/some/path ==> <my-home-dir>/some/path

             ~fred/some/path ==> <fred-home-dir>/some/path

             $workdir/some/path ==> <workdir-env-var>/some/path
          ";
    type string {
      length "1 .. 4095";
    }
  }

  typedef live_ncs_NcPathSpec {
    description
      "A string which specifies a directory name.";
    type string {
      length "1 .. 4095";
    }
  }

  typedef live_ncs_IndentType {
    description
      "Requested indent amount.
       Only a limited range of line indent values are allowed.";
    type uint32 {
      range "0..9";
    }
    // NCS drop default statement
  }

  typedef live_ncs_Timeout {
    description
      "Number of seconds to wait for a response
       from the NETCONF peer before declaring a timeout.
       Zero means no timeout at all.";
    type uint32;
    units "seconds";
    // NCS drop default statement
  }

  typedef live_ncs_Date {
    type string {
      pattern '\d{4}-\d{2}-\d{2}';
    }
    description
      "Represents a specific date in YYYY-MM-DD format.";
  }

  typedef live_ncs_FeatureSpec {
    description
      "Represents a feature specifier, which consists
       of a module-name, colon character ':' and then
       a feature name (e.g., 'foo:bar')";
    type live_ncs_NcxQName;
  }

  typedef live_ncs_TransactionId {
    description
      "Database edit transaction identifier.
       This is not a permanent identifier, and should only
       be used for 'equal or not-equal' comparison tests.
       The value will wrap after the maximum value is reached.";
    type uint64 {
      range "1 .. max";
    }
  }

  typedef int {
    description
      "Changed int base type to int32 for YANG";
    type int32;
  }

  typedef uint {
    description
      "Changed uint base type to uint32 for YANG";
    type uint32;
  }

  typedef long {
    description
      "Changed long base type to int64 for YANG";
    type int64;
  }

  typedef ulong {
    description
      "Changed ulong base type to uint64 for YANG";
    type uint64;
  }

  typedef ustring {
    description
      "Changed ustring base type to binary for YANG";
    type binary;
  }

  typedef NcxName {
    description
      "General Purpose NCX Name string.";
    type string {
      length "1..64";
      pattern '[a-zA-Z_][a-zA-Z0-9\-_\.]{0,63}';
    }
  }

  typedef NcxQName {
    description
      "Qualified Name:
        module-name:NcxName OR owner-name:NcxName.";
    type string {
      length "1..129";
      pattern '(([a-zA-Z_][a-zA-Z0-9\-_\.]{0,63}):)?([a-zA-Z][a-zA-Z0-9\-_\.]{0,63})';
    }
  }

  typedef NcxIdentifier {
    description
      "Union of all the Identifier types.";
    type union {
      type NcxName;
      type NcxQName;
    }
  }

  typedef yang-identifier {
    description
      "YANG identifier string.";
    type string {
      length "1..max";
      pattern '[a-zA-Z_][a-zA-Z0-9\-_\.]*';
    }
  }

  typedef NcxSessionId {
    description
      "NCX Session ID number";
    type uint32 {
      range "1..max";
    }
  }

  typedef NcxLineLength {
    description
      "Requested Maximum Line Length";
    type uint32 {
      range "32..65535";
    }
  }

  typedef NcxDeviceName {
    description
      "NCX Device Name string.";
    type NcxName;
  }

  typedef NcxUserName {
    description
      "NCX User Name string.";
    type NcxName;
  }

  typedef NcxGroupName {
    description
      "NCX Group Name string.";
    type NcxName;
  }

  typedef NcAccessControlType {
    description
      "NCX System access control mode.";
    type enumeration {
      enum "open" {
        description
          "no access control checking enforced";
      }
      enum "loose" {
        description
          "any RPC method in the netconf namespace can
           be invoked;  read-only data allowed for all";
      }
      enum "strict" {
        description
          "RPC entry must be present to invoke
           an RPC method; ncxacl Data entry must be present
           to access any data. (Except for user == 'root'.)";
      }
    }
    default "strict";
  }

  typedef NcxRpcType {
    description
      "NCX RPC Type Classifications";
    type enumeration {
      enum "other";
      enum "config";
      enum "exec";
      enum "monitor";
      enum "debug";
    }
  }

  typedef NcDebugType {
    description
      "NCX Session debug logging control enumeration.
       Each successive value includes all the previous
       messages from lower value enumeration values,
       plus the messages for the specified value.

       off == no logging is done
       write == log write  messages (NOT SUPPORTED IN YUMA)
       dev0 == log developer level 0 messages (NOT SUPPORTED
                 IN YUMA)
       error == log error messages
       warn == log warning messages
       info == log info messages
       dev1    == log developer level 1 messages (NOT SUPPORTED
                  IN YUMA)
       debug  == log debug level 1 messages
       debug2 == log debug level 2 messages
       debug3 == log debug level 3 messages
       debug4 == log debug level 4 messages";
    type enumeration {
      enum "off";
      enum "write";
      enum "dev0";
      enum "error";
      enum "warn";
      enum "info";
      enum "dev1";
      enum "debug";
      enum "debug2";
      enum "debug3";
      enum "debug4";
    }
    default "info";
  }

  typedef NcPortNumber {
    description
      "Transport layer port number.";
    type uint32 {
      range "1 .. 65535";
    }
  }

  typedef NcIndex {
    description
      "Non-negative index value";
    type uint32 {
      range "1..max";
    }
  }

  typedef NcPathList {
    description
      "PATHSPEC formatted string indicating the machine-dependent
       search path for the NCX programs to use.  Parameters
       with this data type can be used to override the
       default search order, and insert special work
       directories in the search path.

       Each component in the string is an absolute or
       relative directory path specification.
       The colon char ':' is used to separate the path strings.
       Whitespace is not allowed in the string at all.

       For example, the following string contains 3 paths
       that would be used in the order given:

       /home/users/testbed1/yang:/home/users/yang:/usr/share/yang";
    type string {
      length "1 .. max";
    }
  }

  typedef NcModuleSpec {
    description
      "A string which specifies a module name, or a filespec
       which represents a module, with an optional revision date.

             If this string represents a filespec,
             containing any path separation characters, and/or
             ending with the '.yang' or '.yin' extension,
             then only that file location will be checked.

             If this string represents a module name, then
             the module search path will be checked for
             a file with the module name and the '.yang'
             or '.yin.' extension.

             If this string contains a module name
             followed by an 'at sign' character (@),
             followed by a revision string (e.g., foo@2010-01-01),
             then that specific version of the module will be used.

             If this string begins with a '~' character,
             then a username is expected to follow or
             a directory separator character.  If it begins
             with a '$' character, then an environment variable
             name is expected to follow.

             ~/some/path ==> <my-home-dir>/some/path

             ~fred/some/path ==> <fred-home-dir>/some/path

             $workdir/some/path ==> <workdir-env-var>/some/path
          ";
    type string {
      length "1 .. 4095";
    }
  }

  typedef NcPathSpec {
    description
      "A string which specifies a directory name.";
    type string {
      length "1 .. 4095";
    }
  }

  typedef IndentType {
    description
      "Requested indent amount.
       Only a limited range of line indent values are allowed.";
    type uint32 {
      range "0..9";
    }
    default "2";
  }

  typedef Timeout {
    description
      "Number of seconds to wait for a response
       from the NETCONF peer before declaring a timeout.
       Zero means no timeout at all.";
    type uint32;
    units "seconds";
    default "30";
  }

  typedef Date {
    type string {
      pattern '\d{4}-\d{2}-\d{2}';
    }
    description
      "Represents a specific date in YYYY-MM-DD format.";
  }

  typedef FeatureSpec {
    description
      "Represents a feature specifier, which consists
       of a module-name, colon character ':' and then
       a feature name (e.g., 'foo:bar')";
    type NcxQName;
  }

  typedef TransactionId {
    description
      "Database edit transaction identifier.
       This is not a permanent identifier, and should only
       be used for 'equal or not-equal' comparison tests.
       The value will wrap after the maximum value is reached.";
    type uint64 {
      range "1 .. max";
    }
  }
}
