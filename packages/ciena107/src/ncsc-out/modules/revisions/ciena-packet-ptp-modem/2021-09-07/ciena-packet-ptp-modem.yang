module ciena-packet-ptp-modem {
  // Generated by yanger -t ncs
  tailf:mount-id "ciena107-nc-1.0:ciena107-nc-1.0";
  tailf:ncs-device-type "netconf";

  namespace "http://www.ciena.com/ns/yang/ciena-packet-ptp-modem";
  prefix ptp-modem;

  import ciena-packet-typedefs {
    prefix cntypes;
  }
  import ciena-packet-ptp {
    prefix ptp;
  }
  import ciena-packet-xcvr {
    prefix xcvr;
  }
  import tailf-common {
    prefix tailf;
  }
  import tailf-ncs {
    prefix ncs;
  }

  organization
    "Ciena Corporation";
  contact
    "Web URL: http://www.ciena.com/
     Postal:  7035 Ridge Road
             Hanover, Maryland 21076
             U.S.A.
     Phone:   +1 800-921-1144
     Fax:     +1 410-694-5750";
  description
    "This module defines modem-transceiver PTP data. It
     augments the ciena-packet-ptp module. The PTP model represents the
     signal carried by the modem transceiver at a physical line port. The PTP
     objects are automatically provisioned during service module installation.";

  revision 2021-09-07 {
    description
      "Adding new container grid-spacing under
       properties/ptp:transmitter.
       Adding must check to block grid-spacing
       config for Wavelogic Ai.";
  }
  revision 2019-11-01 {
    description
      "Adding 250 and 500 values to reach limit";
  }
  revision 2019-03-20 {
    description
      "Enabled PTP properties config for more xcvr types";
  }
  revision 2018-05-17 {
    description
      "Based off of ciena-waveserver-ptp-modem.yang";
  }

  augment "/ncs:devices/ncs:template/ncs:ned-id/ncs:config/ptp:ptps/ptp:ptp/ptp:properties/ptp:transmitter" {
    description
      "PTP transmitter properties";
    container frequency {
      description
        "Tx Frequency attributes.";
      leaf value {
        type cntypes:ncs_template_modem-frequency;
        units "GHz";
        description
          "The configured modem frequency value (GHz). Frequency cannot be
           modified while Admin State is enabled (except when changing from
           zero value to another value).";
      }
      // NCS drop config false leaf 'min-value'
      // NCS drop config false leaf 'max-value'
      // NCS drop config false leaf actual
    }
    container power {
      description
        "Tx Power attributes.";
      leaf value {
        type cntypes:ncs_template_tx-power-lvl;
        units "dBm";
        description
          "The provisioned transmit power in dBm.";
      }
      // NCS drop config false leaf 'min-value'
      // NCS drop config false leaf 'max-value'
      // NCS drop config false leaf actual
    }
    container grid-spacing {
      // NCS drop must statement
      description
        "Tx grid spacing attributes.";
      leaf value {
        type cntypes:ncs_template_grid-spac-enum;
        units "GHz";
        description
          "The configured modem grid spacing value. Default is 50GHz";
      }
    }
  }
  augment "/ncs:devices/ncs:device/ncs:live-status/ptp:ptps/ptp:ptp/ptp:properties/ptp:transmitter" {
    description
      "PTP transmitter properties";
    container frequency {
      tailf:ncs-device-type "netconf";
      tailf:display-when "not(../../../../../../ncs:module) or ../../../../../../ncs:module[ncs:name='ciena-packet-ptp-modem'] or (../../../../../../ncs:live-status-protocol[not(ncs:capability)]) or (../../../../../../ncs:live-status-protocol/ncs:capability/ncs:module[.='ciena-packet-ptp-modem'])";
      description
        "Tx Frequency attributes.";
      leaf value {
        type cntypes:live_ncs_modem-frequency;
        units "GHz";
        description
          "The configured modem frequency value (GHz). Frequency cannot be
           modified while Admin State is enabled (except when changing from
           zero value to another value).";
      }
      leaf min-value {
        type cntypes:live_ncs_modem-frequency;
        units "GHz";
        description
          "The minimum supported frequency value, in GHz.";
      }
      leaf max-value {
        type cntypes:live_ncs_modem-frequency;
        units "GHz";
        description
          "The maximum supported frequency value, in GHz.";
      }
      leaf actual {
        type cntypes:live_ncs_modem-frequency;
        units "GHz";
        description
          "The actual transmitter frequency value applied on the modem (GHz).";
      }
    }
    container power {
      tailf:ncs-device-type "netconf";
      tailf:display-when "not(../../../../../../ncs:module) or ../../../../../../ncs:module[ncs:name='ciena-packet-ptp-modem'] or (../../../../../../ncs:live-status-protocol[not(ncs:capability)]) or (../../../../../../ncs:live-status-protocol/ncs:capability/ncs:module[.='ciena-packet-ptp-modem'])";
      description
        "Tx Power attributes.";
      leaf value {
        type cntypes:live_ncs_tx-power-lvl;
        units "dBm";
        description
          "The provisioned transmit power in dBm.";
      }
      leaf min-value {
        type cntypes:live_ncs_decimal-1-dig;
        units "dBm";
        description
          "The minimum supported tx power value, in dBm.";
      }
      leaf max-value {
        type cntypes:live_ncs_decimal-1-dig;
        units "dBm";
        description
          "The maximum supported tx power value, in dBm.";
      }
      leaf actual {
        type cntypes:live_ncs_tx-power-lvl;
        units "dBm";
        description
          "The actual optical transmit power value, in dBm.";
      }
    }
    container grid-spacing {
      tailf:ncs-device-type "netconf";
      tailf:display-when "not(../../../../../../ncs:module) or ../../../../../../ncs:module[ncs:name='ciena-packet-ptp-modem'] or (../../../../../../ncs:live-status-protocol[not(ncs:capability)]) or (../../../../../../ncs:live-status-protocol/ncs:capability/ncs:module[.='ciena-packet-ptp-modem'])";
      // NCS drop must statement
      description
        "Tx grid spacing attributes.";
      leaf value {
        type cntypes:live_ncs_grid-spac-enum;
        units "GHz";
        description
          "The configured modem grid spacing value. Default is 50GHz";
      }
    }
  }
  augment "/ncs:devices/ncs:device/ncs:config/ptp:ptps/ptp:ptp/ptp:properties/ptp:transmitter" {
    description
      "PTP transmitter properties";
    container frequency {
      tailf:ncs-device-type "netconf";
      tailf:display-when "not(../../../../../../ncs:module) or ../../../../../../ncs:module[ncs:name='ciena-packet-ptp-modem']";
      description
        "Tx Frequency attributes.";
      leaf value {
        type cntypes:modem-frequency;
        units "GHz";
        description
          "The configured modem frequency value (GHz). Frequency cannot be
           modified while Admin State is enabled (except when changing from
           zero value to another value).";
      }
      // NCS drop config false leaf 'min-value'
      // NCS drop config false leaf 'max-value'
      // NCS drop config false leaf actual
    }
    container power {
      tailf:ncs-device-type "netconf";
      tailf:display-when "not(../../../../../../ncs:module) or ../../../../../../ncs:module[ncs:name='ciena-packet-ptp-modem']";
      description
        "Tx Power attributes.";
      leaf value {
        type cntypes:tx-power-lvl;
        units "dBm";
        description
          "The provisioned transmit power in dBm.";
      }
      // NCS drop config false leaf 'min-value'
      // NCS drop config false leaf 'max-value'
      // NCS drop config false leaf actual
    }
    container grid-spacing {
      tailf:ncs-device-type "netconf";
      tailf:display-when "not(../../../../../../ncs:module) or ../../../../../../ncs:module[ncs:name='ciena-packet-ptp-modem']";
      must 'not(../../ptp:xcvr-type)' {
        tailf:xpath-root 3;
        error-message "grid-spacing not supported on Wavelogic Ai ports";
      }
      description
        "Tx grid spacing attributes.";
      leaf value {
        type cntypes:grid-spac-enum;
        units "GHz";
        description
          "The configured modem grid spacing value. Default is 50GHz";
      }
    }
  }
  augment "/ncs:devices/ncs:template/ncs:ned-id/ncs:config/ptp:ptps/ptp:ptp/ptp:properties" {
    description
      "PTP properties specific to PTP modem.";
    container line-system {
      description
        "Line System related attributes.";
      leaf type {
        type cntypes:ncs_template_line-sys-enum;
        description
          "Line system type. Default is coloured";
      }
    }
    container modem {
      description
        "PTP Modem configuration and operational attributes.";
      // NCS drop config false leaf 'baud-rate'
      leaf class {
        type cntypes:ncs_template_modem-class;
        description
          "The modem class type, terrestrial or submarine. Configuration requires
           proper license installed.";
      }
      // NCS drop config false leaf 'far-end-class'
      leaf reach-limit {
        type string;
        units "km";
        description
          "The maximum reach allowed in km. The possible values are [250, 500, 1000, 2000,
           5000] for terrestrial modem class, and [3500, 9000, 14000] for
           submarine modem class. Configuration requires proper license installed.
           [0] if the value is unknown/unavailable or inapplicable.";
      }
      // NCS drop config false leaf 'actual-reach'
      leaf link-optimization-mode {
        type cntypes:ncs_template_link-optimization-mode;
        description
          "Link Optimization Mode. Default is standard.";
      }
      // NCS drop config false leaf 'actual-link-optimization-mode'
      leaf laser-tuning-mode {
        type string;
        description
          "This is the Tuning Mode, which can be set as normal (performance-
           optimized), accelerated, or fast tuning mode. Default is normal.";
      }
      leaf laser-centering-mode {
        type string;
        description
          "This parameter is used to configure which laser centering mode to
           apply to the OTM signal.";
      }
      leaf laser-centering-range {
        type string;
        units "GHz";
        description
          "This parameter is used to configure the laser centering range.";
      }
      leaf laser-shutdown-mode {
        type string;
        description
          "Laser shutdown mode.";
      }
      leaf expected-restoration-time {
        type string;
        units "seconds";
        description
          "Expected link restoration time, in seconds. Prevents the laser from
           dithering for a given period of time after traffic loss in order to
           minimize re-acquisition time. Default is 10 seconds.";
      }
      leaf channel-contention-detection-avoidance {
        type cntypes:ncs_template_enabled-disabled-enum;
        description
          "Enables or disables the channel contention detection and avoidance
           feature. This feature is used to detect the situation where the modem
           port turns on a wavelength (or frequency in Gridless mode) that is in
           use by an existing L0 connection on a colorless network. This feature
           will be triggered by new frequency provisioning and will automatically
           detects if the provisioned frequency is already used. If the
           provisioned frequency is already used, it declares channel contention,
           and then it will hold the Line port TX in a low power state (<-35 dBm)
           and will raise a Channel Contention alarm. This feature will also
           provide a mechanism to allow user to manually release the Line port TX
           from being held in a low power state while the channel collision
           declared.";
      }
      leaf tx-power-reduction-state {
        type cntypes:ncs_template_enabled-disabled-enum;
        description
          "This parameter is used to enable Tx blanking functionality. Default is
           Disabled.";
      }
      leaf tx-dispersion-compensation-mode {
        type string;
        description
          "Tx dispersion compensation management mode.";
      }
      leaf tx-dispersion-precompensation-value {
        type string;
        units "ps/nm";
        description
          "Tx compensation dispersion value, in ps/nm. Default is 0 for automatic
           mode.";
      }
      leaf tx-path-dispersion-value {
        type string;
        units "ps/nm";
        description
          "Tx path dispersion value, in ps/nm.";
      }
      // NCS drop config false leaf 'tx-dispersion-min'
      // NCS drop config false leaf 'tx-dispersion-max'
      // NCS drop config false leaf 'actual-tx-link-dispersion'
      // NCS drop config false leaf 'actual-rx-link-dispersion'
      // NCS drop config false leaf 'actual-tx-precompensation-dispersion'
      // NCS drop config false leaf 'rx-post-compensation-dispersion'
      // NCS drop config false leaf 'estimated-instance-of-differential-group-delay'
      // NCS drop config false leaf 'mean-supported-differential-group-delay'
      // NCS drop config false leaf 'estimated-round-trip-delay'
      // NCS drop config false leaf 'estimated-unidirectional-latency'
      // NCS drop config false leaf 'estimated-fiber-length'
      // NCS drop config false leaf 'allocated-spectral-width'
      // NCS drop config false leaf 'min-spectral-width'
      // NCS drop config false leaf 'supported-3dbm-signal-bandwidth'
      // NCS drop config false leaf 'supported-10dbm-signal-bandwidth'
    }
  }
  augment "/ncs:devices/ncs:device/ncs:live-status/ptp:ptps/ptp:ptp/ptp:properties" {
    description
      "PTP properties specific to PTP modem.";
    container line-system {
      tailf:ncs-device-type "netconf";
      tailf:display-when "not(../../../../../ncs:module) or ../../../../../ncs:module[ncs:name='ciena-packet-ptp-modem'] or (../../../../../ncs:live-status-protocol[not(ncs:capability)]) or (../../../../../ncs:live-status-protocol/ncs:capability/ncs:module[.='ciena-packet-ptp-modem'])";
      description
        "Line System related attributes.";
      leaf type {
        type cntypes:live_ncs_line-sys-enum;
        description
          "Line system type. Default is coloured";
      }
    }
    container modem {
      tailf:ncs-device-type "netconf";
      tailf:display-when "not(../../../../../ncs:module) or ../../../../../ncs:module[ncs:name='ciena-packet-ptp-modem'] or (../../../../../ncs:live-status-protocol[not(ncs:capability)]) or (../../../../../ncs:live-status-protocol/ncs:capability/ncs:module[.='ciena-packet-ptp-modem'])";
      description
        "PTP Modem configuration and operational attributes.";
      leaf baud-rate {
        type uint32;
        units "Gbaud";
        description
          "The baud rate value, based off the mode of the parent XCVR.";
      }
      leaf class {
        type cntypes:live_ncs_modem-class;
        description
          "The modem class type, terrestrial or submarine. Configuration requires
           proper license installed.";
      }
      leaf far-end-class {
        type cntypes:live_ncs_modem-class;
        description
          "The modem class type on the remote end of the line, terrestrial or
           submarine, if available.";
      }
      leaf reach-limit {
        type int16 {
          range "0|250|500|1000|2000|3500|5000|9000|14000";
        }
        units "km";
        description
          "The maximum reach allowed in km. The possible values are [250, 500, 1000, 2000,
           5000] for terrestrial modem class, and [3500, 9000, 14000] for
           submarine modem class. Configuration requires proper license installed.
           [0] if the value is unknown/unavailable or inapplicable.";
      }
      leaf actual-reach {
        type int16;
        units "km";
        description
          "The actual applied reach value, in km. The possible values are [250, 500, 1000,
           2000, 5000] for terrestrial modem class, and [3500, 9000, 14000] for
           submarine modem class. Configuration requires proper license installed.
           [0] if the value is unknown/unavailable or inapplicable.";
      }
      leaf link-optimization-mode {
        type cntypes:live_ncs_link-optimization-mode;
        description
          "Link Optimization Mode. Default is standard.";
      }
      leaf actual-link-optimization-mode {
        type cntypes:live_ncs_link-optimization-mode;
        description
          "Actual Link Optimization mode applied on the modem, if available.";
      }
      leaf laser-tuning-mode {
        type enumeration {
          enum "normal" {
            description
              "Normal (performance-optimized) laser tuning mode.";
          }
          enum "accelerated" {
            description
              "Accelerated laser tuning mode.";
          }
          enum "fast" {
            description
              "Fast laser tuning mode.";
          }
        }
        description
          "This is the Tuning Mode, which can be set as normal (performance-
           optimized), accelerated, or fast tuning mode. Default is normal.";
      }
      leaf laser-centering-mode {
        type enumeration {
          enum "disabled" {
            description
              "Laser centering disabled.";
          }
          enum "enabled" {
            description
              "Laser centering enabled.";
          }
          enum "holdover" {
            description
              "Laser centering in holdover mode.";
          }
        }
        description
          "This parameter is used to configure which laser centering mode to
           apply to the OTM signal.";
      }
      leaf laser-centering-range {
        type decimal64 {
          fraction-digits 1;
          range "0.0 .. 3.0";
        }
        units "GHz";
        description
          "This parameter is used to configure the laser centering range.";
      }
      leaf laser-shutdown-mode {
        type enumeration {
          enum "accelerated" {
            description
              "Laser shutdown accelerated mode.";
          }
          enum "normal" {
            description
              "Laser shutdown normal mode.";
          }
        }
        description
          "Laser shutdown mode.";
      }
      leaf expected-restoration-time {
        type uint32 {
          range "0..255";
        }
        units "seconds";
        description
          "Expected link restoration time, in seconds. Prevents the laser from
           dithering for a given period of time after traffic loss in order to
           minimize re-acquisition time. Default is 10 seconds.";
      }
      leaf channel-contention-detection-avoidance {
        type cntypes:live_ncs_enabled-disabled-enum;
        description
          "Enables or disables the channel contention detection and avoidance
           feature. This feature is used to detect the situation where the modem
           port turns on a wavelength (or frequency in Gridless mode) that is in
           use by an existing L0 connection on a colorless network. This feature
           will be triggered by new frequency provisioning and will automatically
           detects if the provisioned frequency is already used. If the
           provisioned frequency is already used, it declares channel contention,
           and then it will hold the Line port TX in a low power state (<-35 dBm)
           and will raise a Channel Contention alarm. This feature will also
           provide a mechanism to allow user to manually release the Line port TX
           from being held in a low power state while the channel collision
           declared.";
      }
      leaf tx-power-reduction-state {
        type cntypes:live_ncs_enabled-disabled-enum;
        description
          "This parameter is used to enable Tx blanking functionality. Default is
           Disabled.";
      }
      leaf tx-dispersion-compensation-mode {
        type enumeration {
          enum "automatic" {
            description
              "Automatic Tx dispersion compensation management mode. This is the
               default.";
          }
          enum "fixed" {
            description
              "Fixed Tx dispersion compensation management mode.";
          }
          enum "search" {
            description
              "Search Tx dispersion compensation management mode.";
          }
        }
        description
          "Tx dispersion compensation management mode.";
      }
      leaf tx-dispersion-precompensation-value {
        type int32 {
          range "-44500..1200000";
        }
        units "ps/nm";
        description
          "Tx compensation dispersion value, in ps/nm. Default is 0 for automatic
           mode.";
      }
      leaf tx-path-dispersion-value {
        type int32 {
          range "-89000..1244500";
        }
        units "ps/nm";
        description
          "Tx path dispersion value, in ps/nm.";
      }
      leaf tx-dispersion-min {
        type int32;
        units "ps/nm";
        description
          "Tx dispersion minimum value, in ps/nm.";
      }
      leaf tx-dispersion-max {
        type int32;
        units "ps/nm";
        description
          "Tx dispersion maximum value, in ps/nm.";
      }
      leaf actual-tx-link-dispersion {
        type int32;
        units "ps/nm";
        description
          "Total actual Tx link dispersion, in ps/nm.";
      }
      leaf actual-rx-link-dispersion {
        type int32;
        units "ps/nm";
        description
          "Total actual Rx link dispersion, in ps/nm.";
      }
      leaf actual-tx-precompensation-dispersion {
        type int32;
        units "ps/nm";
        description
          "Actual Tx precompensation dispersion value, in ps/nm. This is the
           total link dispersion in the near-to-far direction.";
      }
      leaf rx-post-compensation-dispersion {
        type int32;
        units "ps/nm";
        description
          "Rx post-compensation dispersion, in ps/nm.";
      }
      leaf estimated-instance-of-differential-group-delay {
        type cntypes:live_ncs_decimal-3-dig;
        units "ps";
        description
          "Estimated instance of differential group delay, in picoseconds (ps).";
      }
      leaf mean-supported-differential-group-delay {
        type cntypes:live_ncs_decimal-3-dig;
        units "ps";
        description
          "Mean supported differential group delay, in picoseconds (ps).";
      }
      leaf estimated-round-trip-delay {
        type uint32;
        units "us";
        description
          "Estimated round trip delay, in microseconds (us).";
      }
      leaf estimated-unidirectional-latency {
        type uint32;
        units "us";
        description
          "Estimated unidirectional latency, in microseconds (us).";
      }
      leaf estimated-fiber-length {
        type uint32;
        units "km";
        description
          "Estimated fiber length, in kilometers (km).";
      }
      leaf allocated-spectral-width {
        type cntypes:live_ncs_decimal-1-dig;
        units "GHz";
        description
          "Allocated spectral width, in GHz.";
      }
      leaf min-spectral-width {
        type cntypes:live_ncs_decimal-1-dig;
        units "GHz";
        description
          "Minimum spectral width, in GHz.";
      }
      leaf supported-3dbm-signal-bandwidth {
        type cntypes:live_ncs_decimal-1-dig;
        units "GHz";
        description
          "Supported 3 dBm signal bandwidth, in GHz.";
      }
      leaf supported-10dbm-signal-bandwidth {
        type cntypes:live_ncs_decimal-1-dig;
        units "GHz";
        description
          "Supported 10 dBm signal bandwidth, in GHz.";
      }
    }
  }
  augment "/ncs:devices/ncs:device/ncs:config/ptp:ptps/ptp:ptp/ptp:properties" {
    description
      "PTP properties specific to PTP modem.";
    container line-system {
      tailf:ncs-device-type "netconf";
      tailf:display-when "not(../../../../../ncs:module) or ../../../../../ncs:module[ncs:name='ciena-packet-ptp-modem']";
      description
        "Line System related attributes.";
      leaf type {
        type cntypes:line-sys-enum;
        description
          "Line system type. Default is coloured";
      }
    }
    container modem {
      tailf:ncs-device-type "netconf";
      tailf:display-when "not(../../../../../ncs:module) or ../../../../../ncs:module[ncs:name='ciena-packet-ptp-modem']";
      description
        "PTP Modem configuration and operational attributes.";
      // NCS drop config false leaf 'baud-rate'
      leaf class {
        type cntypes:modem-class;
        description
          "The modem class type, terrestrial or submarine. Configuration requires
           proper license installed.";
      }
      // NCS drop config false leaf 'far-end-class'
      leaf reach-limit {
        type int16 {
          range "0|250|500|1000|2000|3500|5000|9000|14000";
        }
        units "km";
        description
          "The maximum reach allowed in km. The possible values are [250, 500, 1000, 2000,
           5000] for terrestrial modem class, and [3500, 9000, 14000] for
           submarine modem class. Configuration requires proper license installed.
           [0] if the value is unknown/unavailable or inapplicable.";
      }
      // NCS drop config false leaf 'actual-reach'
      leaf link-optimization-mode {
        type cntypes:link-optimization-mode;
        description
          "Link Optimization Mode. Default is standard.";
      }
      // NCS drop config false leaf 'actual-link-optimization-mode'
      leaf laser-tuning-mode {
        type enumeration {
          enum "normal" {
            description
              "Normal (performance-optimized) laser tuning mode.";
          }
          enum "accelerated" {
            description
              "Accelerated laser tuning mode.";
          }
          enum "fast" {
            description
              "Fast laser tuning mode.";
          }
        }
        description
          "This is the Tuning Mode, which can be set as normal (performance-
           optimized), accelerated, or fast tuning mode. Default is normal.";
      }
      leaf laser-centering-mode {
        type enumeration {
          enum "disabled" {
            description
              "Laser centering disabled.";
          }
          enum "enabled" {
            description
              "Laser centering enabled.";
          }
          enum "holdover" {
            description
              "Laser centering in holdover mode.";
          }
        }
        description
          "This parameter is used to configure which laser centering mode to
           apply to the OTM signal.";
      }
      leaf laser-centering-range {
        type decimal64 {
          fraction-digits 1;
          range "0.0 .. 3.0";
        }
        units "GHz";
        description
          "This parameter is used to configure the laser centering range.";
      }
      leaf laser-shutdown-mode {
        type enumeration {
          enum "accelerated" {
            description
              "Laser shutdown accelerated mode.";
          }
          enum "normal" {
            description
              "Laser shutdown normal mode.";
          }
        }
        description
          "Laser shutdown mode.";
      }
      leaf expected-restoration-time {
        type uint32 {
          range "0..255";
        }
        units "seconds";
        description
          "Expected link restoration time, in seconds. Prevents the laser from
           dithering for a given period of time after traffic loss in order to
           minimize re-acquisition time. Default is 10 seconds.";
      }
      leaf channel-contention-detection-avoidance {
        type cntypes:enabled-disabled-enum;
        description
          "Enables or disables the channel contention detection and avoidance
           feature. This feature is used to detect the situation where the modem
           port turns on a wavelength (or frequency in Gridless mode) that is in
           use by an existing L0 connection on a colorless network. This feature
           will be triggered by new frequency provisioning and will automatically
           detects if the provisioned frequency is already used. If the
           provisioned frequency is already used, it declares channel contention,
           and then it will hold the Line port TX in a low power state (<-35 dBm)
           and will raise a Channel Contention alarm. This feature will also
           provide a mechanism to allow user to manually release the Line port TX
           from being held in a low power state while the channel collision
           declared.";
      }
      leaf tx-power-reduction-state {
        type cntypes:enabled-disabled-enum;
        description
          "This parameter is used to enable Tx blanking functionality. Default is
           Disabled.";
      }
      leaf tx-dispersion-compensation-mode {
        type enumeration {
          enum "automatic" {
            description
              "Automatic Tx dispersion compensation management mode. This is the
               default.";
          }
          enum "fixed" {
            description
              "Fixed Tx dispersion compensation management mode.";
          }
          enum "search" {
            description
              "Search Tx dispersion compensation management mode.";
          }
        }
        description
          "Tx dispersion compensation management mode.";
      }
      leaf tx-dispersion-precompensation-value {
        type int32 {
          range "-44500..1200000";
        }
        units "ps/nm";
        description
          "Tx compensation dispersion value, in ps/nm. Default is 0 for automatic
           mode.";
      }
      leaf tx-path-dispersion-value {
        type int32 {
          range "-89000..1244500";
        }
        units "ps/nm";
        description
          "Tx path dispersion value, in ps/nm.";
      }
      // NCS drop config false leaf 'tx-dispersion-min'
      // NCS drop config false leaf 'tx-dispersion-max'
      // NCS drop config false leaf 'actual-tx-link-dispersion'
      // NCS drop config false leaf 'actual-rx-link-dispersion'
      // NCS drop config false leaf 'actual-tx-precompensation-dispersion'
      // NCS drop config false leaf 'rx-post-compensation-dispersion'
      // NCS drop config false leaf 'estimated-instance-of-differential-group-delay'
      // NCS drop config false leaf 'mean-supported-differential-group-delay'
      // NCS drop config false leaf 'estimated-round-trip-delay'
      // NCS drop config false leaf 'estimated-unidirectional-latency'
      // NCS drop config false leaf 'estimated-fiber-length'
      // NCS drop config false leaf 'allocated-spectral-width'
      // NCS drop config false leaf 'min-spectral-width'
      // NCS drop config false leaf 'supported-3dbm-signal-bandwidth'
      // NCS drop config false leaf 'supported-10dbm-signal-bandwidth'
    }
  }
  augment "/ncs:devices/ncs:device/ncs:live-status/ptp:ptps/ptp:ptp/ptp:properties/ptp:lanes/ptp:lane/ptp:rx/ptp:power" {
    description
      "PTP Rx power properties specific to PTP modem.";
    container optical-channel-power {
      tailf:ncs-device-type "netconf";
      tailf:display-when "not(../../../../../../../../../ncs:module) or ../../../../../../../../../ncs:module[ncs:name='ciena-packet-ptp-modem'] or (../../../../../../../../../ncs:live-status-protocol[not(ncs:capability)]) or (../../../../../../../../../ncs:live-status-protocol/ncs:capability/ncs:module[.='ciena-packet-ptp-modem'])";
      description
        "The actual Rx power attributes for the channel to which the receiver is tuned.";
      uses xcvr:live_ncs_optical-power-group;
    }
  }
  augment "/ncs:devices/ncs:device/ncs:live-status/ptp:ptps/ptp:ptp/ptp:properties/ptp:lanes/ptp:lane/ptp:rx/ptp:status" {
    description
      "PTP Rx status properties specific to PTP modem.";
    container optical-channel-power {
      tailf:ncs-device-type "netconf";
      tailf:display-when "not(../../../../../../../../../ncs:module) or ../../../../../../../../../ncs:module[ncs:name='ciena-packet-ptp-modem'] or (../../../../../../../../../ncs:live-status-protocol[not(ncs:capability)]) or (../../../../../../../../../ncs:live-status-protocol/ncs:capability/ncs:module[.='ciena-packet-ptp-modem'])";
      description
        "Optical Channel Rx Power high/low alarm/warning status/thresholds,
         where applicable for the XCVR type.";
      uses xcvr:live_ncs_optical-power-status-group;
      uses xcvr:live_ncs_optical-power-threshold-group;
      leaf loss-of-signal {
        type boolean;
        description
          "Rx Loss of Optical Channel.";
      }
    }
  }
}
