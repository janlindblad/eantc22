module ciena-pkix-transfer {
  // Generated by yanger -t ncs
  tailf:mount-id "ciena107-nc-1.0:ciena107-nc-1.0";
  tailf:ncs-device-type "netconf";

  namespace "http://www.ciena.com/ns/yang/ciena-pkix-transfer";
  prefix pkix-transfer;

  import ciena-pkix-types {
    prefix pkix-types;
  }
  import ciena-tls-service-profile {
    prefix ciena-tls-service-profile;
  }
  import tailf-common {
    prefix tailf;
  }
  import tailf-ncs {
    prefix ncs;
  }

  organization
    "Ciena Corporation";
  contact
    "Web URL: http://www.ciena.com/
     E-mail:  yang@ciena.com
     Postal:  7035 Ridge Road
              Hanover, Maryland 21076
              U.S.A.
     Phone:   +1 800-921-1144
     Fax:     +1 410-694-5750";
  description
    "This YANG module defines the nodes for Public Key Infrastructure
     (PKI) Security Certificates CA (Certificate Authority) and CRL
     (Certificate Revocation List) for the NETCONF protocol.

     Copyright (c) 2016-2017 Ciena Corporation.  All rights reserved.

     All information contained herein is, and remains the property of
     Ciena Corporation. Dissemination of this information or
     reproduction of this material is strictly forbidden unless prior
     written permission is obtained from Ciena Corporation.";

  revision 2020-12-03 {
    description
      "Added range for cert name lengths";
    reference "No specific reference; standard not available.";
  }
  revision 2018-05-01 {
    description
      "Initial version";
    reference
      "RFC 6020: YANG - A Data Modeling Language for
       the Network Configuration Protocol (NETCONF).
       No specific reference; standard not available.";
  }

  augment "/ncs:devices/ncs:device/ncs:rpc" {
    container rpc-pkix-crl-uninstall {
      tailf:ncs-device-type "netconf";
      tailf:display-when "not(../../ncs:module) or ../../ncs:module[ncs:name='ciena-pkix-transfer']";
      tailf:action pkix-crl-uninstall {
        tailf:actionpoint ncsproxy {
          tailf:internal;
        }
        description
          "Uninstall a CRL.";
        input {
          leaf crl-name {
            type string;
            mandatory true;
            description
              "The name identifying a particular CRL.";
          }
        }
      }
    }
  }
  augment "/ncs:devices/ncs:device-group/ncs:ned-id/ncs:rpc" {
    container rpc-pkix-crl-uninstall {
      tailf:ncs-device-type "netconf";
      tailf:display-when "/ncs:devices/ncs:device[ncs:name=current()/../../../ncs:member]/ncs:module[ncs:name='ciena-pkix-transfer']";
      tailf:action pkix-crl-uninstall {
        tailf:actionpoint ncsproxy {
          tailf:internal;
        }
        description
          "Uninstall a CRL.";
        input {
          leaf crl-name {
            type string;
            mandatory true;
            description
              "The name identifying a particular CRL.";
          }
        }
      }
    }
  }
  augment "/ncs:devices/ncs:device/ncs:rpc" {
    container rpc-pkix-crl-install {
      tailf:ncs-device-type "netconf";
      tailf:display-when "not(../../ncs:module) or ../../ncs:module[ncs:name='ciena-pkix-transfer']";
      tailf:action pkix-crl-install {
        tailf:actionpoint ncsproxy {
          tailf:internal;
        }
        description
          "Install a CRL.";
        input {
          leaf crl-cert-name {
            type string {
              length "1..255";
            }
            description
              "The user defined name identifying a particular CRL.";
          }
          leaf tls-service-profile {
            type string;
            description
              "The TLS Service Profile to be used when accepting
               TLS connections.";
          }
          uses pkix-types:ncs_rpc_notif_pkix-file-transfer-parameters;
        }
      }
    }
  }
  augment "/ncs:devices/ncs:device-group/ncs:ned-id/ncs:rpc" {
    container rpc-pkix-crl-install {
      tailf:ncs-device-type "netconf";
      tailf:display-when "/ncs:devices/ncs:device[ncs:name=current()/../../../ncs:member]/ncs:module[ncs:name='ciena-pkix-transfer']";
      tailf:action pkix-crl-install {
        tailf:actionpoint ncsproxy {
          tailf:internal;
        }
        description
          "Install a CRL.";
        input {
          leaf crl-cert-name {
            type string {
              length "1..255";
            }
            description
              "The user defined name identifying a particular CRL.";
          }
          leaf tls-service-profile {
            type string;
            description
              "The TLS Service Profile to be used when accepting
               TLS connections.";
          }
          uses pkix-types:ncs_rpc_notif_pkix-file-transfer-parameters;
        }
      }
    }
  }
  augment "/ncs:devices/ncs:device/ncs:rpc" {
    container rpc-pkix-certificates-uninstall {
      tailf:ncs-device-type "netconf";
      tailf:display-when "not(../../ncs:module) or ../../ncs:module[ncs:name='ciena-pkix-transfer']";
      tailf:action pkix-certificates-uninstall {
        tailf:actionpoint ncsproxy {
          tailf:internal;
        }
        description
          "Uninstall a device  certificate.";
        input {
          leaf cert-name {
            type string;
            mandatory true;
            description
              "The certificate name.";
          }
        }
      }
    }
  }
  augment "/ncs:devices/ncs:device-group/ncs:ned-id/ncs:rpc" {
    container rpc-pkix-certificates-uninstall {
      tailf:ncs-device-type "netconf";
      tailf:display-when "/ncs:devices/ncs:device[ncs:name=current()/../../../ncs:member]/ncs:module[ncs:name='ciena-pkix-transfer']";
      tailf:action pkix-certificates-uninstall {
        tailf:actionpoint ncsproxy {
          tailf:internal;
        }
        description
          "Uninstall a device  certificate.";
        input {
          leaf cert-name {
            type string;
            mandatory true;
            description
              "The certificate name.";
          }
        }
      }
    }
  }
  augment "/ncs:devices/ncs:device/ncs:rpc" {
    container rpc-pkix-certificates-install {
      tailf:ncs-device-type "netconf";
      tailf:display-when "not(../../ncs:module) or ../../ncs:module[ncs:name='ciena-pkix-transfer']";
      tailf:action pkix-certificates-install {
        tailf:actionpoint ncsproxy {
          tailf:internal;
        }
        description
          "Install a device certificate.";
        input {
          leaf cert-name {
            type string {
              length "1..255";
            }
            description
              "The certificate name.";
          }
          leaf cert-passphrase {
            type string;
            description
              "The passphrase for the certificate.";
          }
          leaf cert-only {
            type boolean;
            description
              "Only install the certificate.";
          }
          leaf tls-service-profile {
            type string;
            description
              "The TLS Service Profile to be used when accepting
               TLS connections.";
          }
          uses pkix-types:ncs_rpc_notif_pkix-file-transfer-parameters;
        }
      }
    }
  }
  augment "/ncs:devices/ncs:device-group/ncs:ned-id/ncs:rpc" {
    container rpc-pkix-certificates-install {
      tailf:ncs-device-type "netconf";
      tailf:display-when "/ncs:devices/ncs:device[ncs:name=current()/../../../ncs:member]/ncs:module[ncs:name='ciena-pkix-transfer']";
      tailf:action pkix-certificates-install {
        tailf:actionpoint ncsproxy {
          tailf:internal;
        }
        description
          "Install a device certificate.";
        input {
          leaf cert-name {
            type string {
              length "1..255";
            }
            description
              "The certificate name.";
          }
          leaf cert-passphrase {
            type string;
            description
              "The passphrase for the certificate.";
          }
          leaf cert-only {
            type boolean;
            description
              "Only install the certificate.";
          }
          leaf tls-service-profile {
            type string;
            description
              "The TLS Service Profile to be used when accepting
               TLS connections.";
          }
          uses pkix-types:ncs_rpc_notif_pkix-file-transfer-parameters;
        }
      }
    }
  }
  augment "/ncs:devices/ncs:device/ncs:rpc" {
    container rpc-pkix-certificates-csr-generate {
      tailf:ncs-device-type "netconf";
      tailf:display-when "not(../../ncs:module) or ../../ncs:module[ncs:name='ciena-pkix-transfer']";
      tailf:action pkix-certificates-csr-generate {
        tailf:actionpoint ncsproxy {
          tailf:internal;
        }
        description
          "Generate a certificate signing request.";
        input {
          leaf cert-name {
            type string;
            description
              "The certificate name.";
          }
          leaf algorithm-identifier {
            type identityref {
              base pkix-types:key-algorithm;
            }
            description
              "Identifies which algorithm is to be used to generate the
               key.  Also referred to within SAOS as key-type.";
          }
          leaf cert-passphrase {
            type string;
            description
              "The passphrase for the certificate.";
          }
          leaf tls-service-profile {
            type string;
            description
              "The TLS Service Profile to be used when accepting
               TLS connections.";
          }
          uses pkix-types:ncs_rpc_notif_pkix-file-transfer-parameters;
        }
      }
    }
  }
  augment "/ncs:devices/ncs:device-group/ncs:ned-id/ncs:rpc" {
    container rpc-pkix-certificates-csr-generate {
      tailf:ncs-device-type "netconf";
      tailf:display-when "/ncs:devices/ncs:device[ncs:name=current()/../../../ncs:member]/ncs:module[ncs:name='ciena-pkix-transfer']";
      tailf:action pkix-certificates-csr-generate {
        tailf:actionpoint ncsproxy {
          tailf:internal;
        }
        description
          "Generate a certificate signing request.";
        input {
          leaf cert-name {
            type string;
            description
              "The certificate name.";
          }
          leaf algorithm-identifier {
            type identityref {
              base pkix-types:key-algorithm;
            }
            description
              "Identifies which algorithm is to be used to generate the
               key.  Also referred to within SAOS as key-type.";
          }
          leaf cert-passphrase {
            type string;
            description
              "The passphrase for the certificate.";
          }
          leaf tls-service-profile {
            type string;
            description
              "The TLS Service Profile to be used when accepting
               TLS connections.";
          }
          uses pkix-types:ncs_rpc_notif_pkix-file-transfer-parameters;
        }
      }
    }
  }
  augment "/ncs:devices/ncs:device/ncs:rpc" {
    container rpc-pkix-ca-uninstall {
      tailf:ncs-device-type "netconf";
      tailf:display-when "not(../../ncs:module) or ../../ncs:module[ncs:name='ciena-pkix-transfer']";
      tailf:action pkix-ca-uninstall {
        tailf:actionpoint ncsproxy {
          tailf:internal;
        }
        description
          "Uninstall a CA certificate.";
        input {
          leaf ca-cert-name {
            type string;
            mandatory true;
            description
              "The name identifying a particular CA certificate.";
          }
        }
      }
    }
  }
  augment "/ncs:devices/ncs:device-group/ncs:ned-id/ncs:rpc" {
    container rpc-pkix-ca-uninstall {
      tailf:ncs-device-type "netconf";
      tailf:display-when "/ncs:devices/ncs:device[ncs:name=current()/../../../ncs:member]/ncs:module[ncs:name='ciena-pkix-transfer']";
      tailf:action pkix-ca-uninstall {
        tailf:actionpoint ncsproxy {
          tailf:internal;
        }
        description
          "Uninstall a CA certificate.";
        input {
          leaf ca-cert-name {
            type string;
            mandatory true;
            description
              "The name identifying a particular CA certificate.";
          }
        }
      }
    }
  }
  augment "/ncs:devices/ncs:device/ncs:rpc" {
    container rpc-pkix-ca-install {
      tailf:ncs-device-type "netconf";
      tailf:display-when "not(../../ncs:module) or ../../ncs:module[ncs:name='ciena-pkix-transfer']";
      tailf:action pkix-ca-install {
        tailf:actionpoint ncsproxy {
          tailf:internal;
        }
        description
          "Install a CA certificate.";
        input {
          leaf ca-cert-name {
            type string {
              length "1..255";
            }
            description
              "The user defined name identifying
               a particular CA certificate.";
          }
          leaf tls-service-profile {
            type string;
            description
              "The TLS Service Profile to be used when accepting
               TLS connections.";
          }
          uses pkix-types:ncs_rpc_notif_pkix-file-transfer-parameters;
        }
      }
    }
  }
  augment "/ncs:devices/ncs:device-group/ncs:ned-id/ncs:rpc" {
    container rpc-pkix-ca-install {
      tailf:ncs-device-type "netconf";
      tailf:display-when "/ncs:devices/ncs:device[ncs:name=current()/../../../ncs:member]/ncs:module[ncs:name='ciena-pkix-transfer']";
      tailf:action pkix-ca-install {
        tailf:actionpoint ncsproxy {
          tailf:internal;
        }
        description
          "Install a CA certificate.";
        input {
          leaf ca-cert-name {
            type string {
              length "1..255";
            }
            description
              "The user defined name identifying
               a particular CA certificate.";
          }
          leaf tls-service-profile {
            type string;
            description
              "The TLS Service Profile to be used when accepting
               TLS connections.";
          }
          uses pkix-types:ncs_rpc_notif_pkix-file-transfer-parameters;
        }
      }
    }
  }
}
