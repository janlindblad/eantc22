module iana-bfd-types {
  // Generated by yanger -t ncs
  tailf:mount-id "ciena107-nc-1.0:ciena107-nc-1.0";
  tailf:ncs-device-type "netconf";

  yang-version 1.1;
  namespace "urn:ietf:params:xml:ns:yang:iana-bfd-types";
  prefix iana-bfd-types;

  import tailf-common {
    prefix tailf;
  }
  import tailf-ncs {
    prefix ncs;
  }

  organization
    "IANA";
  contact
    "        Internet Assigned Numbers Authority

     Postal: ICANN
            12025 Waterfront Drive, Suite 300
            Los Angeles, CA 90094-2536
            United States of America

     Tel:    +1 310 823 9358
     <mailto:iana@iana.org>";
  description
    "This module defines YANG data types for IANA-registered
     BFD parameters.

     This YANG module is maintained by IANA and reflects the
     'BFD Diagnostic Codes' and 'BFD Authentication Types' registries.

     Copyright (c) 2018 IETF Trust and the persons
     identified as authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";
  reference "RFC XXXX";

  revision 2018-08-01 {
    description
      "Initial revision.";
    reference "RFC XXXX: IANA BFD YANG Data Types.";
  }

  typedef ncs_template_diagnostic {
    type string;
    description
      "BFD diagnostic as defined in RFC 5880, values are maintained in
       the 'BFD Diagnostic Codes' IANA registry. Range is 0 to 31.";
  }

  typedef ncs_template_auth-type {
    type string;
    description
      "BFD authentication type as defined in RFC 5880, values are
       maintained in the 'BFD Authentication Types' IANA registry.
       Range is 0 to 255.";
  }

  typedef ncs_rpc_notif_diagnostic {
    type enumeration {
      enum "none" {
        value 0;
        description
          "None";
      }
      enum "control-expiry" {
        value 1;
        description
          "Control timer expiry";
      }
      enum "echo-failed" {
        value 2;
        description
          "Echo failure";
      }
      enum "neighbor-down" {
        value 3;
        description
          "Neighbor down";
      }
      enum "forwarding-reset" {
        value 4;
        description
          "Forwarding reset";
      }
      enum "path-down" {
        value 5;
        description
          "Path down";
      }
      enum "concatenated-path-down" {
        value 6;
        description
          "Concatenated path down";
      }
      enum "admin-down" {
        value 7;
        description
          "Admin down";
      }
      enum "reverse-concatenated-path-down" {
        value 8;
        description
          "Reverse concatenated path down";
      }
      enum "mis-connectivity-defect" {
        value 9;
        description
          "Mis-connectivity defect as specified in RFC6428";
      }
    }
    description
      "BFD diagnostic as defined in RFC 5880, values are maintained in
       the 'BFD Diagnostic Codes' IANA registry. Range is 0 to 31.";
  }

  typedef ncs_rpc_notif_auth-type {
    type enumeration {
      enum "reserved" {
        value 0;
        description
          "Reserved";
      }
      enum "simple-password" {
        value 1;
        description
          "Simple password";
      }
      enum "keyed-md5" {
        value 2;
        description
          "Keyed MD5";
      }
      enum "meticulous-keyed-md5" {
        value 3;
        description
          "Meticulous keyed MD5";
      }
      enum "keyed-sha1" {
        value 4;
        description
          "Keyed SHA1";
      }
      enum "meticulous-keyed-sha1" {
        value 5;
        description
          "Meticulous keyed SHA1";
      }
    }
    description
      "BFD authentication type as defined in RFC 5880, values are
       maintained in the 'BFD Authentication Types' IANA registry.
       Range is 0 to 255.";
  }

  typedef live_ncs_diagnostic {
    type enumeration {
      enum "none" {
        value 0;
        description
          "None";
      }
      enum "control-expiry" {
        value 1;
        description
          "Control timer expiry";
      }
      enum "echo-failed" {
        value 2;
        description
          "Echo failure";
      }
      enum "neighbor-down" {
        value 3;
        description
          "Neighbor down";
      }
      enum "forwarding-reset" {
        value 4;
        description
          "Forwarding reset";
      }
      enum "path-down" {
        value 5;
        description
          "Path down";
      }
      enum "concatenated-path-down" {
        value 6;
        description
          "Concatenated path down";
      }
      enum "admin-down" {
        value 7;
        description
          "Admin down";
      }
      enum "reverse-concatenated-path-down" {
        value 8;
        description
          "Reverse concatenated path down";
      }
      enum "mis-connectivity-defect" {
        value 9;
        description
          "Mis-connectivity defect as specified in RFC6428";
      }
    }
    description
      "BFD diagnostic as defined in RFC 5880, values are maintained in
       the 'BFD Diagnostic Codes' IANA registry. Range is 0 to 31.";
  }

  typedef live_ncs_auth-type {
    type enumeration {
      enum "reserved" {
        value 0;
        description
          "Reserved";
      }
      enum "simple-password" {
        value 1;
        description
          "Simple password";
      }
      enum "keyed-md5" {
        value 2;
        description
          "Keyed MD5";
      }
      enum "meticulous-keyed-md5" {
        value 3;
        description
          "Meticulous keyed MD5";
      }
      enum "keyed-sha1" {
        value 4;
        description
          "Keyed SHA1";
      }
      enum "meticulous-keyed-sha1" {
        value 5;
        description
          "Meticulous keyed SHA1";
      }
    }
    description
      "BFD authentication type as defined in RFC 5880, values are
       maintained in the 'BFD Authentication Types' IANA registry.
       Range is 0 to 255.";
  }

  typedef diagnostic {
    type enumeration {
      enum "none" {
        value 0;
        description
          "None";
      }
      enum "control-expiry" {
        value 1;
        description
          "Control timer expiry";
      }
      enum "echo-failed" {
        value 2;
        description
          "Echo failure";
      }
      enum "neighbor-down" {
        value 3;
        description
          "Neighbor down";
      }
      enum "forwarding-reset" {
        value 4;
        description
          "Forwarding reset";
      }
      enum "path-down" {
        value 5;
        description
          "Path down";
      }
      enum "concatenated-path-down" {
        value 6;
        description
          "Concatenated path down";
      }
      enum "admin-down" {
        value 7;
        description
          "Admin down";
      }
      enum "reverse-concatenated-path-down" {
        value 8;
        description
          "Reverse concatenated path down";
      }
      enum "mis-connectivity-defect" {
        value 9;
        description
          "Mis-connectivity defect as specified in RFC6428";
      }
    }
    description
      "BFD diagnostic as defined in RFC 5880, values are maintained in
       the 'BFD Diagnostic Codes' IANA registry. Range is 0 to 31.";
  }

  typedef auth-type {
    type enumeration {
      enum "reserved" {
        value 0;
        description
          "Reserved";
      }
      enum "simple-password" {
        value 1;
        description
          "Simple password";
      }
      enum "keyed-md5" {
        value 2;
        description
          "Keyed MD5";
      }
      enum "meticulous-keyed-md5" {
        value 3;
        description
          "Meticulous keyed MD5";
      }
      enum "keyed-sha1" {
        value 4;
        description
          "Keyed SHA1";
      }
      enum "meticulous-keyed-sha1" {
        value 5;
        description
          "Meticulous keyed SHA1";
      }
    }
    description
      "BFD authentication type as defined in RFC 5880, values are
       maintained in the 'BFD Authentication Types' IANA registry.
       Range is 0 to 255.";
  }
}
