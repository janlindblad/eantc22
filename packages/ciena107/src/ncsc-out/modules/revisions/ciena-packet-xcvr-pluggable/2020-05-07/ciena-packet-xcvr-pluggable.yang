module ciena-packet-xcvr-pluggable {
  // Generated by yanger -t ncs
  tailf:mount-id "ciena107-nc-1.0:ciena107-nc-1.0";
  tailf:ncs-device-type "netconf";

  namespace "http://www.ciena.com/ns/yang/ciena-xcvr-pluggable";
  prefix xcvr-pluggable;

  import ciena-packet-typedefs {
    prefix cntypes;
  }
  import ciena-packet-xcvr {
    prefix xcvr;
  }
  import tailf-common {
    prefix tailf;
  }
  import tailf-ncs {
    prefix ncs;
  }

  organization
    "Ciena Corporation";
  contact
    "Web URL: http://www.ciena.com/
     Postal:  7035 Ridge Road
             Hanover, Maryland 21076
             U.S.A.
     Phone:   +1 800-921-1144
     Fax:     +1 410-694-5750";
  description
    "This YANG module defines Ciena's XCVR common pluggable specific data for the NETCONF protocol. It will augment the ciena-packet-xcvr module.";

  revision 2020-05-07 {
    description
      "Added bit Spec-Compliance-10GBASE-ER to specification-compliance";
  }
  revision 2019-10-31 {
    description
      "Added firmware-version leaf along with new values to identifier enum";
  }
  revision 2019-10-07 {
    description
      "Changed xcvr-event to xcvr-events in notification augment";
  }
  revision 2019-09-09 {
    description
      "Changed notification augment xcvrEvent to xcvr-event";
  }
  revision 2018-05-17 {
    description
      "Based off of ciena-waveserver-xcvr-pluggable.yang";
  }

  augment "/ncs:devices/ncs:device/ncs:live-status/xcvr:xcvrs/xcvr:xcvr/xcvr:properties/xcvr:vendor-data/xcvr:id/xcvr:vendor-id" {
    // NCS drop when statement
    description
      "XCVR vendor-id properties specific to pluggable XCVRs.";
    leaf revision-compliance {
      tailf:ncs-device-type "netconf";
      tailf:display-when "not(../../../../../../../../ncs:module) or ../../../../../../../../ncs:module[ncs:name='ciena-packet-xcvr-pluggable'] or (../../../../../../../../ncs:live-status-protocol[not(ncs:capability)]) or (../../../../../../../../ncs:live-status-protocol/ncs:capability/ncs:module[.='ciena-packet-xcvr-pluggable'])";
      type enumeration {
        enum "not-specified" {
          description
            "Revision compliance not specified.";
        }
        enum "RV4.7" {
          description
            "Revision compliance RV4.7.";
        }
        enum "RV4.7-2h" {
          description
            "Revision compliance RV4.7-2h.";
        }
        enum "RV1.3" {
          description
            "Revision compliance RV1.3.";
        }
        enum "RV1.4" {
          description
            "Revision compliance RV1.4.";
        }
        enum "RV1.5" {
          description
            "Revision compliance RV1.5.";
        }
        enum "RV2.0" {
          description
            "Revision compliance RV2.0.";
        }
        enum "RV2.0 and 2.6 and 2.7" {
          description
            "Revision compliance RV2.0 and 2.6 and 2.7.";
        }
      }
      description
        "Revision Compliance flags, as defined in documentation for Common Management Interface, SFF-8636, table 6-3.";
    }
    leaf-list vendor-oui {
      tailf:ncs-device-type "netconf";
      tailf:display-when "not(../../../../../../../../ncs:module) or ../../../../../../../../ncs:module[ncs:name='ciena-packet-xcvr-pluggable'] or (../../../../../../../../ncs:live-status-protocol[not(ncs:capability)]) or (../../../../../../../../ncs:live-status-protocol/ncs:capability/ncs:module[.='ciena-packet-xcvr-pluggable'])";
      type uint8;
      // NCS drop max-elements statement
      ordered-by system;
      description
        "Free side device vendor IEEE company ID. Defined in Common Management Interface, SFF-8636, table 6-15. 3 bytes of data.";
    }
  }
  augment "/ncs:devices/ncs:device/ncs:live-status/xcvr:xcvrs/xcvr:xcvr/xcvr:properties/xcvr:vendor-data/xcvr:properties/xcvr:device-id" {
    // NCS drop when statement
    description
      "XCVR device-id properties specific to pluggable XCVRs.";
    leaf identifier {
      tailf:ncs-device-type "netconf";
      tailf:display-when "not(../../../../../../../../ncs:module) or ../../../../../../../../ncs:module[ncs:name='ciena-packet-xcvr-pluggable'] or (../../../../../../../../ncs:live-status-protocol[not(ncs:capability)]) or (../../../../../../../../ncs:live-status-protocol/ncs:capability/ncs:module[.='ciena-packet-xcvr-pluggable'])";
      type enumeration {
        enum "Unknown or unspecified" {
          value 0;
          description
            "Identifier value 0x00, Unknown or unspecified.";
        }
        enum "GBIC" {
          value 1;
          description
            "Identifier value 0x01, GBIC.";
        }
        enum "Module/connector soldered to motherboard" {
          value 2;
          description
            "Identifier value 0x02, Module/connector soldered to motherboard.";
        }
        enum "SFP/SFP+/SFP28" {
          value 3;
          description
            "Identifier value 0x03, SFP/SFP+/SFP28.";
        }
        enum "300 pin XBI" {
          value 4;
          description
            "Identifier value 0x04, 300 pin XBI.";
        }
        enum "XENPAK" {
          value 5;
          description
            "Identifier value 0x05, XENPAK.";
        }
        enum "XFP" {
          value 6;
          description
            "Identifier value 0x06, XFP.";
        }
        enum "XFF" {
          value 7;
          description
            "Identifier value 0x07, XFF.";
        }
        enum "XFP-E" {
          value 8;
          description
            "Identifier value 0x08, XFP-E.";
        }
        enum "XPAK" {
          value 9;
          description
            "Identifier value 0x09, XPAK.";
        }
        enum "X2" {
          value 10;
          description
            "Identifier value 0x0A, X2.";
        }
        enum "DWDM-SFP/SFP+" {
          value 11;
          description
            "Identifier value 0x0B, DWDM-SFP/SFP+.";
        }
        enum "QSFP INF-8438" {
          value 12;
          description
            "Identifier value 0x0C, QSFP (INF-8438).";
        }
        enum "QSFP+ SFF-8436" {
          value 13;
          description
            "Identifier value 0x0D, QSFP+ (SFF-8436) or later.";
        }
        enum "CXP" {
          value 14;
          description
            "Identifier value 0x0E, CXP or later.";
        }
        enum "Shielded Mini Multilane HD 4X" {
          value 15;
          description
            "Identifier value 0x0F, Shielded Mini Multilane HD 4X.";
        }
        enum "Shielded Mini Multilane HD 8X" {
          value 16;
          description
            "Identifier value 0x0F, Shielded Mini Multilane HD 8X.";
        }
        enum "QSFP28 SFF-8636" {
          value 17;
          description
            "Identifier value 0x11, QSFP28 (SFF-8636) or later.";
        }
        enum "CXP2 aka CXP28" {
          value 18;
          description
            "Identifier value 0x12, CXP2 (aka CXP28) or later.";
        }
        enum "CDFP Style1/Style2" {
          value 19;
          description
            "Identifier value 0x13, CDFP (Style 1 / Style 2).";
        }
        enum "Shielded Mini Multilane HD 4X Fanout" {
          value 20;
          description
            "Identifier value 0x14, Shielded Mini Multilane HD 4X Fanout.";
        }
        enum "Shielded Mini Multilane HD 8X Fanout" {
          value 21;
          description
            "Identifier value 0x15, Shielded Mini Multilane HD 8X Fanout.";
        }
        enum "CDFP Style 3" {
          value 22;
          description
            "Identifier value 0x16, CDFP (Style 3).";
        }
        enum "micro QSFP" {
          value 23;
          description
            "Identifier value 0x17, microQSFP.";
        }
        enum "QSFP DD" {
          value 24;
          description
            "Identifier value 0x18, QSFP-DD.";
        }
        enum "CFP2 DCO" {
          value 25;
          description
            "Identifier value 0x19, CFP2-DCO.";
        }
      }
      description
        "Human readable description of Vendor's identifier byte value. Reference SFF-8024, table 4-1";
    }
    leaf identifier-raw {
      tailf:ncs-device-type "netconf";
      tailf:display-when "not(../../../../../../../../ncs:module) or ../../../../../../../../ncs:module[ncs:name='ciena-packet-xcvr-pluggable'] or (../../../../../../../../ncs:live-status-protocol[not(ncs:capability)]) or (../../../../../../../../ncs:live-status-protocol/ncs:capability/ncs:module[.='ciena-packet-xcvr-pluggable'])";
      type cntypes:live_ncs_string-maxl-32;
      description
        "Vendor's identifier raw byte value. In the format of a HEX string. Reference SFF-8024, table 4-1";
    }
    leaf extended-identifier-raw {
      tailf:ncs-device-type "netconf";
      tailf:display-when "not(../../../../../../../../ncs:module) or ../../../../../../../../ncs:module[ncs:name='ciena-packet-xcvr-pluggable'] or (../../../../../../../../ncs:live-status-protocol[not(ncs:capability)]) or (../../../../../../../../ncs:live-status-protocol/ncs:capability/ncs:module[.='ciena-packet-xcvr-pluggable'])";
      type cntypes:live_ncs_string-maxl-32;
      description
        "Vendor's extended identifier raw byte value. In the format of a HEX string. Reference SFF-8436, table 4-1";
    }
    leaf power-consumption {
      tailf:ncs-device-type "netconf";
      tailf:display-when "not(../../../../../../../../ncs:module) or ../../../../../../../../ncs:module[ncs:name='ciena-packet-xcvr-pluggable'] or (../../../../../../../../ncs:live-status-protocol[not(ncs:capability)]) or (../../../../../../../../ncs:live-status-protocol/ncs:capability/ncs:module[.='ciena-packet-xcvr-pluggable'])";
      type enumeration {
        enum "Class 1 Module 1.5W max" {
          description
            "Class 1 Module 1.5W max.";
        }
        enum "Class 2 Module 2.0W max" {
          description
            "Class 2 Module 2.0W max.";
        }
        enum "Class 3 Module 2.5W max" {
          description
            "Class 3 Module 2.5W max.";
        }
        enum "Class 4 Module 3.5W max" {
          description
            "Class 4 Module 3.5W max.";
        }
      }
      description
        "The class of Power Consumption portion of the extended identifier byte, bit 7 to 6. Reference SFF-8436, section 7.6.2.2";
    }
    leaf clei {
      tailf:ncs-device-type "netconf";
      tailf:display-when "not(../../../../../../../../ncs:module) or ../../../../../../../../ncs:module[ncs:name='ciena-packet-xcvr-pluggable'] or (../../../../../../../../ncs:live-status-protocol[not(ncs:capability)]) or (../../../../../../../../ncs:live-status-protocol/ncs:capability/ncs:module[.='ciena-packet-xcvr-pluggable'])";
      type cntypes:live_ncs_string-maxl-16;
      description
        "CLEI code. If bit4 in extended identifier is set to 1, show the CLEI code. If bit4 in extended identifier is set to 0, 'No CLEI code' will be shown. Reference SFF-8436, section 7.6.2.2 and section 7.6.4";
    }
    leaf connector-type-raw {
      tailf:ncs-device-type "netconf";
      tailf:display-when "not(../../../../../../../../ncs:module) or ../../../../../../../../ncs:module[ncs:name='ciena-packet-xcvr-pluggable'] or (../../../../../../../../ncs:live-status-protocol[not(ncs:capability)]) or (../../../../../../../../ncs:live-status-protocol/ncs:capability/ncs:module[.='ciena-packet-xcvr-pluggable'])";
      type cntypes:live_ncs_string-maxl-32;
      description
        "Vendor's connector type raw byte value. In the format of a HEX string. Reference SFF-8024, table 4-3";
    }
    leaf firmware-version {
      tailf:ncs-device-type "netconf";
      tailf:display-when "not(../../../../../../../../ncs:module) or ../../../../../../../../ncs:module[ncs:name='ciena-packet-xcvr-pluggable'] or (../../../../../../../../ncs:live-status-protocol[not(ncs:capability)]) or (../../../../../../../../ncs:live-status-protocol/ncs:capability/ncs:module[.='ciena-packet-xcvr-pluggable'])";
      type cntypes:live_ncs_string-maxl-16;
      description
        "Vendor's Module Firmware Version Number.
         A version number in the format of x.y as a string.  0.0 value indicates undefined.";
    }
  }
  augment "/ncs:devices/ncs:device/ncs:live-status/xcvr:xcvrs/xcvr:xcvr/xcvr:properties/xcvr:vendor-data/xcvr:properties/xcvr:transmitter" {
    // NCS drop when statement
    description
      "XCVR transmitter properties specific to pluggable XCVRs.";
    leaf wavelength {
      tailf:ncs-device-type "netconf";
      tailf:display-when "not(../../../../../../../../ncs:module) or ../../../../../../../../ncs:module[ncs:name='ciena-packet-xcvr-pluggable'] or (../../../../../../../../ncs:live-status-protocol[not(ncs:capability)]) or (../../../../../../../../ncs:live-status-protocol/ncs:capability/ncs:module[.='ciena-packet-xcvr-pluggable'])";
      type cntypes:live_ncs_decimal-2-dig;
      units "nm";
      description
        "Wave length value, in nanometers.";
    }
    leaf wavelength-raw {
      tailf:ncs-device-type "netconf";
      tailf:display-when "not(../../../../../../../../ncs:module) or ../../../../../../../../ncs:module[ncs:name='ciena-packet-xcvr-pluggable'] or (../../../../../../../../ncs:live-status-protocol[not(ncs:capability)]) or (../../../../../../../../ncs:live-status-protocol/ncs:capability/ncs:module[.='ciena-packet-xcvr-pluggable'])";
      type cntypes:live_ncs_string-maxl-32;
      description
        "Raw byte value of Wavelength, before any multiplier operation is done. In the format of a HEX string.";
    }
    leaf encoding-description {
      tailf:ncs-device-type "netconf";
      tailf:display-when "not(../../../../../../../../ncs:module) or ../../../../../../../../ncs:module[ncs:name='ciena-packet-xcvr-pluggable'] or (../../../../../../../../ncs:live-status-protocol[not(ncs:capability)]) or (../../../../../../../../ncs:live-status-protocol/ncs:capability/ncs:module[.='ciena-packet-xcvr-pluggable'])";
      type enumeration {
        enum "Unspecified" {
          value 0;
          description
            "Unspecified encoding.";
        }
        enum "8B/10B" {
          value 1;
          description
            "8B/10B encoding.";
        }
        enum "4B/5B" {
          value 2;
          description
            "4B/5B encoding.";
        }
        enum "NRZ" {
          value 3;
          description
            "NRZ encoding.";
        }
        enum "SONET Scrambled" {
          value 4;
          description
            "SONET Scrambled encoding.";
        }
        enum "64B/66B" {
          value 5;
          description
            "64B/66B encoding.";
        }
        enum "Manchester" {
          value 6;
          description
            "Manchester encoding.";
        }
        enum "256B/257B" {
          value 7;
          description
            "256B/257B encoding.";
        }
      }
      description
        "Human readable description of Device encoding mechanism. Some values may differ depending on if it is 8472 or 8x36. Reference SFF-8024, TABLE 4-2.";
    }
    leaf encoding-raw {
      tailf:ncs-device-type "netconf";
      tailf:display-when "not(../../../../../../../../ncs:module) or ../../../../../../../../ncs:module[ncs:name='ciena-packet-xcvr-pluggable'] or (../../../../../../../../ncs:live-status-protocol[not(ncs:capability)]) or (../../../../../../../../ncs:live-status-protocol/ncs:capability/ncs:module[.='ciena-packet-xcvr-pluggable'])";
      type cntypes:live_ncs_string-maxl-32;
      description
        "Raw byte value of Device encoding mechanism. Some values may differ depending on if it is 8472 or 8x36. In the format of a HEX string. Reference SFF-8024, TABLE 4-2.";
    }
  }
  augment "/ncs:devices/ncs:device/ncs:live-status/xcvr:xcvrs/xcvr:xcvr/xcvr:properties/xcvr:vendor-data/xcvr:properties/xcvr:diagnostic-monitoring" {
    // NCS drop when statement
    description
      "XCVR diagnostic properties specific to pluggable XCVRs.";
    leaf diagnostic-monitoring-type-raw {
      tailf:ncs-device-type "netconf";
      tailf:display-when "not(../../../../../../../../ncs:module) or ../../../../../../../../ncs:module[ncs:name='ciena-packet-xcvr-pluggable'] or (../../../../../../../../ncs:live-status-protocol[not(ncs:capability)]) or (../../../../../../../../ncs:live-status-protocol/ncs:capability/ncs:module[.='ciena-packet-xcvr-pluggable'])";
      type cntypes:live_ncs_string-maxl-32;
      description
        "Display the raw byte value of Diagnostic Monitoring Type, in the format of a HEX string. Reference SFF 8472 section 8.8 and table 9.5 for detail.";
    }
    leaf diagnostic-monitoring-implemented {
      tailf:ncs-device-type "netconf";
      tailf:display-when "not(../../../../../../../../ncs:module) or ../../../../../../../../ncs:module[ncs:name='ciena-packet-xcvr-pluggable'] or (../../../../../../../../ncs:live-status-protocol[not(ncs:capability)]) or (../../../../../../../../ncs:live-status-protocol/ncs:capability/ncs:module[.='ciena-packet-xcvr-pluggable'])";
      type boolean;
      description
        "If Digital diagnostic monitoring is implemented, determined by bit 6 of diagnostic monitoring type. Reference SFF 8472 section 8.8 and table 9.5 for detail.";
    }
  }
  augment "/ncs:devices/ncs:device/ncs:live-status/xcvr:xcvrs/xcvr:xcvr/xcvr:properties/xcvr:vendor-data/xcvr:properties" {
    // NCS drop when statement
    description
      "XCVR vendor-data properties specific to pluggable XCVRs.";
    container transceiver-code {
      tailf:ncs-device-type "netconf";
      tailf:display-when "not(../../../../../../../ncs:module) or ../../../../../../../ncs:module[ncs:name='ciena-packet-xcvr-pluggable'] or (../../../../../../../ncs:live-status-protocol[not(ncs:capability)]) or (../../../../../../../ncs:live-status-protocol/ncs:capability/ncs:module[.='ciena-packet-xcvr-pluggable'])";
      description
        "XCVR vendor data transceiver code properties.";
      leaf specification-compliance {
        type bits {
          bit Spec-Compliance-40G-Active-Cable-XLPPI {
            position 0;
            description
              "Spec Compliance 40G Active Cable XLPPI";
          }
          bit Spec-Compliance-40GBASE-LR4 {
            position 1;
            description
              "Spec Compliance 40GBASE-LR4";
          }
          bit Spec-Compliance-40GBASE-SR4 {
            position 2;
            description
              "Spec Compliance 40GBASE-SR4";
          }
          bit Spec-Compliance-40GBASE-CR4 {
            position 3;
            description
              "Spec Compliance 40GBASE-CR4";
          }
          bit Spec-Compliance-10GBASE-SR {
            position 4;
            description
              "Spec Compliance 10GBASE-SR";
          }
          bit Spec-Compliance-10GBASE-LR {
            position 5;
            description
              "Spec Compliance 10GBASE-LR";
          }
          bit Spec-Compliance-10GBASE-LRM {
            position 6;
            description
              "Spec Compliance 10GBASE-LRM";
          }
          bit Spec-Compliance-10GBASE-ER {
            position 7;
            description
              "Spec Compliance 10GBASE-ER";
          }
          bit Extended-Spec-Compliance-100G-Active-Optical-Cable {
            position 8;
            description
              "Extended Spec Compliance 100G Active Optical Cable";
          }
          bit Extended-Spec-Compliance-100GBASE-SR4 {
            position 9;
            description
              "Extended Spec Compliance 100GBASE-SR4";
          }
          bit Extended-Spec-Compliance-100GBASE-LR4 {
            position 10;
            description
              "Extended-Spec Compliance 100GBASE-LR4";
          }
          bit Extended-Spec-Compliance-100GBASE-ER4 {
            position 11;
            description
              "Extended Spec Compliance 100GBASE-ER4";
          }
          bit Extended-Spec-Compliance-100GBASE-SR10 {
            position 12;
            description
              "Extended Spec Compliance 100GBASE-SR10";
          }
          bit Extended-Spec-Compliance-100G-CWDM4-MSA-with-FEC {
            position 13;
            description
              "Extended Spec Compliance 100G CWDM4 MSA with FEC";
          }
          bit Extended-Spec-Compliance-100G-PSM4-Parallel-SMF {
            position 14;
            description
              "Extended Spec Compliance 100G PSM4 Parallel SMF";
          }
          bit Extended-Spec-Compliance-100G-Active-Copper-Cable {
            position 15;
            description
              "Extended Spec Compliance 100G Active Copper Cable";
          }
          bit Extended-Spec-Compliance-100G-CWDM-MSA-without-FEC {
            position 16;
            description
              "Extended Spec Compliance 100G CWDM MSA without FEC";
          }
          bit Extended-Spec-Compliance-100GBASE-CR4 {
            position 18;
            description
              "Extended Spec Compliance 100GBASE-CR4";
          }
          bit Extended-Spec-Compliance-40GBASE-ER4 {
            position 23;
            description
              "Extended Spec Compliance 40GBASE-ER4";
          }
          bit Extended-Spec-Compliance-4x10GBASE-SR {
            position 24;
            description
              "Extended Spec Compliance 4x10GBASE-SR";
          }
          bit Extended-Spec-Compliance-40G-PSM4-Parallel-SMF {
            position 25;
            description
              "Extended Spec Compliance 40G PSM4 Parallel SMF";
          }
          bit "Extended-Spec-Compliance-G.959.1-P1I1-2D1" {
            position 26;
            description
              "Extended Spec Compliance G.959.1 P1I1 2D1";
          }
          bit "Extended-Spec-Compliance-G.959.1-P1S1-2D2" {
            position 27;
            description
              "Extended Spec Compliance G.959.1 P1S1 2D2";
          }
          bit "Extended-Spec-Compliance-G.959.1-P1L1-2D2" {
            position 28;
            description
              "Extended Spec Compliance G.959.1 P1L1 2D2";
          }
          bit ExtSpecCode-10GBASE-T-with-SFI {
            position 29;
            description
              "ExtSpecCode 10GBASE-T with SFI";
          }
          bit ExtSpecCode-100G-CLR4 {
            position 30;
            description
              "ExtSpecCode 100G-CLR4";
          }
          bit SpecCode-1000BASE-SX {
            position 31;
            description
              "SpecCode-1000BASE-SX";
          }
          bit SpecCode-1000BASE-LX {
            position 32;
            description
              "SpecCode-1000BASE-LX";
          }
          bit SpecCode-1000BASE-CX {
            position 33;
            description
              "SpecCode-1000BASE-CX";
          }
          bit SpecCode-1000BASE-T {
            position 34;
            description
              "SpecCode-1000BASE-T";
          }
        }
        description
          "10 GbE ethernet, 40 GbE ethernet, and 100 GbE extended specification compliance of the transceiver. In the form of a YANG bit field. Note, the bit field in this node is not mapped with the SFF tables. Reference SFF-8436 table 33 for specification compliance of 10 GbE and 40 GbE Ethernet. Reference SFF-8024, TABLE 4-4 for extended specification compliance of 100 GbE.";
      }
      leaf transceiver-code-raw {
        type cntypes:live_ncs_string-maxl-32;
        description
          "Specification Compliance/Transceiver Code raw byte value. In the format of a HEX string. Reference SFF-8436 table 33 for specification compliance";
      }
    }
    container device-technology {
      tailf:ncs-device-type "netconf";
      tailf:display-when "not(../../../../../../../ncs:module) or ../../../../../../../ncs:module[ncs:name='ciena-packet-xcvr-pluggable'] or (../../../../../../../ncs:live-status-protocol[not(ncs:capability)]) or (../../../../../../../ncs:live-status-protocol/ncs:capability/ncs:module[.='ciena-packet-xcvr-pluggable'])";
      description
        "XCVR vendor data device technology properties.";
      leaf device-technology-raw {
        type cntypes:live_ncs_string-maxl-32;
        description
          "Display the raw byte value of Device Technology, in the format of a HEX string. Reference SFF 8636 table 6-19.";
      }
      leaf transmitter-tunable {
        type boolean;
        description
          "Device Technology Transmitter tuneable value. Reference SFF 8636 table 6-19, bit 0.";
      }
      leaf max-case-temperature {
        type uint8;
        units "C";
        description
          "Maximum Case Temperature. In degrees C.";
      }
    }
    container options {
      tailf:ncs-device-type "netconf";
      tailf:display-when "not(../../../../../../../ncs:module) or ../../../../../../../ncs:module[ncs:name='ciena-packet-xcvr-pluggable'] or (../../../../../../../ncs:live-status-protocol[not(ncs:capability)]) or (../../../../../../../ncs:live-status-protocol/ncs:capability/ncs:module[.='ciena-packet-xcvr-pluggable'])";
      description
        "XCVR device options, as described in reference SFF 8636.";
      leaf options-raw {
        type cntypes:live_ncs_string-maxl-32;
        description
          "Raw byte value of 'options' field. In the format of a HEX string. Reference SFF 8636 table 6-22.";
      }
      leaf tx-input-equalization-auto-adaptive-capable {
        type boolean;
        description
          "A bit flag in 'options', reference SFF 8636 table 6-22.";
      }
      leaf tx-input-equalization-fixed-programmable-setting {
        type boolean;
        description
          "A bit flag in 'options', reference SFF 8636 table 6-22.";
      }
      leaf rx-output-emphasis-fixed-programmable-setting {
        type boolean;
        description
          "A bit flag in 'options', reference SFF 8636 table 6-22.";
      }
      leaf rx-output-amplitude-fixed-programmable-setting {
        type boolean;
        description
          "A bit flag in 'options', reference SFF 8636 table 6-22.";
      }
      leaf tx-cdr-loss-of-lock-flag {
        type boolean;
        description
          "A bit flag in 'options', reference SFF 8636 table 6-22.";
      }
      leaf rx-cdr-loss-of-lock-flag {
        type boolean;
        description
          "A bit flag in 'options', reference SFF 8636 table 6-22.";
      }
      leaf user-eeprom-page-02h-provided {
        type boolean;
        description
          "A bit flag in 'options', reference SFF 8636 table 6-22.";
      }
      leaf ast-page-01h-provided {
        type boolean;
        description
          "A bit flag in 'options', reference SFF 8636 table 6-22.";
      }
    }
  }
  augment "/ncs:devices/ncs:device/ncs:live-status/xcvr:xcvrs/xcvr:xcvr/xcvr:properties/xcvr:diagnostics/xcvr:device" {
    // NCS drop when statement
    description
      "XCVR diagnostics device properties specific to pluggable XCVRs.";
    container supply-voltage {
      tailf:ncs-device-type "netconf";
      tailf:display-when "not(../../../../../../../ncs:module) or ../../../../../../../ncs:module[ncs:name='ciena-packet-xcvr-pluggable'] or (../../../../../../../ncs:live-status-protocol[not(ncs:capability)]) or (../../../../../../../ncs:live-status-protocol/ncs:capability/ncs:module[.='ciena-packet-xcvr-pluggable'])";
      description
        "XCVR supply voltage readings and thresholds.";
      leaf actual {
        type cntypes:live_ncs_decimal-2-dig;
        units "V";
        description
          "Supply voltage, actual supply voltage in volts (V). Range must be between 0 and 6.55V.";
      }
      container status {
        description
          "Supply voltage status.";
        uses xcvr:live_ncs_supply-voltage-status-group;
      }
      container threshold {
        description
          "Supply voltage thresholds.";
        uses xcvr:live_ncs_supply-voltage-threshold-group;
      }
    }
  }
  augment "/ncs:devices/ncs:device/ncs:live-status/xcvr:xcvrs/xcvr:xcvr/xcvr:properties/xcvr:diagnostics/xcvr:lane" {
    // NCS drop when statement
    description
      "XCVR lane properties specific to pluggable XCVRs.";
    leaf transmitter-fault {
      tailf:ncs-device-type "netconf";
      tailf:display-when "not(../../../../../../../ncs:module) or ../../../../../../../ncs:module[ncs:name='ciena-packet-xcvr-pluggable'] or (../../../../../../../ncs:live-status-protocol[not(ncs:capability)]) or (../../../../../../../ncs:live-status-protocol/ncs:capability/ncs:module[.='ciena-packet-xcvr-pluggable'])";
      type boolean;
      description
        "If the xcvr channel transmitter has detected a fault.";
    }
    leaf tx-adaptive-eq-fault {
      tailf:ncs-device-type "netconf";
      tailf:display-when "not(../../../../../../../ncs:module) or ../../../../../../../ncs:module[ncs:name='ciena-packet-xcvr-pluggable'] or (../../../../../../../ncs:live-status-protocol[not(ncs:capability)]) or (../../../../../../../ncs:live-status-protocol/ncs:capability/ncs:module[.='ciena-packet-xcvr-pluggable'])";
      type boolean;
      description
        "If the xcvr channel Tx Adaptive EQ Fault has detected a fault. Only applicable for QSFP28. For QSFP+, default value of FALSE will be returned.";
    }
  }
  augment "/ncs:devices/ncs:device/ncs:notifications/ncs:received-notifications/ncs:notification/ncs:data/xcvr:xcvr-events" {
    leaf optic-voltage-high-threshold {
      type empty;
      description
        "Voltage high threshold";
    }
    leaf optic-voltage-low-threshold {
      type empty;
      description
        "Voltage low threshold";
    }
    leaf optic-voltage-normal {
      type empty;
      description
        "Voltage has returned to normal having previously crossed a threshold.";
    }
  }
  augment "/ncs:devices/ncs:device/ncs:netconf-notifications/ncs:received-notifications/ncs:notification/ncs:data/xcvr:xcvr-events" {
    leaf optic-voltage-high-threshold {
      type empty;
      description
        "Voltage high threshold";
    }
    leaf optic-voltage-low-threshold {
      type empty;
      description
        "Voltage low threshold";
    }
    leaf optic-voltage-normal {
      type empty;
      description
        "Voltage has returned to normal having previously crossed a threshold.";
    }
  }
}
