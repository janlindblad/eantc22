module ciena-module {
  // Generated by yanger -t ncs
  tailf:mount-id "ciena107-nc-1.0:ciena107-nc-1.0";
  tailf:ncs-device-type "netconf";

  namespace "http://www.ciena.com/ns/yang/ciena-module";
  prefix ciena-mod;

  import openconfig-platform {
    prefix oc-platform;
  }
  import tailf-common {
    prefix tailf;
  }
  import tailf-ncs {
    prefix ncs;
  }

  organization
    "Ciena Corporation";
  contact
    "Web URL: http://www.ciena.com/
     E-mail:  yang@ciena.com
     Postal:  7035 Ridge Road
             Hanover, Maryland 21076
             U.S.A.
     Phone:   +1 800-921-1144
     Fax:     +1 410-694-5750";
  description
    "This YANG module defines the node
     for fru module restart.

     Copyright (c) 2019 Ciena Corporation.  All rights
     reserved.

     All information contained herein is, and remains
     the property of Ciena Corporation. Dissemination of this
     information or reproduction of this material is strictly
     forbidden unless prior written permission is obtained from
     Ciena Corporation.";

  revision 2019-01-16 {
    description
      "Initial revision with module restart RPC";
    reference "";
  }

  augment "/ncs:devices/ncs:device/ncs:rpc" {
    container rpc-module-restart {
      tailf:ncs-device-type "netconf";
      tailf:display-when "not(../../ncs:module) or ../../ncs:module[ncs:name='ciena-module']";
      tailf:action module-restart {
        tailf:actionpoint ncsproxy {
          tailf:internal;
        }
        description
          "Request that the FRU module be reset immediately.
           A server SHOULD send an rpc reply to the client before
           FRU reset.";
        input {
          leaf name {
            type string;
            description
              "The name of the module component which will be reset.";
          }
          leaf type {
            type enumeration {
              enum "warm" {
                description
                  "FRU warm restart, user traffic will not be affected";
              }
              enum "cold" {
                description
                  "FRU cold restart, user traffic will be interrupted";
              }
            }
            default "warm";
            description
              "Set the restart type for the module.";
          }
        }
      }
    }
  }
  augment "/ncs:devices/ncs:device-group/ncs:ned-id/ncs:rpc" {
    container rpc-module-restart {
      tailf:ncs-device-type "netconf";
      tailf:display-when "/ncs:devices/ncs:device[ncs:name=current()/../../../ncs:member]/ncs:module[ncs:name='ciena-module']";
      tailf:action module-restart {
        tailf:actionpoint ncsproxy {
          tailf:internal;
        }
        description
          "Request that the FRU module be reset immediately.
           A server SHOULD send an rpc reply to the client before
           FRU reset.";
        input {
          leaf name {
            type string;
            description
              "The name of the module component which will be reset.";
          }
          leaf type {
            type enumeration {
              enum "warm" {
                description
                  "FRU warm restart, user traffic will not be affected";
              }
              enum "cold" {
                description
                  "FRU cold restart, user traffic will be interrupted";
              }
            }
            default "warm";
            description
              "Set the restart type for the module.";
          }
        }
      }
    }
  }
}
