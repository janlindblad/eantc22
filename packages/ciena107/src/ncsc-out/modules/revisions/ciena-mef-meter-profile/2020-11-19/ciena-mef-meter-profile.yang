module ciena-mef-meter-profile {
  // Generated by yanger -t ncs
  tailf:mount-id "ciena107-nc-1.0:ciena107-nc-1.0";
  tailf:ncs-device-type "netconf";

  namespace "urn:ciena:params:xml:ns:yang:ciena-pn::ciena-mef-meter-profile";
  prefix meter;

  import tailf-common {
    prefix tailf;
  }
  import tailf-ncs {
    prefix ncs;
  }

  organization
    "Ciena Corporation";
  contact
    "Web URL: http://www.ciena.com/
     E-mail:  yang@ciena.com
     Postal:  7035 Ridge Road
             Hanover, Maryland 21076
             U.S.A.
     Phone:   +1 800-921-1144
     Fax:     +1 410-694-5750";
  description
    "This YANG module defines the Meter Profile configuration
     requirements.";

  revision 2020-11-19 {
    description
      "Added shared-meter-instance and valid-interface-type to meter-profile.";
  }
  revision 2020-06-12 {
    description
      "fixed the typo in EBS and CBS leaf.
       changed bytes to kilobytes";
  }
  revision 2015-07-16 {
    description
      "Initial revision";
  }

  typedef ncs_template_meter-ref {
    type string;
    description
      "This type is used by data models that need to reference
       configured meter profiles.";
  }

  typedef ncs_rpc_notif_meter-ref {
    type string;
    description
      "This type is used by data models that need to reference
       configured meter profiles.";
  }

  typedef live_ncs_meter-ref {
    type leafref {
      path "/ncs:devices/ncs:device/ncs:live-status/meter:meter-profiles/meter:meter-profile/meter:name" {
        tailf:xpath-root 3;
      }
    }
    description
      "This type is used by data models that need to reference
       configured meter profiles.";
  }

  typedef meter-ref {
    type leafref {
      path "/ncs:devices/ncs:device/ncs:config/meter:meter-profiles/meter:meter-profile/meter:name" {
        tailf:xpath-root 3;
      }
    }
    description
      "This type is used by data models that need to reference
       configured meter profiles.";
  }

  augment "/ncs:devices/ncs:device/ncs:config" {
    container meter-profiles {
      tailf:ncs-device-type "netconf";
      tailf:display-when "not(../../ncs:module) or ../../ncs:module[ncs:name='ciena-mef-meter-profile']";
      description
        "List of meter-profile templates. Meter profiles can be referenced by various entities (flow-point/logical-port etc.)
         to instantiate TrTCM/SrTCM meters for the entities.";
      list meter-profile {
        key "name";
        description
          "Meter Profile template containing meter instance parameters";
        leaf name {
          type string;
          description
            "A unique identifier for the profile that is either
             set as part of configuration or set by the system.";
        }
        leaf description {
          type string;
          description
            "A more detailed description of the profile.";
        }
        leaf cir {
          type uint32;
          description
            "Committed Information Rate (CIR). CIR is a Bandwidth
             Profile parameter. It defines the average rate in
             Kbits/s of Service Frames up to which the network
             delivers Service Frames and meets the performance
             objectives defined by the CoS Service Attribute.";
        }
        leaf eir {
          type uint32;
          description
            "Excess Information Rate (EIR). EIR is a Bandwidth Profile
             parameter. It defines the average rate in Kbits/s of
             Service Frames up to which the network may deliver
             Service Frames but without any performance objectives.";
        }
        leaf cbs {
          type uint32;
          description
            "Commited Burst Size (CBS). CBS is a Bandwidth Profile
             parameter. It limits the maximum number of kilobytes
             available for a burst of Service Frames sent at the UNI
             speed to remain CIR-conformant.";
        }
        leaf ebs {
          type uint32;
          description
            "Excess Burst Size (EBS). EBS is a Bandwidth Profile
             parameter. It limits the maximum number of kilobytes
             available for a burst of Service Frames sent at the UNI
             speed to remain EIR-conformant.";
        }
        leaf color-aware {
          type boolean;
          description
            "The Bandwidth Profile algorithm is said to be in color
             aware mode when each Service Frame already has a level
             of compliance (i.e., a color) associated with it and
             that color is taken into account in determining the
             level of compliance  by the Bandwidth Profile
             algorithm. The Bandwidth Profile algorithm is said to be
             in color blind mode when the color (if any) already
             associated with each Service Frame is ignored by the
             Bandwidth Profile Algorithm.";
        }
        leaf coupling-flag {
          type boolean;
          description
            "CF is a Bandwidth Profile parameter. The Coupling Flag
             allows the choice between two modes of operation of the
             rate enforcement algorithm. It takes a value of 0 or 1
             only.";
          reference
            "MEF 10.2, Section 7.11.1, Standard Bandwidth Profile
             and Parameters.";
        }
        leaf shared-meter-instance {
          type boolean;
          description
            "True => The set of logical interfaces referencing this meter-profile would
             share a meter-instance. False (or leaf not present) => a meter-instance is
             created for each logical-interface reference to a meter-profile.";
        }
        leaf valid-interface-type {
          type enumeration {
            enum "flow-point" {
              description
                "flow-points are valid interface-types for this meter-profile";
            }
            enum "qos-flow" {
              description
                "qos-flows are valid interface-types for this meter-profile";
            }
          }
          description
            "The constraint of the type of interface that can be attached to this meter-profile.";
        }
      }
    }
  }
  augment "/ncs:devices/ncs:device/ncs:live-status" {
    container meter-profiles {
      tailf:ncs-device-type "netconf";
      tailf:display-when "not(../../ncs:module) or ../../ncs:module[ncs:name='ciena-mef-meter-profile'] or (../../ncs:live-status-protocol[not(ncs:capability)]) or (../../ncs:live-status-protocol/ncs:capability/ncs:module[.='ciena-mef-meter-profile'])";
      description
        "List of meter-profile templates. Meter profiles can be referenced by various entities (flow-point/logical-port etc.)
         to instantiate TrTCM/SrTCM meters for the entities.";
      list meter-profile {
        key "name";
        description
          "Meter Profile template containing meter instance parameters";
        leaf name {
          type string;
          description
            "A unique identifier for the profile that is either
             set as part of configuration or set by the system.";
        }
        leaf description {
          type string;
          description
            "A more detailed description of the profile.";
        }
        leaf cir {
          type uint32;
          description
            "Committed Information Rate (CIR). CIR is a Bandwidth
             Profile parameter. It defines the average rate in
             Kbits/s of Service Frames up to which the network
             delivers Service Frames and meets the performance
             objectives defined by the CoS Service Attribute.";
        }
        leaf eir {
          type uint32;
          description
            "Excess Information Rate (EIR). EIR is a Bandwidth Profile
             parameter. It defines the average rate in Kbits/s of
             Service Frames up to which the network may deliver
             Service Frames but without any performance objectives.";
        }
        leaf cbs {
          type uint32;
          description
            "Commited Burst Size (CBS). CBS is a Bandwidth Profile
             parameter. It limits the maximum number of kilobytes
             available for a burst of Service Frames sent at the UNI
             speed to remain CIR-conformant.";
        }
        leaf ebs {
          type uint32;
          description
            "Excess Burst Size (EBS). EBS is a Bandwidth Profile
             parameter. It limits the maximum number of kilobytes
             available for a burst of Service Frames sent at the UNI
             speed to remain EIR-conformant.";
        }
        leaf color-aware {
          type boolean;
          description
            "The Bandwidth Profile algorithm is said to be in color
             aware mode when each Service Frame already has a level
             of compliance (i.e., a color) associated with it and
             that color is taken into account in determining the
             level of compliance  by the Bandwidth Profile
             algorithm. The Bandwidth Profile algorithm is said to be
             in color blind mode when the color (if any) already
             associated with each Service Frame is ignored by the
             Bandwidth Profile Algorithm.";
        }
        leaf coupling-flag {
          type boolean;
          description
            "CF is a Bandwidth Profile parameter. The Coupling Flag
             allows the choice between two modes of operation of the
             rate enforcement algorithm. It takes a value of 0 or 1
             only.";
          reference
            "MEF 10.2, Section 7.11.1, Standard Bandwidth Profile
             and Parameters.";
        }
        leaf shared-meter-instance {
          type boolean;
          description
            "True => The set of logical interfaces referencing this meter-profile would
             share a meter-instance. False (or leaf not present) => a meter-instance is
             created for each logical-interface reference to a meter-profile.";
        }
        leaf valid-interface-type {
          type enumeration {
            enum "flow-point" {
              description
                "flow-points are valid interface-types for this meter-profile";
            }
            enum "qos-flow" {
              description
                "qos-flows are valid interface-types for this meter-profile";
            }
          }
          description
            "The constraint of the type of interface that can be attached to this meter-profile.";
        }
      }
    }
  }
  augment "/ncs:devices/ncs:template/ncs:ned-id/ncs:config" {
    container meter-profiles {
      description
        "List of meter-profile templates. Meter profiles can be referenced by various entities (flow-point/logical-port etc.)
         to instantiate TrTCM/SrTCM meters for the entities.";
      list meter-profile {
        // NCS patched for predictable order
        ordered-by user;
        key "name";
        description
          "Meter Profile template containing meter instance parameters";
        leaf name {
          type string;
          description
            "A unique identifier for the profile that is either
             set as part of configuration or set by the system.";
        }
        leaf description {
          type string;
          description
            "A more detailed description of the profile.";
        }
        leaf cir {
          type string;
          description
            "Committed Information Rate (CIR). CIR is a Bandwidth
             Profile parameter. It defines the average rate in
             Kbits/s of Service Frames up to which the network
             delivers Service Frames and meets the performance
             objectives defined by the CoS Service Attribute.";
        }
        leaf eir {
          type string;
          description
            "Excess Information Rate (EIR). EIR is a Bandwidth Profile
             parameter. It defines the average rate in Kbits/s of
             Service Frames up to which the network may deliver
             Service Frames but without any performance objectives.";
        }
        leaf cbs {
          type string;
          description
            "Commited Burst Size (CBS). CBS is a Bandwidth Profile
             parameter. It limits the maximum number of kilobytes
             available for a burst of Service Frames sent at the UNI
             speed to remain CIR-conformant.";
        }
        leaf ebs {
          type string;
          description
            "Excess Burst Size (EBS). EBS is a Bandwidth Profile
             parameter. It limits the maximum number of kilobytes
             available for a burst of Service Frames sent at the UNI
             speed to remain EIR-conformant.";
        }
        leaf color-aware {
          type string;
          description
            "The Bandwidth Profile algorithm is said to be in color
             aware mode when each Service Frame already has a level
             of compliance (i.e., a color) associated with it and
             that color is taken into account in determining the
             level of compliance  by the Bandwidth Profile
             algorithm. The Bandwidth Profile algorithm is said to be
             in color blind mode when the color (if any) already
             associated with each Service Frame is ignored by the
             Bandwidth Profile Algorithm.";
        }
        leaf coupling-flag {
          type string;
          description
            "CF is a Bandwidth Profile parameter. The Coupling Flag
             allows the choice between two modes of operation of the
             rate enforcement algorithm. It takes a value of 0 or 1
             only.";
          reference
            "MEF 10.2, Section 7.11.1, Standard Bandwidth Profile
             and Parameters.";
        }
        leaf shared-meter-instance {
          type string;
          description
            "True => The set of logical interfaces referencing this meter-profile would
             share a meter-instance. False (or leaf not present) => a meter-instance is
             created for each logical-interface reference to a meter-profile.";
        }
        leaf valid-interface-type {
          type string;
          description
            "The constraint of the type of interface that can be attached to this meter-profile.";
        }
      }
    }
  }
}
