module ciena-dhcp-multi-deviation {
  // Generated by yanger -t ncs
  tailf:mount-id "ciena107-nc-1.0:ciena107-nc-1.0";
  tailf:ncs-device-type "netconf";

  namespace "http://www.ciena.com/ns/yang/ciena-dhcp-multi-dev";
  prefix dhcp-multi-dev;

  import ciena-dhcp {
    prefix dhcp;
  }
  import tailf-common {
    prefix tailf;
  }
  import tailf-ncs {
    prefix ncs;
  }

  organization
    "Ciena Corporation";
  contact
    "Web URL: http://www.ciena.com/
     E-mail:  yang@ciena.com
     Postal:  7035 Ridge Road
              Hanover, Maryland 21076
              U.S.A.
     Phone:   +1 800-921-1144
     Fax:     +1 410-694-5750";
  description
    "This YANG module defines Ciena's and deviations from the ciena-dhcp
     model for the purpose of adding support for DHCP clients on
     multiple interfaces.

     Copyright (c) 2016 Ciena Corporation.  All rights reserved.

     All information contained herein is, and remains the property of
     Ciena Corporation. Dissemination of this information or
     reproduction of this material is strictly forbidden unless prior
     written permission is obtained from Ciena Corporation.";

  revision 2018-06-26 {
    description
      "Initial revision.";
    reference
      "RFC 2131, Dynamic Host Configuration Protocol
       RFC 2132, DHCP Options and BOOTP Vendor Extensions
       RFC 3046, DHCP Relay Agent Information Option
       RFC 3925, Vendor-Identifying Vendor Options for
                 Dynamic Host Configuration Protocol version 4
                 (DHCPv4)";
  }

  deviation "/ncs:devices/ncs:template/ncs:ned-id/ncs:config/dhcp:dhcp-client/dhcp:admin-state" {
    deviate not-supported;
  }
  deviation "/ncs:devices/ncs:device/ncs:live-status/dhcp:dhcp-client/dhcp:admin-state" {
    deviate not-supported;
  }
  deviation "/ncs:devices/ncs:device/ncs:config/dhcp:dhcp-client/dhcp:admin-state" {
    deviate not-supported;
  }
  deviation "/ncs:devices/ncs:template/ncs:ned-id/ncs:config/dhcp:dhcp-client/dhcp:interface-type" {
    deviate not-supported;
  }
  deviation "/ncs:devices/ncs:device/ncs:live-status/dhcp:dhcp-client/dhcp:interface-type" {
    deviate not-supported;
  }
  deviation "/ncs:devices/ncs:device/ncs:config/dhcp:dhcp-client/dhcp:interface-type" {
    deviate not-supported;
  }
  deviation "/ncs:devices/ncs:template/ncs:ned-id/ncs:config/dhcp:dhcp-client/dhcp:discovery-interval" {
    deviate not-supported;
  }
  deviation "/ncs:devices/ncs:device/ncs:live-status/dhcp:dhcp-client/dhcp:discovery-interval" {
    deviate not-supported;
  }
  deviation "/ncs:devices/ncs:device/ncs:config/dhcp:dhcp-client/dhcp:discovery-interval" {
    deviate not-supported;
  }
  deviation "/ncs:devices/ncs:template/ncs:ned-id/ncs:config/dhcp:dhcp-client/dhcp:requested-lease-time" {
    deviate not-supported;
  }
  deviation "/ncs:devices/ncs:device/ncs:live-status/dhcp:dhcp-client/dhcp:requested-lease-time" {
    deviate not-supported;
  }
  deviation "/ncs:devices/ncs:device/ncs:config/dhcp:dhcp-client/dhcp:requested-lease-time" {
    deviate not-supported;
  }
  deviation "/ncs:devices/ncs:template/ncs:ned-id/ncs:config/dhcp:dhcp-client/dhcp:option-enable" {
    deviate not-supported;
  }
  deviation "/ncs:devices/ncs:device/ncs:live-status/dhcp:dhcp-client/dhcp:option-enable" {
    deviate not-supported;
  }
  deviation "/ncs:devices/ncs:device/ncs:config/dhcp:dhcp-client/dhcp:option-enable" {
    deviate not-supported;
  }
  deviation "/ncs:devices/ncs:device/ncs:live-status/dhcp:dhcp-client-state/dhcp:oper-state" {
    deviate not-supported;
  }
  deviation "/ncs:devices/ncs:device/ncs:live-status/dhcp:dhcp-client-state/dhcp:dhcp-state" {
    deviate not-supported;
  }
  deviation "/ncs:devices/ncs:device/ncs:live-status/dhcp:dhcp-client-state/dhcp:lease-time" {
    deviate not-supported;
  }
  deviation "/ncs:devices/ncs:device/ncs:live-status/dhcp:dhcp-client-state/dhcp:lease-time-remaining" {
    deviate not-supported;
  }
  deviation "/ncs:devices/ncs:device/ncs:live-status/dhcp:dhcp-client-state/dhcp:renewal-time" {
    deviate not-supported;
  }
  deviation "/ncs:devices/ncs:device/ncs:live-status/dhcp:dhcp-client-state/dhcp:renewal-time-remaining" {
    deviate not-supported;
  }
  deviation "/ncs:devices/ncs:device/ncs:live-status/dhcp:dhcp-client-state/dhcp:rebinding-time" {
    deviate not-supported;
  }
  deviation "/ncs:devices/ncs:device/ncs:live-status/dhcp:dhcp-client-state/dhcp:rebinding-time-remaining" {
    deviate not-supported;
  }
  deviation "/ncs:devices/ncs:device/ncs:live-status/dhcp:dhcp-client-state/dhcp:dhcp-server-identifier" {
    deviate not-supported;
  }
  deviation "/ncs:devices/ncs:device/ncs:live-status/dhcp:dhcp-client-state/dhcp:option-value" {
    deviate not-supported;
  }
  deviation "/ncs:devices/ncs:template/ncs:ned-id/ncs:config/dhcp:dhcp-tpid-rotation" {
    deviate not-supported;
  }
  deviation "/ncs:devices/ncs:device/ncs:live-status/dhcp:dhcp-tpid-rotation" {
    deviate not-supported;
  }
  deviation "/ncs:devices/ncs:device/ncs:config/dhcp:dhcp-tpid-rotation" {
    deviate not-supported;
  }
  deviation "/ncs:devices/ncs:device/ncs:live-status/dhcp:dhcp-tpid-rotation-state" {
    deviate not-supported;
  }
  deviation "/ncs:devices/ncs:template/ncs:ned-id/ncs:config/dhcp:dhcp-l2-relay-agent" {
    deviate not-supported;
  }
  deviation "/ncs:devices/ncs:device/ncs:live-status/dhcp:dhcp-l2-relay-agent" {
    deviate not-supported;
  }
  deviation "/ncs:devices/ncs:device/ncs:config/dhcp:dhcp-l2-relay-agent" {
    deviate not-supported;
  }
  deviation "/ncs:devices/ncs:device/ncs:live-status/dhcp:dhcp-l2-relay-agent-state" {
    deviate not-supported;
  }
}
