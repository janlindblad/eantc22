module ciena-l2vpn {
  // Generated by yanger -t ncs
  tailf:mount-id "ciena107-nc-1.0:ciena107-nc-1.0";
  tailf:ncs-device-type "netconf";

  namespace "http://ciena.com/ns/yang/ciena-l2vpn";
  prefix l2vpn;

  import ietf-pseudowires {
    prefix pw;
  }
  import ciena-mef-fd {
    prefix mef-fd;
  }
  import ciena-l3-types {
    prefix cn-l3-types;
  }
  import yuma-ncx {
    prefix ncx;
  }
  import tailf-common {
    prefix tailf;
  }
  import tailf-ncs {
    prefix ncs;
  }

  organization
    "Ciena Corporation";
  contact
    "Web URL: http://www.ciena.com/
     E-mail:  yang@ciena.com
     Postal:  7035 Ridge Road
               Hanover, Maryland 21076
                   U.S.A.
     Phone:   +1 800-921-1144
     Fax:     +1 410-694-5750";
  description
    "This YANG module defines Ciena's specific l2vpn
     protocol

     Copyright (c) 2018  Ciena Corporation.  All rights
     reserved.

     All information contained herein is, and remains the
     property of Ciena Corporation. Dissemination of this
     information or reproduction of this material is strictly
     forbidden unless prior written permission is obtained
     from Ciena Corporation.";

  revision 2018-11-12 {
    description
      "Initial version of ciena-l2vpn config and state yang model";
  }

  typedef ncs_template_protocol-type {
    type string;
  }

  typedef ncs_rpc_notif_protocol-type {
    type enumeration {
      enum "ldp" {
        description
          "Protocol type is LDP signaling";
      }
    }
  }

  typedef live_ncs_protocol-type {
    type enumeration {
      enum "ldp" {
        description
          "Protocol type is LDP signaling";
      }
    }
  }

  typedef protocol-type {
    type enumeration {
      enum "ldp" {
        description
          "Protocol type is LDP signaling";
      }
    }
  }

  grouping ncs_template_l2vpn-common-parameters-grp {
    description
      "L2VPN common parameters";
    leaf mtu {
      type string;
      // NCS drop default statement
      units "bytes";
      description
        "This attribute sets the Maximum Transmission Unit(MTU) for a L2VPN service";
    }
    leaf service-type {
      ncx:user-write "create";
      type cn-l3-types:ncs_template_mpls-vpls-type;
      // NCS drop default statement
      description
        "The service type as Vlan or Ethernet, Ethernet is default.";
    }
    leaf signaling-type {
      ncx:user-write "create";
      type ncs_template_protocol-type;
      description
        "The signaling type to be used for L2VPN signaling.";
    }
  }

  grouping ncs_rpc_notif_l2vpn-common-parameters-grp {
    description
      "L2VPN common parameters";
    leaf mtu {
      type uint16 {
        range "576..16000";
      }
      default "1500";
      units "bytes";
      description
        "This attribute sets the Maximum Transmission Unit(MTU) for a L2VPN service";
    }
    leaf service-type {
      ncx:user-write "create";
      type cn-l3-types:ncs_rpc_notif_mpls-vpls-type;
      default "ethernet";
      description
        "The service type as Vlan or Ethernet, Ethernet is default.";
    }
    leaf signaling-type {
      ncx:user-write "create";
      type ncs_rpc_notif_protocol-type;
      description
        "The signaling type to be used for L2VPN signaling.";
    }
  }

  grouping live_ncs_l2vpn-common-parameters-grp {
    description
      "L2VPN common parameters";
    leaf mtu {
      type uint16 {
        range "576..16000";
      }
      // NCS drop default statement
      units "bytes";
      description
        "This attribute sets the Maximum Transmission Unit(MTU) for a L2VPN service";
    }
    leaf service-type {
      ncx:user-write "create";
      type cn-l3-types:live_ncs_mpls-vpls-type;
      // NCS drop default statement
      description
        "The service type as Vlan or Ethernet, Ethernet is default.";
    }
    leaf signaling-type {
      ncx:user-write "create";
      type live_ncs_protocol-type;
      description
        "The signaling type to be used for L2VPN signaling.";
    }
  }

  grouping l2vpn-common-parameters-grp {
    description
      "L2VPN common parameters";
    leaf mtu {
      type uint16 {
        range "576..16000";
      }
      default "1500";
      units "bytes";
      description
        "This attribute sets the Maximum Transmission Unit(MTU) for a L2VPN service";
    }
    leaf service-type {
      ncx:user-write "create";
      type cn-l3-types:mpls-vpls-type;
      default "ethernet";
      description
        "The service type as Vlan or Ethernet, Ethernet is default.";
    }
    leaf signaling-type {
      ncx:user-write "create";
      type protocol-type;
      description
        "The signaling type to be used for L2VPN signaling.";
    }
  }

  augment "/ncs:devices/ncs:device/ncs:rpc" {
    container rpc-vc-switchover {
      tailf:ncs-device-type "netconf";
      tailf:display-when "not(../../ncs:module) or ../../ncs:module[ncs:name='ciena-l2vpn']";
      tailf:action vc-switchover {
        tailf:actionpoint ncsproxy {
          tailf:internal;
        }
        input {
          leaf from {
            type pw:ncs_rpc_notif_pseudowire-ref;
            description
              "Name of pseudowire in use.";
          }
          leaf to {
            type pw:ncs_rpc_notif_pseudowire-ref;
            description
              "Name of pseudowire to be switched to.";
          }
        }
        output {
          leaf response {
            type string;
            description
              "The response could be 'success', or the reason for isis-clear-ip-route failure";
          }
        }
      }
    }
  }
  augment "/ncs:devices/ncs:device-group/ncs:ned-id/ncs:rpc" {
    container rpc-vc-switchover {
      tailf:ncs-device-type "netconf";
      tailf:display-when "/ncs:devices/ncs:device[ncs:name=current()/../../../ncs:member]/ncs:module[ncs:name='ciena-l2vpn']";
      tailf:action vc-switchover {
        tailf:actionpoint ncsproxy {
          tailf:internal;
        }
        input {
          leaf from {
            type pw:ncs_rpc_notif_pseudowire-ref;
            description
              "Name of pseudowire in use.";
          }
          leaf to {
            type pw:ncs_rpc_notif_pseudowire-ref;
            description
              "Name of pseudowire to be switched to.";
          }
        }
        output {
          container "device" {
            leaf "name" {
              type string;
            }
            leaf "info" {
              type string;
            }
            container "result" {
              leaf response {
                type string;
                description
                  "The response could be 'success', or the reason for isis-clear-ip-route failure";
              }
            }
          }
        }
      }
    }
  }
  augment "/ncs:devices/ncs:device/ncs:config" {
    container l2vpn-services {
      tailf:ncs-device-type "netconf";
      tailf:display-when "not(../../ncs:module) or ../../ncs:module[ncs:name='ciena-l2vpn']";
      description
        "List of layer-2 VPN services instances.";
      list l2vpn {
        key "name";
        description
          "L2VPN services instance";
        leaf name {
          type string {
            length "1..255";
          }
          description
            "L2vpn-services instance name";
        }
        uses l2vpn-common-parameters-grp;
        leaf forwarding-domain {
          ncx:user-write "create";
          type leafref {
            path "/ncs:devices/ncs:device/ncs:config/mef-fd:fds/mef-fd:fd/mef-fd:name" {
              tailf:xpath-root 3;
            }
          }
          description
            "Mention the forwarding domain name";
        }
        leaf-list pseudowire {
          type pw:pseudowire-ref;
          description
            "Mention the pseudowire names required for l2vpn service";
        }
        leaf vc-mode-revertive {
          type boolean;
          default "false";
          description
            "If TRUE, vc-mode-revertive is enabled.";
        }
        leaf control-word {
          type boolean;
          default "false";
          description
            "If true, control-word is enabled";
        }
      }
    }
  }
  augment "/ncs:devices/ncs:device/ncs:live-status" {
    container l2vpn-services {
      tailf:ncs-device-type "netconf";
      tailf:display-when "not(../../ncs:module) or ../../ncs:module[ncs:name='ciena-l2vpn'] or (../../ncs:live-status-protocol[not(ncs:capability)]) or (../../ncs:live-status-protocol/ncs:capability/ncs:module[.='ciena-l2vpn'])";
      description
        "List of layer-2 VPN services instances.";
      list l2vpn {
        key "name";
        description
          "L2VPN services instance";
        leaf name {
          type string {
            length "1..255";
          }
          description
            "L2vpn-services instance name";
        }
        uses live_ncs_l2vpn-common-parameters-grp;
        leaf forwarding-domain {
          ncx:user-write "create";
          type leafref {
            path "/ncs:devices/ncs:device/ncs:live-status/mef-fd:fds/mef-fd:fd/mef-fd:name" {
              tailf:xpath-root 3;
            }
          }
          description
            "Mention the forwarding domain name";
        }
        leaf-list pseudowire {
          type pw:live_ncs_pseudowire-ref;
          description
            "Mention the pseudowire names required for l2vpn service";
        }
        leaf vc-mode-revertive {
          type boolean;
          // NCS drop default statement
          description
            "If TRUE, vc-mode-revertive is enabled.";
        }
        leaf control-word {
          type boolean;
          // NCS drop default statement
          description
            "If true, control-word is enabled";
        }
      }
    }
  }
  augment "/ncs:devices/ncs:template/ncs:ned-id/ncs:config" {
    container l2vpn-services {
      description
        "List of layer-2 VPN services instances.";
      list l2vpn {
        // NCS patched for predictable order
        ordered-by user;
        key "name";
        description
          "L2VPN services instance";
        leaf name {
          type string;
          description
            "L2vpn-services instance name";
        }
        uses ncs_template_l2vpn-common-parameters-grp;
        leaf forwarding-domain {
          ncx:user-write "create";
          type string;
          description
            "Mention the forwarding domain name";
        }
        leaf-list pseudowire {
          // NCS patched for predictable order
          ordered-by user;
          type pw:ncs_template_pseudowire-ref;
          description
            "Mention the pseudowire names required for l2vpn service";
        }
        leaf vc-mode-revertive {
          type string;
          // NCS drop default statement
          description
            "If TRUE, vc-mode-revertive is enabled.";
        }
        leaf control-word {
          type string;
          // NCS drop default statement
          description
            "If true, control-word is enabled";
        }
      }
    }
  }
}
