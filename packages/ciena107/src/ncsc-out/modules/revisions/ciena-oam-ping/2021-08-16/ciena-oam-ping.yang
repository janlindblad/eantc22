module ciena-oam-ping {
  // Generated by yanger -t ncs
  tailf:mount-id "ciena107-nc-1.0:ciena107-nc-1.0";
  tailf:ncs-device-type "netconf";

  yang-version 1.1;
  namespace "http://ciena.com/ns/yang/ciena-oam-ping";
  prefix oam-ping;

  import openconfig-interfaces {
    prefix oc-if;
  }
  import ciena-sr-policy {
    prefix cnsr;
  }
  import ciena-oam-options {
    prefix oam-options;
  }
  import ietf-yang-types {
    prefix yang;
  }
  import ietf-inet-types {
    prefix inet;
  }
  import tailf-common {
    prefix tailf;
  }
  import tailf-ncs {
    prefix ncs;
  }

  organization
    "Ciena Corporation";
  contact
    "Web URL: http://www.ciena.com/
     E-mail:  yang@ciena.com
     Postal:  7035 Ridge Road
              Hanover, Maryland 21076
              U.S.A.
     Phone:   +1 800-921-1144
     Fax:     +1 410-694-5750";
  description
    "This YANG module defines Ciena's specific
     implementation for ping. It includes IP ping,
     LSP ping and Pseudowire ping.

     Copyright (c) 2020  Ciena Corporation.  All rights
     reserved.

     All information contained herein is, and remains the
     property of Ciena Corporation. Dissemination of this
     information or reproduction of this material is strictly
     forbidden unless prior written permission is obtained
     from Ciena Corporation.";

  revision 2021-08-16 {
    description
      "Updated description of destination-ip leaf.
       Added LDP and BGP-LU FEC in backup leaf.";
  }
  revision 2020-12-04 {
    description
      "Added segment parameters for MSPW ping.
       Updated target-fec for SR policy ping.
       Description change for ethernet-segment-identifier.";
  }
  revision 2020-01-31 {
    description
      "Initial Version of ping data model.";
  }

  grouping ncs_template_mspw-segment-config-params {
    leaf segment {
      // NCS drop when statement
      type string;
      // NCS drop default statement
      description
        "Segment number corresponding to the target PW hop
         in the MSPW path. This value is filled in TTL of
         PW label header and in TTL-TLV value of echo
         request.";
    }
    leaf segment-pseudowire-id {
      // NCS drop when statement
      type string;
      description
        "PW-ID of target node to be pinged.";
    }
    leaf segment-source-ip {
      // NCS drop when statement
      type string;
      description
        "Loopback IP of PW hop immediately before the
         target node.";
    }
    leaf segment-destination-ip {
      // NCS drop when statement
      type string;
      description
        "Loopback IP of target node to be pinged.";
    }
  }

  grouping ncs_template_oam-mpls-config-params {
    leaf fec-stack-validation {
      type oam-options:ncs_template_fec-verification-state;
      description
        "To validate the downstream FEC path.";
    }
    leaf reverse-fec-stack-validation {
      type oam-options:ncs_template_fec-verification-state;
      description
        "To validate upstream FEC path.";
    }
    leaf encap {
      type oam-options:ncs_template_encap-ip-udp;
      description
        "Encapsulation: ip/udp, if ip/udp needs to be used in frame.
         non-ip/udp, when it does not need ip/udp in frame.";
    }
    description
      "Advanced parameters for MPLS Ping";
  }

  grouping ncs_template_oam-ping-session-data {
    leaf target-fec-type {
      type oam-options:ncs_template_oam-target-fec-type;
      description
        "Target fec type";
    }
    leaf vrf-name {
      // NCS drop when statement
      type string;
      description
        "VRF name";
    }
    leaf pseudo-wire {
      // NCS drop when statement
      type string;
      description
        "Pseudowire Name";
    }
    leaf tunnel-name {
      // NCS drop when statement
      type string;
      description
        "Tunnel name";
    }
    leaf tunnel-src {
      // NCS drop when statement
      type string;
      description
        "Tunnel Source Ip Address";
    }
    leaf tunnel-dst {
      // NCS drop when statement
      type string;
      description
        "Tunnel Destintion Ip Address";
    }
    leaf evpn-inst-id {
      // NCS drop when statement
      type string;
      description
        "Evpn Instance ID";
    }
    leaf ethernet-tag-id {
      // NCS drop when statement
      type string;
      description
        "Ethernet Tag Identifier.
         For EVPN FXC VPWS mode:
           -Remote Single VID format: <vid> eg. 111
           -Remote Double VID format: <vid>.<vid> eg. 111.222
           -Range of VID 1-4094
         For EVPN VPWS:
           -Remote ServiceId format: <Service-Id> eg. 627654
           -Range of Service Id 1-16777216";
    }
    leaf evpn-dst {
      // NCS drop when statement
      type string;
      description
        "Evpn Destination Prefix";
    }
    leaf ethernet-segment-identifier {
      // NCS drop when statement
      type string;
      description
        "10-octet Ethernet segment identifier (esi) of remote node,
         format: XX:XX:XX:XX:XX:XX:XX:XX:XX:XX
         This is remote ESI required only for ping to multihomed device";
    }
    leaf destination-ip {
      // NCS drop when statement
      type string;
      description
        "IP address of the destination host. For IPv6, when doing ping
         to a link-local scope address, source interface is required.";
    }
    leaf destination-ip-prefix {
      // NCS drop when statement
      type string;
      description
        "Destination Ip prefix for ldp/sr-isis/sr-ospf/bgp-lu lsp";
    }
    leaf backup {
      // NCS drop when statement
      type string;
      description
        "It will be used to ping backup LSP path";
    }
    uses oam-options:ncs_template_oam-base-config-params;
    uses ncs_template_oam-mpls-config-params {
      // NCS drop when statement
    }
    leaf interface {
      // NCS drop when statement
      type string;
      description
        "Source interface name";
    }
    leaf echo-packet-size {
      // NCS drop when statement
      type string;
      units "bytes";
      description
        "Specifies the size of the echo payload to be
         transmitted in each MPLS ping request. Actual
         echo payload shall be larger than specified
         value if it is smaller than minimum size needed
         to hold the TLVs of ping request.";
    }
    uses ncs_template_mspw-segment-config-params;
    leaf policy-name {
      // NCS drop when statement
      type string;
      description
        "SR policy name.";
    }
    leaf color {
      // NCS drop when statement
      type string;
      description
        "Color associated with the SR policy.";
    }
    leaf endpoint {
      // NCS drop when statement
      type string;
      description
        "SR policy end point IP address.";
    }
    description
      "Oam Ping Session data";
  }

  grouping ncs_template_oam-ping-config {
    leaf target-fec-type {
      type oam-options:ncs_template_oam-target-fec-type;
      description
        "Target fec type";
    }
    choice target-fec {
      case vrf-fec {
        leaf vrf-name {
          // NCS drop when statement
          type string;
          description
            "VRF name";
        }
        leaf vrf-dst {
          // NCS drop when statement
          type string;
          description
            "VRF Destination IP";
        }
      }
      case target-ip {
        leaf ip-address {
          // NCS drop when statement
          type string;
          description
            "Destination IP";
        }
      }
      case ldp-fec {
        leaf ldp {
          // NCS drop when statement
          type string;
          description
            "LDP FEC";
        }
      }
      case bgp-lu-fec {
        leaf bgp-lu {
          // NCS drop when statement
          type string;
          description
            "BGP LU FEC";
        }
      }
      case sr-isis-fec {
        leaf sr-isis {
          // NCS drop when statement
          type string;
          description
            "SR ISIS FEC";
        }
      }
      case sr-ospf-fec {
        leaf sr-ospf {
          // NCS drop when statement
          type string;
          description
            "SR OSPF FEC";
        }
      }
      case tunnel-fec {
        leaf tunnel-name {
          // NCS drop when statement
          type string;
          // NCS drop mandatory statement
          description
            "Tunnel Name";
        }
        leaf tunnel-src {
          // NCS drop when statement
          type string;
          // NCS drop mandatory statement
          description
            "Tunnel Source Address";
        }
        leaf tunnel-dst {
          // NCS drop when statement
          type string;
          // NCS drop mandatory statement
          description
            "Tunnel Destination Address";
        }
      }
      case pw {
        leaf pseudo-wire {
          // NCS drop when statement
          type string;
          description
            "Pseudowire Name";
        }
      }
      case evpn-fec {
        leaf evpn-inst-id {
          // NCS drop when statement
          type string;
          // NCS drop mandatory statement
          description
            "Evpn Instance ID";
        }
        leaf ethernet-tag-id {
          // NCS drop when statement
          type string;
          // NCS drop mandatory statement
          description
            "Ethernet Tag Identifier.
             For EVPN FXC VPWS mode:
               -Remote Single VID format: <vid> eg. 111
               -Remote Double VID format: <vid>.<vid> eg. 111.222
               -Range of VID 1-4094
             For EVPN VPWS:
               -Remote ServiceId format: <Service-Id> eg. 627654
               -Range of Service Id 1-16777216";
        }
        leaf evpn-dst {
          // NCS drop when statement
          type string;
          // NCS drop mandatory statement
          description
            "Evpn Destination Prefix";
        }
        leaf ethernet-segment-identifier {
          // NCS drop when statement
          type string;
          description
            "10-octet Ethernet segment identifier (esi),
             format: XX:XX:XX:XX:XX:XX:XX:XX:XX:XX
             This is remote ESI required only for ping to multihomed device";
        }
      }
      case sr-policy-fec {
        leaf policy-name {
          // NCS drop when statement
          type string;
          description
            "Reference to SR policy name.
             Policy name is mutually exclusive with color and endpoint.";
        }
        leaf color {
          // NCS drop when statement
          type string;
          description
            "Reference to color associated with the SR policy.
             Color and endpoint are mutually exclusive with policy name.";
        }
        leaf endpoint {
          // NCS drop when statement
          type string;
          description
            "Reference to SR policy end point IP address.
             Endpoint and color are mutually exclusive with policy name.";
        }
      }
      description
        "Choice for FEC type in MPLS ping";
    }
    leaf backup {
      // NCS drop when statement
      type string;
      // NCS drop default statement
      description
        "It will be used to ping backup LSP path";
    }
    uses oam-options:ncs_template_oam-base-config-params;
    uses ncs_template_oam-mpls-config-params {
      // NCS drop when statement
    }
    leaf interface {
      // NCS drop when statement
      type string;
      description
        "Source interface name";
    }
    leaf echo-packet-size {
      // NCS drop when statement
      type string;
      units "bytes";
      description
        "Specifies the size of the echo payload to be
         transmitted in each MPLS ping request. Actual
         echo payload shall be larger than specified
         value if it is smaller than minimum size needed
         to hold the TLVs of ping request.";
    }
    uses ncs_template_mspw-segment-config-params;
    description
      "Ping Configuration";
  }

  grouping ncs_template_oam-ping-results {
    leaf operational-state {
      type oam-options:ncs_template_operational-state;
      description
        "Operational state of the Ping test.";
    }
    leaf min-rtt {
      type string;
      units "milliseconds";
      description
        "The minimum Ping round-trip-time(RTT) received.";
    }
    leaf max-rtt {
      type string;
      units "milliseconds";
      description
        "The maximum Ping round-trip-time(RTT) received.";
    }
    leaf average-rtt {
      type string;
      units "milliseconds";
      description
        "The current average Ping round-trip-time(RTT).";
    }
    leaf echo-requests-sent {
      type string;
      description
        "Number of echo request sent for the Ping test.";
    }
    leaf echo-replies-received {
      type string;
      description
        "Number of echo replies received for corresponding Ping test.";
    }
    leaf last-good-reply {
      type string;
      description
        "Date and time when the last response was received for
         an echo request.";
    }
    description
      "Ping Results Information";
  }

  grouping ncs_template_oam-ping-probe-results {
    leaf probe-index {
      type string;
      description
        "Probe index.";
    }
    leaf return-code {
      type oam-options:ncs_template_oam-return-code;
      description
        "The Return Code set in the echo reply. This is as per IANA defined error codes.";
    }
    leaf return-sub-code {
      type string;
      description
        "The Return Sub-code set in the echo reply.";
    }
    leaf rtt {
      type string;
      units "milliseconds";
      description
        "The round-trip-time (RTT) received.";
    }
    leaf result-type {
      type oam-options:ncs_template_oam-result-type;
      description
        "The probe result success/failure or any other error.";
    }
    description
      "Ping Probe's Result Information";
  }

  grouping ncs_rpc_notif_mspw-segment-config-params {
    leaf segment {
      when "../target-fec-type = 'pseudowire-fec'" {
        tailf:xpath-root 3;
      }
      type uint8 {
        range "1..255";
      }
      default "1";
      description
        "Segment number corresponding to the target PW hop
         in the MSPW path. This value is filled in TTL of
         PW label header and in TTL-TLV value of echo
         request.";
    }
    leaf segment-pseudowire-id {
      when "../target-fec-type = 'pseudowire-fec'" {
        tailf:xpath-root 3;
      }
      type uint32 {
        range "1..4294967295";
      }
      description
        "PW-ID of target node to be pinged.";
    }
    leaf segment-source-ip {
      when "../target-fec-type = 'pseudowire-fec'" {
        tailf:xpath-root 3;
      }
      type inet:ip-address;
      description
        "Loopback IP of PW hop immediately before the
         target node.";
    }
    leaf segment-destination-ip {
      when "../target-fec-type = 'pseudowire-fec'" {
        tailf:xpath-root 3;
      }
      type inet:ip-address;
      description
        "Loopback IP of target node to be pinged.";
    }
  }

  grouping ncs_rpc_notif_oam-mpls-config-params {
    leaf fec-stack-validation {
      type oam-options:ncs_rpc_notif_fec-verification-state;
      description
        "To validate the downstream FEC path.";
    }
    leaf reverse-fec-stack-validation {
      type oam-options:ncs_rpc_notif_fec-verification-state;
      description
        "To validate upstream FEC path.";
    }
    leaf encap {
      type oam-options:ncs_rpc_notif_encap-ip-udp;
      description
        "Encapsulation: ip/udp, if ip/udp needs to be used in frame.
         non-ip/udp, when it does not need ip/udp in frame.";
    }
    description
      "Advanced parameters for MPLS Ping";
  }

  grouping ncs_rpc_notif_oam-ping-session-data {
    leaf target-fec-type {
      type oam-options:ncs_rpc_notif_oam-target-fec-type;
      description
        "Target fec type";
    }
    leaf vrf-name {
      when "../target-fec-type = 'vrf-fec'" {
        tailf:xpath-root 3;
      }
      type string;
      description
        "VRF name";
    }
    leaf pseudo-wire {
      when "../target-fec-type = 'pseudowire-fec'" {
        tailf:xpath-root 3;
      }
      type string;
      description
        "Pseudowire Name";
    }
    leaf tunnel-name {
      when "../target-fec-type = 'scrt-fec'" {
        tailf:xpath-root 3;
      }
      type string;
      description
        "Tunnel name";
    }
    leaf tunnel-src {
      when "../target-fec-type = 'scrt-fec'" {
        tailf:xpath-root 3;
      }
      type inet:ip-address;
      description
        "Tunnel Source Ip Address";
    }
    leaf tunnel-dst {
      when "../target-fec-type = 'scrt-fec'" {
        tailf:xpath-root 3;
      }
      type inet:ip-address;
      description
        "Tunnel Destintion Ip Address";
    }
    leaf evpn-inst-id {
      when "../target-fec-type = 'evpn-fec'" {
        tailf:xpath-root 3;
      }
      type uint32 {
        range "1..65536";
      }
      description
        "Evpn Instance ID";
    }
    leaf ethernet-tag-id {
      when "../target-fec-type = 'evpn-fec'" {
        tailf:xpath-root 3;
      }
      type string {
        pattern '[1-9][0-9]{0,7}([.][1-9][0-9]{0,3})?';
      }
      description
        "Ethernet Tag Identifier.
         For EVPN FXC VPWS mode:
           -Remote Single VID format: <vid> eg. 111
           -Remote Double VID format: <vid>.<vid> eg. 111.222
           -Range of VID 1-4094
         For EVPN VPWS:
           -Remote ServiceId format: <Service-Id> eg. 627654
           -Range of Service Id 1-16777216";
    }
    leaf evpn-dst {
      when "../target-fec-type = 'evpn-fec'" {
        tailf:xpath-root 3;
      }
      type inet:ip-address;
      description
        "Evpn Destination Prefix";
    }
    leaf ethernet-segment-identifier {
      when "../target-fec-type = 'evpn-fec'" {
        tailf:xpath-root 3;
      }
      type yang:hex-string {
        length "29";
      }
      description
        "10-octet Ethernet segment identifier (esi) of remote node,
         format: XX:XX:XX:XX:XX:XX:XX:XX:XX:XX
         This is remote ESI required only for ping to multihomed device";
    }
    leaf destination-ip {
      when "../target-fec-type = 'ip-fec' or
../target-fec-type = 'vrf-fec'" {
        tailf:xpath-root 3;
      }
      type inet:ip-address;
      description
        "IP address of the destination host. For IPv6, when doing ping
         to a link-local scope address, source interface is required.";
    }
    leaf destination-ip-prefix {
      when "../target-fec-type != 'ip-fec' or
../target-fec-type != 'vrf-fec' or
../target-fec-type != 'scrt-fec' or
../target-fec-type != 'evpn-fec'" {
        tailf:xpath-root 3;
      }
      type inet:ip-prefix;
      description
        "Destination Ip prefix for ldp/sr-isis/sr-ospf/bgp-lu lsp";
    }
    leaf backup {
      when "../target-fec-type = 'sr-ospf-fec' or
../target-fec-type = 'sr-isis-fec' or
../target-fec-type = 'bgp-lu-fec' or
../target-fec-type = 'ldp-fec' " {
        tailf:xpath-root 3;
      }
      type boolean;
      description
        "It will be used to ping backup LSP path";
    }
    uses oam-options:ncs_rpc_notif_oam-base-config-params;
    uses ncs_rpc_notif_oam-mpls-config-params {
      when "target-fec-type != 'ip-fec' or
target-fec-type != 'vrf-fec'" {
        tailf:xpath-root 3;
      }
    }
    leaf interface {
      when "../target-fec-type = 'ip-fec'" {
        tailf:xpath-root 3;
      }
      type string;
      description
        "Source interface name";
    }
    leaf echo-packet-size {
      when "../target-fec-type != 'ip-fec' and
../target-fec-type != 'vrf-fec'" {
        tailf:xpath-root 3;
      }
      type uint16 {
        range "52..1452";
      }
      units "bytes";
      description
        "Specifies the size of the echo payload to be
         transmitted in each MPLS ping request. Actual
         echo payload shall be larger than specified
         value if it is smaller than minimum size needed
         to hold the TLVs of ping request.";
    }
    uses ncs_rpc_notif_mspw-segment-config-params;
    leaf policy-name {
      when "../target-fec-type = 'sr-policy-fec'" {
        tailf:xpath-root 3;
      }
      type string;
      description
        "SR policy name.";
    }
    leaf color {
      when "../target-fec-type = 'sr-policy-fec'" {
        tailf:xpath-root 3;
      }
      type string;
      description
        "Color associated with the SR policy.";
    }
    leaf endpoint {
      when "../target-fec-type = 'sr-policy-fec'" {
        tailf:xpath-root 3;
      }
      type string;
      description
        "SR policy end point IP address.";
    }
    description
      "Oam Ping Session data";
  }

  grouping ncs_rpc_notif_oam-ping-config {
    leaf target-fec-type {
      type oam-options:ncs_rpc_notif_oam-target-fec-type;
      description
        "Target fec type";
    }
    choice target-fec {
      case vrf-fec {
        leaf vrf-name {
          when "../target-fec-type = 'vrf-fec'" {
            tailf:xpath-root 3;
          }
          type string;
          description
            "VRF name";
        }
        leaf vrf-dst {
          when "../target-fec-type = 'vrf-fec'" {
            tailf:xpath-root 3;
          }
          type inet:ip-address;
          description
            "VRF Destination IP";
        }
      }
      case target-ip {
        leaf ip-address {
          when "../target-fec-type = 'ip-fec'" {
            tailf:xpath-root 3;
          }
          type inet:ip-address;
          description
            "Destination IP";
        }
      }
      case ldp-fec {
        leaf ldp {
          when "../target-fec-type = 'ldp-fec'" {
            tailf:xpath-root 3;
          }
          type inet:ip-prefix;
          description
            "LDP FEC";
        }
      }
      case bgp-lu-fec {
        leaf bgp-lu {
          when "../target-fec-type = 'bgp-lu-fec'" {
            tailf:xpath-root 3;
          }
          type inet:ip-prefix;
          description
            "BGP LU FEC";
        }
      }
      case sr-isis-fec {
        leaf sr-isis {
          when "../target-fec-type = 'sr-isis-fec'" {
            tailf:xpath-root 3;
          }
          type inet:ip-prefix;
          description
            "SR ISIS FEC";
        }
      }
      case sr-ospf-fec {
        leaf sr-ospf {
          when "../target-fec-type = 'sr-ospf-fec'" {
            tailf:xpath-root 3;
          }
          type inet:ip-prefix;
          description
            "SR OSPF FEC";
        }
      }
      case tunnel-fec {
        leaf tunnel-name {
          when "../target-fec-type = 'scrt-fec'" {
            tailf:xpath-root 3;
          }
          type string;
          mandatory true;
          description
            "Tunnel Name";
        }
        leaf tunnel-src {
          when "../target-fec-type = 'scrt-fec'" {
            tailf:xpath-root 3;
          }
          type inet:ip-address;
          mandatory true;
          description
            "Tunnel Source Address";
        }
        leaf tunnel-dst {
          when "../target-fec-type = 'scrt-fec'" {
            tailf:xpath-root 3;
          }
          type inet:ip-address;
          mandatory true;
          description
            "Tunnel Destination Address";
        }
      }
      case pw {
        leaf pseudo-wire {
          when "../target-fec-type = 'pseudowire-fec'" {
            tailf:xpath-root 3;
          }
          type string;
          description
            "Pseudowire Name";
        }
      }
      case evpn-fec {
        leaf evpn-inst-id {
          when "../target-fec-type = 'evpn-fec'" {
            tailf:xpath-root 3;
          }
          type uint32 {
            range "1..65536";
          }
          mandatory true;
          description
            "Evpn Instance ID";
        }
        leaf ethernet-tag-id {
          when "../target-fec-type = 'evpn-fec'" {
            tailf:xpath-root 3;
          }
          type string {
            pattern '[1-9][0-9]{0,7}([.][1-9][0-9]{0,3})?';
          }
          mandatory true;
          description
            "Ethernet Tag Identifier.
             For EVPN FXC VPWS mode:
               -Remote Single VID format: <vid> eg. 111
               -Remote Double VID format: <vid>.<vid> eg. 111.222
               -Range of VID 1-4094
             For EVPN VPWS:
               -Remote ServiceId format: <Service-Id> eg. 627654
               -Range of Service Id 1-16777216";
        }
        leaf evpn-dst {
          when "../target-fec-type = 'evpn-fec'" {
            tailf:xpath-root 3;
          }
          type inet:ip-address;
          mandatory true;
          description
            "Evpn Destination Prefix";
        }
        leaf ethernet-segment-identifier {
          when "../target-fec-type = 'evpn-fec'" {
            tailf:xpath-root 3;
          }
          type yang:hex-string {
            length "29";
          }
          description
            "10-octet Ethernet segment identifier (esi),
             format: XX:XX:XX:XX:XX:XX:XX:XX:XX:XX
             This is remote ESI required only for ping to multihomed device";
        }
      }
      case sr-policy-fec {
        leaf policy-name {
          when "../target-fec-type = 'sr-policy-fec' and not(../color or ../endpoint)" {
            tailf:xpath-root 3;
          }
          type string;
          description
            "Reference to SR policy name.
             Policy name is mutually exclusive with color and endpoint.";
        }
        leaf color {
          when "../target-fec-type = 'sr-policy-fec' and not(../policy-name)" {
            tailf:xpath-root 3;
          }
          type string;
          description
            "Reference to color associated with the SR policy.
             Color and endpoint are mutually exclusive with policy name.";
        }
        leaf endpoint {
          when "../target-fec-type = 'sr-policy-fec' and (../color) and not(../policy-name)" {
            tailf:xpath-root 3;
          }
          type string;
          description
            "Reference to SR policy end point IP address.
             Endpoint and color are mutually exclusive with policy name.";
        }
      }
      description
        "Choice for FEC type in MPLS ping";
    }
    leaf backup {
      when "../target-fec-type = 'sr-ospf-fec' or
../target-fec-type = 'sr-isis-fec' or
../target-fec-type = 'bgp-lu-fec' or
../target-fec-type = 'ldp-fec' " {
        tailf:xpath-root 3;
      }
      type boolean;
      default "false";
      description
        "It will be used to ping backup LSP path";
    }
    uses oam-options:ncs_rpc_notif_oam-base-config-params;
    uses ncs_rpc_notif_oam-mpls-config-params {
      when "target-fec-type != 'ip-fec' or
target-fec-type != 'vrf-fec'" {
        tailf:xpath-root 3;
      }
    }
    leaf interface {
      when "../target-fec-type = 'ip-fec'" {
        tailf:xpath-root 3;
      }
      type string;
      description
        "Source interface name";
    }
    leaf echo-packet-size {
      when "../target-fec-type != 'ip-fec' and
../target-fec-type != 'vrf-fec'" {
        tailf:xpath-root 3;
      }
      type uint16 {
        range "52..1452";
      }
      units "bytes";
      description
        "Specifies the size of the echo payload to be
         transmitted in each MPLS ping request. Actual
         echo payload shall be larger than specified
         value if it is smaller than minimum size needed
         to hold the TLVs of ping request.";
    }
    uses ncs_rpc_notif_mspw-segment-config-params;
    description
      "Ping Configuration";
  }

  grouping ncs_rpc_notif_oam-ping-results {
    leaf operational-state {
      type oam-options:ncs_rpc_notif_operational-state;
      description
        "Operational state of the Ping test.";
    }
    leaf min-rtt {
      type decimal64 {
        fraction-digits 2;
      }
      units "milliseconds";
      description
        "The minimum Ping round-trip-time(RTT) received.";
    }
    leaf max-rtt {
      type decimal64 {
        fraction-digits 2;
      }
      units "milliseconds";
      description
        "The maximum Ping round-trip-time(RTT) received.";
    }
    leaf average-rtt {
      type decimal64 {
        fraction-digits 2;
      }
      units "milliseconds";
      description
        "The current average Ping round-trip-time(RTT).";
    }
    leaf echo-requests-sent {
      type uint8;
      description
        "Number of echo request sent for the Ping test.";
    }
    leaf echo-replies-received {
      type uint8;
      description
        "Number of echo replies received for corresponding Ping test.";
    }
    leaf last-good-reply {
      type yang:date-and-time;
      description
        "Date and time when the last response was received for
         an echo request.";
    }
    description
      "Ping Results Information";
  }

  grouping ncs_rpc_notif_oam-ping-probe-results {
    leaf probe-index {
      type uint8;
      description
        "Probe index.";
    }
    leaf return-code {
      type oam-options:ncs_rpc_notif_oam-return-code;
      description
        "The Return Code set in the echo reply. This is as per IANA defined error codes.";
    }
    leaf return-sub-code {
      type uint8;
      description
        "The Return Sub-code set in the echo reply.";
    }
    leaf rtt {
      type decimal64 {
        fraction-digits 2;
      }
      units "milliseconds";
      description
        "The round-trip-time (RTT) received.";
    }
    leaf result-type {
      type oam-options:ncs_rpc_notif_oam-result-type;
      description
        "The probe result success/failure or any other error.";
    }
    description
      "Ping Probe's Result Information";
  }

  grouping live_ncs_mspw-segment-config-params {
    leaf segment {
      // NCS drop when statement
      type uint8 {
        range "1..255";
      }
      // NCS drop default statement
      description
        "Segment number corresponding to the target PW hop
         in the MSPW path. This value is filled in TTL of
         PW label header and in TTL-TLV value of echo
         request.";
    }
    leaf segment-pseudowire-id {
      // NCS drop when statement
      type uint32 {
        range "1..4294967295";
      }
      description
        "PW-ID of target node to be pinged.";
    }
    leaf segment-source-ip {
      // NCS drop when statement
      type inet:ip-address;
      description
        "Loopback IP of PW hop immediately before the
         target node.";
    }
    leaf segment-destination-ip {
      // NCS drop when statement
      type inet:ip-address;
      description
        "Loopback IP of target node to be pinged.";
    }
  }

  grouping live_ncs_oam-mpls-config-params {
    leaf fec-stack-validation {
      type oam-options:live_ncs_fec-verification-state;
      description
        "To validate the downstream FEC path.";
    }
    leaf reverse-fec-stack-validation {
      type oam-options:live_ncs_fec-verification-state;
      description
        "To validate upstream FEC path.";
    }
    leaf encap {
      type oam-options:live_ncs_encap-ip-udp;
      description
        "Encapsulation: ip/udp, if ip/udp needs to be used in frame.
         non-ip/udp, when it does not need ip/udp in frame.";
    }
    description
      "Advanced parameters for MPLS Ping";
  }

  grouping live_ncs_oam-ping-session-data {
    leaf target-fec-type {
      type oam-options:live_ncs_oam-target-fec-type;
      description
        "Target fec type";
    }
    leaf vrf-name {
      // NCS drop when statement
      type string;
      description
        "VRF name";
    }
    leaf pseudo-wire {
      // NCS drop when statement
      type string;
      description
        "Pseudowire Name";
    }
    leaf tunnel-name {
      // NCS drop when statement
      type string;
      description
        "Tunnel name";
    }
    leaf tunnel-src {
      // NCS drop when statement
      type inet:ip-address;
      description
        "Tunnel Source Ip Address";
    }
    leaf tunnel-dst {
      // NCS drop when statement
      type inet:ip-address;
      description
        "Tunnel Destintion Ip Address";
    }
    leaf evpn-inst-id {
      // NCS drop when statement
      type uint32 {
        range "1..65536";
      }
      description
        "Evpn Instance ID";
    }
    leaf ethernet-tag-id {
      // NCS drop when statement
      type string {
        pattern '[1-9][0-9]{0,7}([.][1-9][0-9]{0,3})?';
      }
      description
        "Ethernet Tag Identifier.
         For EVPN FXC VPWS mode:
           -Remote Single VID format: <vid> eg. 111
           -Remote Double VID format: <vid>.<vid> eg. 111.222
           -Range of VID 1-4094
         For EVPN VPWS:
           -Remote ServiceId format: <Service-Id> eg. 627654
           -Range of Service Id 1-16777216";
    }
    leaf evpn-dst {
      // NCS drop when statement
      type inet:ip-address;
      description
        "Evpn Destination Prefix";
    }
    leaf ethernet-segment-identifier {
      // NCS drop when statement
      type yang:hex-string {
        length "29";
      }
      description
        "10-octet Ethernet segment identifier (esi) of remote node,
         format: XX:XX:XX:XX:XX:XX:XX:XX:XX:XX
         This is remote ESI required only for ping to multihomed device";
    }
    leaf destination-ip {
      // NCS drop when statement
      type inet:ip-address;
      description
        "IP address of the destination host. For IPv6, when doing ping
         to a link-local scope address, source interface is required.";
    }
    leaf destination-ip-prefix {
      // NCS drop when statement
      type inet:ip-prefix;
      description
        "Destination Ip prefix for ldp/sr-isis/sr-ospf/bgp-lu lsp";
    }
    leaf backup {
      // NCS drop when statement
      type boolean;
      description
        "It will be used to ping backup LSP path";
    }
    uses oam-options:live_ncs_oam-base-config-params;
    uses live_ncs_oam-mpls-config-params {
      // NCS drop when statement
    }
    leaf interface {
      // NCS drop when statement
      type leafref {
        path "/ncs:devices/ncs:device/ncs:live-status/oc-if:interfaces/oc-if:interface/oc-if:name" {
          tailf:xpath-root 3;
        }
      }
      description
        "Source interface name";
    }
    leaf echo-packet-size {
      // NCS drop when statement
      type uint16 {
        range "52..1452";
      }
      units "bytes";
      description
        "Specifies the size of the echo payload to be
         transmitted in each MPLS ping request. Actual
         echo payload shall be larger than specified
         value if it is smaller than minimum size needed
         to hold the TLVs of ping request.";
    }
    uses live_ncs_mspw-segment-config-params;
    leaf policy-name {
      // NCS drop when statement
      type leafref {
        path "/ncs:devices/ncs:device/ncs:live-status/cnsr:segment-routing-traffic-engineering/cnsr:policies/cnsr:policy/cnsr:name" {
          tailf:xpath-root 3;
        }
      }
      description
        "SR policy name.";
    }
    leaf color {
      // NCS drop when statement
      type leafref {
        path "/ncs:devices/ncs:device/ncs:live-status/cnsr:segment-routing-traffic-engineering/cnsr:policies/cnsr:policy/cnsr:color" {
          tailf:xpath-root 3;
        }
      }
      description
        "Color associated with the SR policy.";
    }
    leaf endpoint {
      // NCS drop when statement
      type leafref {
        path "/ncs:devices/ncs:device/ncs:live-status/cnsr:segment-routing-traffic-engineering/cnsr:policies/cnsr:policy/cnsr:endpoint" {
          tailf:xpath-root 3;
        }
      }
      description
        "SR policy end point IP address.";
    }
    description
      "Oam Ping Session data";
  }

  grouping live_ncs_oam-ping-config {
    leaf target-fec-type {
      type oam-options:live_ncs_oam-target-fec-type;
      description
        "Target fec type";
    }
    choice target-fec {
      case vrf-fec {
        leaf vrf-name {
          // NCS drop when statement
          type string;
          description
            "VRF name";
        }
        leaf vrf-dst {
          // NCS drop when statement
          type inet:ip-address;
          description
            "VRF Destination IP";
        }
      }
      case target-ip {
        leaf ip-address {
          // NCS drop when statement
          type inet:ip-address;
          description
            "Destination IP";
        }
      }
      case ldp-fec {
        leaf ldp {
          // NCS drop when statement
          type inet:ip-prefix;
          description
            "LDP FEC";
        }
      }
      case bgp-lu-fec {
        leaf bgp-lu {
          // NCS drop when statement
          type inet:ip-prefix;
          description
            "BGP LU FEC";
        }
      }
      case sr-isis-fec {
        leaf sr-isis {
          // NCS drop when statement
          type inet:ip-prefix;
          description
            "SR ISIS FEC";
        }
      }
      case sr-ospf-fec {
        leaf sr-ospf {
          // NCS drop when statement
          type inet:ip-prefix;
          description
            "SR OSPF FEC";
        }
      }
      case tunnel-fec {
        leaf tunnel-name {
          // NCS drop when statement
          type string;
          // NCS drop mandatory statement
          description
            "Tunnel Name";
        }
        leaf tunnel-src {
          // NCS drop when statement
          type inet:ip-address;
          // NCS drop mandatory statement
          description
            "Tunnel Source Address";
        }
        leaf tunnel-dst {
          // NCS drop when statement
          type inet:ip-address;
          // NCS drop mandatory statement
          description
            "Tunnel Destination Address";
        }
      }
      case pw {
        leaf pseudo-wire {
          // NCS drop when statement
          type string;
          description
            "Pseudowire Name";
        }
      }
      case evpn-fec {
        leaf evpn-inst-id {
          // NCS drop when statement
          type uint32 {
            range "1..65536";
          }
          // NCS drop mandatory statement
          description
            "Evpn Instance ID";
        }
        leaf ethernet-tag-id {
          // NCS drop when statement
          type string {
            pattern '[1-9][0-9]{0,7}([.][1-9][0-9]{0,3})?';
          }
          // NCS drop mandatory statement
          description
            "Ethernet Tag Identifier.
             For EVPN FXC VPWS mode:
               -Remote Single VID format: <vid> eg. 111
               -Remote Double VID format: <vid>.<vid> eg. 111.222
               -Range of VID 1-4094
             For EVPN VPWS:
               -Remote ServiceId format: <Service-Id> eg. 627654
               -Range of Service Id 1-16777216";
        }
        leaf evpn-dst {
          // NCS drop when statement
          type inet:ip-address;
          // NCS drop mandatory statement
          description
            "Evpn Destination Prefix";
        }
        leaf ethernet-segment-identifier {
          // NCS drop when statement
          type yang:hex-string {
            length "29";
          }
          description
            "10-octet Ethernet segment identifier (esi),
             format: XX:XX:XX:XX:XX:XX:XX:XX:XX:XX
             This is remote ESI required only for ping to multihomed device";
        }
      }
      case sr-policy-fec {
        leaf policy-name {
          // NCS drop when statement
          type leafref {
            path "/ncs:devices/ncs:device/ncs:live-status/cnsr:segment-routing-traffic-engineering/cnsr:policies/cnsr:policy/cnsr:name" {
              tailf:xpath-root 3;
            }
          }
          description
            "Reference to SR policy name.
             Policy name is mutually exclusive with color and endpoint.";
        }
        leaf color {
          // NCS drop when statement
          type leafref {
            path "/ncs:devices/ncs:device/ncs:live-status/cnsr:segment-routing-traffic-engineering/cnsr:policies/cnsr:policy/cnsr:color" {
              tailf:xpath-root 3;
            }
          }
          description
            "Reference to color associated with the SR policy.
             Color and endpoint are mutually exclusive with policy name.";
        }
        leaf endpoint {
          // NCS drop when statement
          type leafref {
            path "/ncs:devices/ncs:device/ncs:live-status/cnsr:segment-routing-traffic-engineering/cnsr:policies/cnsr:policy/cnsr:endpoint" {
              tailf:xpath-root 3;
            }
          }
          description
            "Reference to SR policy end point IP address.
             Endpoint and color are mutually exclusive with policy name.";
        }
      }
      description
        "Choice for FEC type in MPLS ping";
    }
    leaf backup {
      // NCS drop when statement
      type boolean;
      // NCS drop default statement
      description
        "It will be used to ping backup LSP path";
    }
    uses oam-options:live_ncs_oam-base-config-params;
    uses live_ncs_oam-mpls-config-params {
      // NCS drop when statement
    }
    leaf interface {
      // NCS drop when statement
      type leafref {
        path "/ncs:devices/ncs:device/ncs:live-status/oc-if:interfaces/oc-if:interface/oc-if:name" {
          tailf:xpath-root 3;
        }
      }
      description
        "Source interface name";
    }
    leaf echo-packet-size {
      // NCS drop when statement
      type uint16 {
        range "52..1452";
      }
      units "bytes";
      description
        "Specifies the size of the echo payload to be
         transmitted in each MPLS ping request. Actual
         echo payload shall be larger than specified
         value if it is smaller than minimum size needed
         to hold the TLVs of ping request.";
    }
    uses live_ncs_mspw-segment-config-params;
    description
      "Ping Configuration";
  }

  grouping live_ncs_oam-ping-results {
    leaf operational-state {
      type oam-options:live_ncs_operational-state;
      description
        "Operational state of the Ping test.";
    }
    leaf min-rtt {
      type decimal64 {
        fraction-digits 2;
      }
      units "milliseconds";
      description
        "The minimum Ping round-trip-time(RTT) received.";
    }
    leaf max-rtt {
      type decimal64 {
        fraction-digits 2;
      }
      units "milliseconds";
      description
        "The maximum Ping round-trip-time(RTT) received.";
    }
    leaf average-rtt {
      type decimal64 {
        fraction-digits 2;
      }
      units "milliseconds";
      description
        "The current average Ping round-trip-time(RTT).";
    }
    leaf echo-requests-sent {
      type uint8;
      description
        "Number of echo request sent for the Ping test.";
    }
    leaf echo-replies-received {
      type uint8;
      description
        "Number of echo replies received for corresponding Ping test.";
    }
    leaf last-good-reply {
      type yang:date-and-time;
      description
        "Date and time when the last response was received for
         an echo request.";
    }
    description
      "Ping Results Information";
  }

  grouping live_ncs_oam-ping-probe-results {
    leaf probe-index {
      type uint8;
      description
        "Probe index.";
    }
    leaf return-code {
      type oam-options:live_ncs_oam-return-code;
      description
        "The Return Code set in the echo reply. This is as per IANA defined error codes.";
    }
    leaf return-sub-code {
      type uint8;
      description
        "The Return Sub-code set in the echo reply.";
    }
    leaf rtt {
      type decimal64 {
        fraction-digits 2;
      }
      units "milliseconds";
      description
        "The round-trip-time (RTT) received.";
    }
    leaf result-type {
      type oam-options:live_ncs_oam-result-type;
      description
        "The probe result success/failure or any other error.";
    }
    description
      "Ping Probe's Result Information";
  }

  grouping mspw-segment-config-params {
    leaf segment {
      when "../target-fec-type = 'pseudowire-fec'" {
        tailf:xpath-root 3;
      }
      type uint8 {
        range "1..255";
      }
      default "1";
      description
        "Segment number corresponding to the target PW hop
         in the MSPW path. This value is filled in TTL of
         PW label header and in TTL-TLV value of echo
         request.";
    }
    leaf segment-pseudowire-id {
      when "../target-fec-type = 'pseudowire-fec'" {
        tailf:xpath-root 3;
      }
      type uint32 {
        range "1..4294967295";
      }
      description
        "PW-ID of target node to be pinged.";
    }
    leaf segment-source-ip {
      when "../target-fec-type = 'pseudowire-fec'" {
        tailf:xpath-root 3;
      }
      type inet:ip-address;
      description
        "Loopback IP of PW hop immediately before the
         target node.";
    }
    leaf segment-destination-ip {
      when "../target-fec-type = 'pseudowire-fec'" {
        tailf:xpath-root 3;
      }
      type inet:ip-address;
      description
        "Loopback IP of target node to be pinged.";
    }
  }

  grouping oam-mpls-config-params {
    leaf fec-stack-validation {
      type oam-options:fec-verification-state;
      description
        "To validate the downstream FEC path.";
    }
    leaf reverse-fec-stack-validation {
      type oam-options:fec-verification-state;
      description
        "To validate upstream FEC path.";
    }
    leaf encap {
      type oam-options:encap-ip-udp;
      description
        "Encapsulation: ip/udp, if ip/udp needs to be used in frame.
         non-ip/udp, when it does not need ip/udp in frame.";
    }
    description
      "Advanced parameters for MPLS Ping";
  }

  grouping oam-ping-session-data {
    leaf target-fec-type {
      type oam-options:oam-target-fec-type;
      description
        "Target fec type";
    }
    leaf vrf-name {
      when "../target-fec-type = 'vrf-fec'" {
        tailf:xpath-root 3;
      }
      type string;
      description
        "VRF name";
    }
    leaf pseudo-wire {
      when "../target-fec-type = 'pseudowire-fec'" {
        tailf:xpath-root 3;
      }
      type string;
      description
        "Pseudowire Name";
    }
    leaf tunnel-name {
      when "../target-fec-type = 'scrt-fec'" {
        tailf:xpath-root 3;
      }
      type string;
      description
        "Tunnel name";
    }
    leaf tunnel-src {
      when "../target-fec-type = 'scrt-fec'" {
        tailf:xpath-root 3;
      }
      type inet:ip-address;
      description
        "Tunnel Source Ip Address";
    }
    leaf tunnel-dst {
      when "../target-fec-type = 'scrt-fec'" {
        tailf:xpath-root 3;
      }
      type inet:ip-address;
      description
        "Tunnel Destintion Ip Address";
    }
    leaf evpn-inst-id {
      when "../target-fec-type = 'evpn-fec'" {
        tailf:xpath-root 3;
      }
      type uint32 {
        range "1..65536";
      }
      description
        "Evpn Instance ID";
    }
    leaf ethernet-tag-id {
      when "../target-fec-type = 'evpn-fec'" {
        tailf:xpath-root 3;
      }
      type string {
        pattern '[1-9][0-9]{0,7}([.][1-9][0-9]{0,3})?';
      }
      description
        "Ethernet Tag Identifier.
         For EVPN FXC VPWS mode:
           -Remote Single VID format: <vid> eg. 111
           -Remote Double VID format: <vid>.<vid> eg. 111.222
           -Range of VID 1-4094
         For EVPN VPWS:
           -Remote ServiceId format: <Service-Id> eg. 627654
           -Range of Service Id 1-16777216";
    }
    leaf evpn-dst {
      when "../target-fec-type = 'evpn-fec'" {
        tailf:xpath-root 3;
      }
      type inet:ip-address;
      description
        "Evpn Destination Prefix";
    }
    leaf ethernet-segment-identifier {
      when "../target-fec-type = 'evpn-fec'" {
        tailf:xpath-root 3;
      }
      type yang:hex-string {
        length "29";
      }
      description
        "10-octet Ethernet segment identifier (esi) of remote node,
         format: XX:XX:XX:XX:XX:XX:XX:XX:XX:XX
         This is remote ESI required only for ping to multihomed device";
    }
    leaf destination-ip {
      when "../target-fec-type = 'ip-fec' or
../target-fec-type = 'vrf-fec'" {
        tailf:xpath-root 3;
      }
      type inet:ip-address;
      description
        "IP address of the destination host. For IPv6, when doing ping
         to a link-local scope address, source interface is required.";
    }
    leaf destination-ip-prefix {
      when "../target-fec-type != 'ip-fec' or
../target-fec-type != 'vrf-fec' or
../target-fec-type != 'scrt-fec' or
../target-fec-type != 'evpn-fec'" {
        tailf:xpath-root 3;
      }
      type inet:ip-prefix;
      description
        "Destination Ip prefix for ldp/sr-isis/sr-ospf/bgp-lu lsp";
    }
    leaf backup {
      when "../target-fec-type = 'sr-ospf-fec' or
../target-fec-type = 'sr-isis-fec' or
../target-fec-type = 'bgp-lu-fec' or
../target-fec-type = 'ldp-fec' " {
        tailf:xpath-root 3;
      }
      type boolean;
      description
        "It will be used to ping backup LSP path";
    }
    uses oam-options:oam-base-config-params;
    uses oam-mpls-config-params {
      when "target-fec-type != 'ip-fec' or
target-fec-type != 'vrf-fec'" {
        tailf:xpath-root 3;
      }
    }
    leaf interface {
      when "../target-fec-type = 'ip-fec'" {
        tailf:xpath-root 3;
      }
      type leafref {
        path "/ncs:devices/ncs:device/ncs:config/oc-if:interfaces/oc-if:interface/oc-if:name" {
          tailf:xpath-root 3;
        }
      }
      description
        "Source interface name";
    }
    leaf echo-packet-size {
      when "../target-fec-type != 'ip-fec' and
../target-fec-type != 'vrf-fec'" {
        tailf:xpath-root 3;
      }
      type uint16 {
        range "52..1452";
      }
      units "bytes";
      description
        "Specifies the size of the echo payload to be
         transmitted in each MPLS ping request. Actual
         echo payload shall be larger than specified
         value if it is smaller than minimum size needed
         to hold the TLVs of ping request.";
    }
    uses mspw-segment-config-params;
    leaf policy-name {
      when "../target-fec-type = 'sr-policy-fec'" {
        tailf:xpath-root 3;
      }
      type leafref {
        path "/ncs:devices/ncs:device/ncs:config/cnsr:segment-routing-traffic-engineering/cnsr:policies/cnsr:policy/cnsr:name" {
          tailf:xpath-root 3;
        }
      }
      description
        "SR policy name.";
    }
    leaf color {
      when "../target-fec-type = 'sr-policy-fec'" {
        tailf:xpath-root 3;
      }
      type leafref {
        path "/ncs:devices/ncs:device/ncs:config/cnsr:segment-routing-traffic-engineering/cnsr:policies/cnsr:policy/cnsr:color" {
          tailf:xpath-root 3;
        }
      }
      description
        "Color associated with the SR policy.";
    }
    leaf endpoint {
      when "../target-fec-type = 'sr-policy-fec'" {
        tailf:xpath-root 3;
      }
      type leafref {
        path "/ncs:devices/ncs:device/ncs:config/cnsr:segment-routing-traffic-engineering/cnsr:policies/cnsr:policy/cnsr:endpoint" {
          tailf:xpath-root 3;
        }
      }
      description
        "SR policy end point IP address.";
    }
    description
      "Oam Ping Session data";
  }

  grouping oam-ping-config {
    leaf target-fec-type {
      type oam-options:oam-target-fec-type;
      description
        "Target fec type";
    }
    choice target-fec {
      case vrf-fec {
        leaf vrf-name {
          when "../target-fec-type = 'vrf-fec'" {
            tailf:xpath-root 3;
          }
          type string;
          description
            "VRF name";
        }
        leaf vrf-dst {
          when "../target-fec-type = 'vrf-fec'" {
            tailf:xpath-root 3;
          }
          type inet:ip-address;
          description
            "VRF Destination IP";
        }
      }
      case target-ip {
        leaf ip-address {
          when "../target-fec-type = 'ip-fec'" {
            tailf:xpath-root 3;
          }
          type inet:ip-address;
          description
            "Destination IP";
        }
      }
      case ldp-fec {
        leaf ldp {
          when "../target-fec-type = 'ldp-fec'" {
            tailf:xpath-root 3;
          }
          type inet:ip-prefix;
          description
            "LDP FEC";
        }
      }
      case bgp-lu-fec {
        leaf bgp-lu {
          when "../target-fec-type = 'bgp-lu-fec'" {
            tailf:xpath-root 3;
          }
          type inet:ip-prefix;
          description
            "BGP LU FEC";
        }
      }
      case sr-isis-fec {
        leaf sr-isis {
          when "../target-fec-type = 'sr-isis-fec'" {
            tailf:xpath-root 3;
          }
          type inet:ip-prefix;
          description
            "SR ISIS FEC";
        }
      }
      case sr-ospf-fec {
        leaf sr-ospf {
          when "../target-fec-type = 'sr-ospf-fec'" {
            tailf:xpath-root 3;
          }
          type inet:ip-prefix;
          description
            "SR OSPF FEC";
        }
      }
      case tunnel-fec {
        leaf tunnel-name {
          when "../target-fec-type = 'scrt-fec'" {
            tailf:xpath-root 3;
          }
          type string;
          mandatory true;
          description
            "Tunnel Name";
        }
        leaf tunnel-src {
          when "../target-fec-type = 'scrt-fec'" {
            tailf:xpath-root 3;
          }
          type inet:ip-address;
          mandatory true;
          description
            "Tunnel Source Address";
        }
        leaf tunnel-dst {
          when "../target-fec-type = 'scrt-fec'" {
            tailf:xpath-root 3;
          }
          type inet:ip-address;
          mandatory true;
          description
            "Tunnel Destination Address";
        }
      }
      case pw {
        leaf pseudo-wire {
          when "../target-fec-type = 'pseudowire-fec'" {
            tailf:xpath-root 3;
          }
          type string;
          description
            "Pseudowire Name";
        }
      }
      case evpn-fec {
        leaf evpn-inst-id {
          when "../target-fec-type = 'evpn-fec'" {
            tailf:xpath-root 3;
          }
          type uint32 {
            range "1..65536";
          }
          mandatory true;
          description
            "Evpn Instance ID";
        }
        leaf ethernet-tag-id {
          when "../target-fec-type = 'evpn-fec'" {
            tailf:xpath-root 3;
          }
          type string {
            pattern '[1-9][0-9]{0,7}([.][1-9][0-9]{0,3})?';
          }
          mandatory true;
          description
            "Ethernet Tag Identifier.
             For EVPN FXC VPWS mode:
               -Remote Single VID format: <vid> eg. 111
               -Remote Double VID format: <vid>.<vid> eg. 111.222
               -Range of VID 1-4094
             For EVPN VPWS:
               -Remote ServiceId format: <Service-Id> eg. 627654
               -Range of Service Id 1-16777216";
        }
        leaf evpn-dst {
          when "../target-fec-type = 'evpn-fec'" {
            tailf:xpath-root 3;
          }
          type inet:ip-address;
          mandatory true;
          description
            "Evpn Destination Prefix";
        }
        leaf ethernet-segment-identifier {
          when "../target-fec-type = 'evpn-fec'" {
            tailf:xpath-root 3;
          }
          type yang:hex-string {
            length "29";
          }
          description
            "10-octet Ethernet segment identifier (esi),
             format: XX:XX:XX:XX:XX:XX:XX:XX:XX:XX
             This is remote ESI required only for ping to multihomed device";
        }
      }
      case sr-policy-fec {
        leaf policy-name {
          when "../target-fec-type = 'sr-policy-fec' and not(../color or ../endpoint)" {
            tailf:xpath-root 3;
          }
          type leafref {
            path "/ncs:devices/ncs:device/ncs:config/cnsr:segment-routing-traffic-engineering/cnsr:policies/cnsr:policy/cnsr:name" {
              tailf:xpath-root 3;
            }
          }
          description
            "Reference to SR policy name.
             Policy name is mutually exclusive with color and endpoint.";
        }
        leaf color {
          when "../target-fec-type = 'sr-policy-fec' and not(../policy-name)" {
            tailf:xpath-root 3;
          }
          type leafref {
            path "/ncs:devices/ncs:device/ncs:config/cnsr:segment-routing-traffic-engineering/cnsr:policies/cnsr:policy/cnsr:color" {
              tailf:xpath-root 3;
            }
          }
          description
            "Reference to color associated with the SR policy.
             Color and endpoint are mutually exclusive with policy name.";
        }
        leaf endpoint {
          when "../target-fec-type = 'sr-policy-fec' and (../color) and not(../policy-name)" {
            tailf:xpath-root 3;
          }
          type leafref {
            path "/ncs:devices/ncs:device/ncs:config/cnsr:segment-routing-traffic-engineering/cnsr:policies/cnsr:policy/cnsr:endpoint" {
              tailf:xpath-root 3;
            }
          }
          description
            "Reference to SR policy end point IP address.
             Endpoint and color are mutually exclusive with policy name.";
        }
      }
      description
        "Choice for FEC type in MPLS ping";
    }
    leaf backup {
      when "../target-fec-type = 'sr-ospf-fec' or
../target-fec-type = 'sr-isis-fec' or
../target-fec-type = 'bgp-lu-fec' or
../target-fec-type = 'ldp-fec' " {
        tailf:xpath-root 3;
      }
      type boolean;
      default "false";
      description
        "It will be used to ping backup LSP path";
    }
    uses oam-options:oam-base-config-params;
    uses oam-mpls-config-params {
      when "target-fec-type != 'ip-fec' or
target-fec-type != 'vrf-fec'" {
        tailf:xpath-root 3;
      }
    }
    leaf interface {
      when "../target-fec-type = 'ip-fec'" {
        tailf:xpath-root 3;
      }
      type leafref {
        path "/ncs:devices/ncs:device/ncs:config/oc-if:interfaces/oc-if:interface/oc-if:name" {
          tailf:xpath-root 3;
        }
      }
      description
        "Source interface name";
    }
    leaf echo-packet-size {
      when "../target-fec-type != 'ip-fec' and
../target-fec-type != 'vrf-fec'" {
        tailf:xpath-root 3;
      }
      type uint16 {
        range "52..1452";
      }
      units "bytes";
      description
        "Specifies the size of the echo payload to be
         transmitted in each MPLS ping request. Actual
         echo payload shall be larger than specified
         value if it is smaller than minimum size needed
         to hold the TLVs of ping request.";
    }
    uses mspw-segment-config-params;
    description
      "Ping Configuration";
  }

  grouping oam-ping-results {
    leaf operational-state {
      type oam-options:operational-state;
      description
        "Operational state of the Ping test.";
    }
    leaf min-rtt {
      type decimal64 {
        fraction-digits 2;
      }
      units "milliseconds";
      description
        "The minimum Ping round-trip-time(RTT) received.";
    }
    leaf max-rtt {
      type decimal64 {
        fraction-digits 2;
      }
      units "milliseconds";
      description
        "The maximum Ping round-trip-time(RTT) received.";
    }
    leaf average-rtt {
      type decimal64 {
        fraction-digits 2;
      }
      units "milliseconds";
      description
        "The current average Ping round-trip-time(RTT).";
    }
    leaf echo-requests-sent {
      type uint8;
      description
        "Number of echo request sent for the Ping test.";
    }
    leaf echo-replies-received {
      type uint8;
      description
        "Number of echo replies received for corresponding Ping test.";
    }
    leaf last-good-reply {
      type yang:date-and-time;
      description
        "Date and time when the last response was received for
         an echo request.";
    }
    description
      "Ping Results Information";
  }

  grouping oam-ping-probe-results {
    leaf probe-index {
      type uint8;
      description
        "Probe index.";
    }
    leaf return-code {
      type oam-options:oam-return-code;
      description
        "The Return Code set in the echo reply. This is as per IANA defined error codes.";
    }
    leaf return-sub-code {
      type uint8;
      description
        "The Return Sub-code set in the echo reply.";
    }
    leaf rtt {
      type decimal64 {
        fraction-digits 2;
      }
      units "milliseconds";
      description
        "The round-trip-time (RTT) received.";
    }
    leaf result-type {
      type oam-options:oam-result-type;
      description
        "The probe result success/failure or any other error.";
    }
    description
      "Ping Probe's Result Information";
  }

  augment "/ncs:devices/ncs:device/ncs:rpc" {
    container rpc-cancel-ping {
      tailf:ncs-device-type "netconf";
      tailf:display-when "not(../../ncs:module) or ../../ncs:module[ncs:name='ciena-oam-ping']";
      tailf:action cancel-ping {
        tailf:actionpoint ncsproxy {
          tailf:internal;
        }
        description
          "RPC to cancel ping";
        input {
          leaf ping-session-id {
            type uint16;
            description
              "Auto-generated session id.";
          }
        }
        output {
          leaf response {
            type oam-options:ncs_rpc_notif_oam-response-type;
            description
              "Status of the executed rpc. Success/Failure Message.";
          }
        }
      }
    }
  }
  augment "/ncs:devices/ncs:device-group/ncs:ned-id/ncs:rpc" {
    container rpc-cancel-ping {
      tailf:ncs-device-type "netconf";
      tailf:display-when "/ncs:devices/ncs:device[ncs:name=current()/../../../ncs:member]/ncs:module[ncs:name='ciena-oam-ping']";
      tailf:action cancel-ping {
        tailf:actionpoint ncsproxy {
          tailf:internal;
        }
        description
          "RPC to cancel ping";
        input {
          leaf ping-session-id {
            type uint16;
            description
              "Auto-generated session id.";
          }
        }
        output {
          container "device" {
            leaf "name" {
              type string;
            }
            leaf "info" {
              type string;
            }
            container "result" {
              leaf response {
                type oam-options:ncs_rpc_notif_oam-response-type;
                description
                  "Status of the executed rpc. Success/Failure Message.";
              }
            }
          }
        }
      }
    }
  }
  augment "/ncs:devices/ncs:device/ncs:rpc" {
    container rpc-delete-ping {
      tailf:ncs-device-type "netconf";
      tailf:display-when "not(../../ncs:module) or ../../ncs:module[ncs:name='ciena-oam-ping']";
      tailf:action delete-ping {
        tailf:actionpoint ncsproxy {
          tailf:internal;
        }
        description
          "RPC to delete ping";
        input {
          leaf ping-session-id {
            type uint16;
            description
              "Auto-generated session id.";
          }
        }
        output {
          leaf response {
            type oam-options:ncs_rpc_notif_oam-response-type;
            description
              "Status of the executed rpc. Success/Failure Message.";
          }
        }
      }
    }
  }
  augment "/ncs:devices/ncs:device-group/ncs:ned-id/ncs:rpc" {
    container rpc-delete-ping {
      tailf:ncs-device-type "netconf";
      tailf:display-when "/ncs:devices/ncs:device[ncs:name=current()/../../../ncs:member]/ncs:module[ncs:name='ciena-oam-ping']";
      tailf:action delete-ping {
        tailf:actionpoint ncsproxy {
          tailf:internal;
        }
        description
          "RPC to delete ping";
        input {
          leaf ping-session-id {
            type uint16;
            description
              "Auto-generated session id.";
          }
        }
        output {
          container "device" {
            leaf "name" {
              type string;
            }
            leaf "info" {
              type string;
            }
            container "result" {
              leaf response {
                type oam-options:ncs_rpc_notif_oam-response-type;
                description
                  "Status of the executed rpc. Success/Failure Message.";
              }
            }
          }
        }
      }
    }
  }
  augment "/ncs:devices/ncs:device/ncs:rpc" {
    container rpc-start-ping {
      tailf:ncs-device-type "netconf";
      tailf:display-when "not(../../ncs:module) or ../../ncs:module[ncs:name='ciena-oam-ping']";
      tailf:action start-ping {
        tailf:actionpoint ncsproxy {
          tailf:internal;
        }
        description
          "RPC to start ping";
        input {
          uses ncs_rpc_notif_oam-ping-config;
        }
        output {
          leaf ping-session-id {
            type uint16;
            description
              "Auto-generated ping-session-id on
               the basis of input options.";
          }
          leaf response {
            type oam-options:ncs_rpc_notif_oam-response-type;
            description
              "Status of the executed rpc. Success/Failure Message.";
          }
        }
      }
    }
  }
  augment "/ncs:devices/ncs:device-group/ncs:ned-id/ncs:rpc" {
    container rpc-start-ping {
      tailf:ncs-device-type "netconf";
      tailf:display-when "/ncs:devices/ncs:device[ncs:name=current()/../../../ncs:member]/ncs:module[ncs:name='ciena-oam-ping']";
      tailf:action start-ping {
        tailf:actionpoint ncsproxy {
          tailf:internal;
        }
        description
          "RPC to start ping";
        input {
          uses ncs_rpc_notif_oam-ping-config;
        }
        output {
          container "device" {
            leaf "name" {
              type string;
            }
            leaf "info" {
              type string;
            }
            container "result" {
              leaf ping-session-id {
                type uint16;
                description
                  "Auto-generated ping-session-id on
                   the basis of input options.";
              }
              leaf response {
                type oam-options:ncs_rpc_notif_oam-response-type;
                description
                  "Status of the executed rpc. Success/Failure Message.";
              }
            }
          }
        }
      }
    }
  }
  augment "/ncs:devices/ncs:device/ncs:config" {
    // NCS drop config false container 'oam-ping-sessions'
  }
  augment "/ncs:devices/ncs:device/ncs:live-status" {
    container oam-ping-sessions {
      tailf:ncs-device-type "netconf";
      tailf:display-when "not(../../ncs:module) or ../../ncs:module[ncs:name='ciena-oam-ping'] or (../../ncs:live-status-protocol[not(ncs:capability)]) or (../../ncs:live-status-protocol/ncs:capability/ncs:module[.='ciena-oam-ping'])";
      description
        "Multiple instances of ping tests.";
      list oam-ping-session {
        key "ping-session-id";
        description
          "Ping test";
        leaf ping-session-id {
          type uint16;
          description
            "Auto-generated session id for a ping session.";
        }
        container oam-ping-config-params {
          uses live_ncs_oam-ping-session-data;
          description
            "Configures Ping type and its parameters";
        }
        container ping-results {
          description
            "Ping test result information.";
          uses live_ncs_oam-ping-results;
          container ping-probe-results {
            description
              "Result information of each test probe.";
            list ping-probe-result {
              key "probe-index";
              description
                "Result info of each test probe.";
              uses live_ncs_oam-ping-probe-results;
            }
          }
        }
      }
    }
  }
  augment "/ncs:devices/ncs:template/ncs:ned-id/ncs:config" {
    // NCS drop config false container 'oam-ping-sessions'
  }
}
