module ciena-itut-g8032-draft {
  // Generated by yanger -t ncs
  tailf:mount-id "ciena107-nc-1.0:ciena107-nc-1.0";
  tailf:ncs-device-type "netconf";

  namespace "http://www.ciena.com/ns/yang/ciena-itut-g8032-draft";
  prefix g8032;

  import ietf-interfaces {
    prefix if;
  }
  import ieee802-dot1q-types {
    prefix dot1q-types;
  }
  import ieee-types {
    prefix ieee;
  }
  import ietf-yang-types {
    prefix yang;
  }
  import tailf-common {
    prefix tailf;
  }
  import tailf-ncs {
    prefix ncs;
  }

  organization
    "Ciena Corporation";
  contact
    "Ciena Corporation
      - Web URL: http://www.ciena.com/
      - E-mail:  yang@ciena.com
      - Postal:  7035 Ridge Road
               Hanover, Maryland 21076
               U.S.A.
      - Phone:   +1 800-921-1144
      - Fax:     +1 410-694-5750
    ";
  description
    "This YANG module describes configuration and operational
     data model for ITU.T G.8032 Ethernet Ring Protocol (ERP).

     G.8032 provides a loop avoidance and protection switching
     mechanism in ethernet ring network.

     An Ethernet ring node (which is assumed to be compliant to an
     IEEE 802.1Q bridge) is connected to adjacent Ethernet ring
     nodes participating in the same Ethernet ring, using two
     independent links. A ring link is bounded by two adjacent
     Ethernet ring nodes and a port for a ring link is called a
     ring port. The minimum number of Ethernet ring nodes in
     an Ethernet ring is two.

     An Automatic Protection Switching(APS) protocol is used to
     coordinate the protection actions over the ring.";

  revision 2020-09-21 {
    description
      "Changes to add backward support for telemetry notifications";
  }
  revision 2020-03-18 {
    description
      "Changes to support telemetry filtering";
  }
  revision 2016-04-06 {
    description
      "This YANG model describes the configuration and
       operational state information in support of G.8032.";
    reference "ITU-T G.8032/Y.1344 (08/2015)";
  }

  typedef ncs_template_rpl-type {
    type string;
    description
      "The disposition of the RPL ownership associated with a ring
       Interface.";
    reference "ITU-T G.8032/Y.1344 (08/2015); Section 10.1";
  }

  typedef ncs_template_reversion-mode {
    type string;
    description
      "This typedef defines G.8032 ring protection operation mode.";
    reference "ITU-T G.8032/Y.1344 (08/2015); Section 9.1, 10.2.3.1";
  }

  typedef ncs_template_ring-name-type {
    type string;
    description
      "The ring name type identifier.";
  }

  typedef ncs_template_ring-id-type {
    type string;
    // NCS drop default statement
    description
      "G.8032 Ring ID";
    reference "ITU-T G.8032/Y.1344 (08/2015); Section 10.1.1";
  }

  typedef ncs_template_ring-port-type {
    type string;
    description
      "Each ring instance has maximum of two ports. This definition
       labels these ports as port0 and port1 for identifications.";
    reference "ITU-T G.8032/Y.1344 (08/2015); Section 10.1 (Figure 10-1)";
  }

  typedef ncs_template_hold-off-timer-type {
    type string;
    units "milliseconds";
    // NCS drop default statement
    description
      "The hold-off timer is used to coordinate the timing of
       protection switches.

       When a new defect or more severe defect occurs (new SF), this
       event is not to be reported immediately to protection switching
       if the provisioned hold-off timer value is non-zero. Instead,
       the hold-off timer is started. When the hold-off timer expires,
       the trail that started the timer is checked as to whether a
       defect still exists. If one does exist, that defect is
       reported to protection switching.

       Hold off timer values SHOULD be specified in multiple of 100.";
    reference "ITU-T G.8032/Y.1344 (08/2015); Section 10.1.8";
  }

  typedef ncs_template_guard-timer-type {
    type string;
    units "milliseconds";
    // NCS drop default statement
    description
      "The guard timer is used to prevent Ethernet ring nodes from
       acting upon outdated R-APS messages and prevents the
       possibility of forming a closed loop.

       This timer period SHOULD be greater than the maximum expected
       forwarding delay in which an R-APS message traverses the
       entire ring.

       The period of the guard timer MAY be configured by the operator
       in 10 ms steps between 10 ms and 2 seconds.";
    reference "ITU-T G.8032/Y.1344 (08/2015); Section 10.1.5";
  }

  typedef ncs_template_wtr-timer-type {
    type string;
    units "minutes";
    // NCS drop default statement
    description
      "In revertive mode the 'wait to restore' (WTR) timer
       is used to prevent frequent operation of the protection
       switching due to intermittent signal failure defects.

       When recovering from a Signal fail, the delay timer
       must be long enough to allow the recovering network to
       become stable.

       WTR timer is activated on RPL owner node. When WTR
       timer is expired RPL owner node initiates the reversion
       process by transmitting an R-APS (NR, RB) message.";
    reference "ITU-T G.8032/Y.1344 (08/2015); Section 10.1.4";
  }

  typedef ncs_template_erps-instance-status-type {
    type string;
    description
      "Erps Instance Status Type";
  }

  typedef ncs_template_erps-instance-port-status-type {
    type string;
    description
      "Erps Instance Port Status Type";
  }

  typedef ncs_rpc_notif_rpl-type {
    type enumeration {
      enum "none" {
        description
          "No RPL.";
      }
      enum "owner" {
        description
          "An RPL owner.";
      }
      enum "neighbor" {
        description
          "An RPL neighbor owner.";
      }
      enum "next-neighbor" {
        description
          "Represents next-neighbour node in the ring.";
      }
    }
    description
      "The disposition of the RPL ownership associated with a ring
       Interface.";
    reference "ITU-T G.8032/Y.1344 (08/2015); Section 10.1";
  }

  typedef ncs_rpc_notif_reversion-mode {
    type enumeration {
      enum "revertive" {
        description
          "Represents revertive mode operation of a G.8032
           ethernet ring.";
      }
      enum "non-revertive" {
        description
          "Represents non-revertive mode operation of a
           G.8032 ethernet ring.";
      }
    }
    description
      "This typedef defines G.8032 ring protection operation mode.";
    reference "ITU-T G.8032/Y.1344 (08/2015); Section 9.1, 10.2.3.1";
  }

  typedef ncs_rpc_notif_ring-name-type {
    type string {
      length "1..255";
    }
    description
      "The ring name type identifier.";
  }

  typedef ncs_rpc_notif_ring-id-type {
    type uint8 {
      range "1..239";
    }
    default "1";
    description
      "G.8032 Ring ID";
    reference "ITU-T G.8032/Y.1344 (08/2015); Section 10.1.1";
  }

  typedef ncs_rpc_notif_ring-port-type {
    type enumeration {
      enum "port0" {
        description
          "Port 0 of the ring node.";
      }
      enum "port1" {
        description
          "Port 1 of the ring node.";
      }
    }
    description
      "Each ring instance has maximum of two ports. This definition
       labels these ports as port0 and port1 for identifications.";
    reference "ITU-T G.8032/Y.1344 (08/2015); Section 10.1 (Figure 10-1)";
  }

  typedef ncs_rpc_notif_hold-off-timer-type {
    type uint16 {
      range "0..10000";
    }
    units "milliseconds";
    default "0";
    description
      "The hold-off timer is used to coordinate the timing of
       protection switches.

       When a new defect or more severe defect occurs (new SF), this
       event is not to be reported immediately to protection switching
       if the provisioned hold-off timer value is non-zero. Instead,
       the hold-off timer is started. When the hold-off timer expires,
       the trail that started the timer is checked as to whether a
       defect still exists. If one does exist, that defect is
       reported to protection switching.

       Hold off timer values SHOULD be specified in multiple of 100.";
    reference "ITU-T G.8032/Y.1344 (08/2015); Section 10.1.8";
  }

  typedef ncs_rpc_notif_guard-timer-type {
    type uint16 {
      range "10..2000";
    }
    units "milliseconds";
    default "500";
    description
      "The guard timer is used to prevent Ethernet ring nodes from
       acting upon outdated R-APS messages and prevents the
       possibility of forming a closed loop.

       This timer period SHOULD be greater than the maximum expected
       forwarding delay in which an R-APS message traverses the
       entire ring.

       The period of the guard timer MAY be configured by the operator
       in 10 ms steps between 10 ms and 2 seconds.";
    reference "ITU-T G.8032/Y.1344 (08/2015); Section 10.1.5";
  }

  typedef ncs_rpc_notif_wtr-timer-type {
    type uint8 {
      range "1..12";
    }
    units "minutes";
    default "5";
    description
      "In revertive mode the 'wait to restore' (WTR) timer
       is used to prevent frequent operation of the protection
       switching due to intermittent signal failure defects.

       When recovering from a Signal fail, the delay timer
       must be long enough to allow the recovering network to
       become stable.

       WTR timer is activated on RPL owner node. When WTR
       timer is expired RPL owner node initiates the reversion
       process by transmitting an R-APS (NR, RB) message.";
    reference "ITU-T G.8032/Y.1344 (08/2015); Section 10.1.4";
  }

  typedef ncs_rpc_notif_erps-instance-status-type {
    type enumeration {
      enum "clear" {
        description
          "Reason for erp-instance-state: The ring is clear (VirtRingStatus_Clear)";
      }
      enum "localSf" {
        description
          "Reason for erp-instance-state: The ring has local signal-failure (VirtRingStatus_LocalSf)";
      }
      enum "localFs" {
        description
          "Reason for erp-instance-state: Local force-switch (VirtRingStatus_LocalFs)";
      }
      enum "remoteSf" {
        description
          "Reason for erp-instance-state: Remote signal-failure (VirtRingStatus_RemoteSf)";
      }
      enum "remoteFs" {
        description
          "Reason for erp-instance-state: Remote force-switch (VirtRingStatus_RemoteFs)";
      }
      enum "provMismatch" {
        description
          "Reason for erp-instance-state: Provisioning mismatch (VirtRingStatus_ProvMismatch)";
      }
      enum "noPduRxd" {
        description
          "Reason for erp-instance-state: No PDU received (VirtRingStatus_NoPduRxd)";
      }
      enum "noRplOwner" {
        description
          "Reason for erp-instance-state: No rpl owner (VirtRingStatus_NoRplOwner)";
      }
    }
    description
      "Erps Instance Status Type";
  }

  typedef ncs_rpc_notif_erps-instance-port-status-type {
    type enumeration {
      enum "clear" {
        description
          "Reason for erp-instance-port-state: LinkStatus_Clear (The link is clear)";
      }
      enum "down" {
        description
          "Reason for erp-instance-port-state: LinkStatus_Down (The link is down)";
      }
      enum "ccmFail" {
        description
          "Reason for erp-instance-port-state: LinkStatus_CcmFail (The link has CCM Failure)";
      }
      enum "localFs" {
        description
          "Reason for erp-instance-port-state: LinkStatus_LocalFs (Local force-switch)";
      }
      enum "remoteFs" {
        description
          "Reason for erp-instance-port-state: LinkStatus_RemoteFs (Remote force-switch)";
      }
      enum "remoteSf" {
        description
          "Reason for erp-instance-port-state: LinkStatus_RemoteSf (Remote signal-failure)";
      }
    }
    description
      "Erps Instance Port Status Type";
  }

  typedef live_ncs_rpl-type {
    type enumeration {
      enum "none" {
        description
          "No RPL.";
      }
      enum "owner" {
        description
          "An RPL owner.";
      }
      enum "neighbor" {
        description
          "An RPL neighbor owner.";
      }
      enum "next-neighbor" {
        description
          "Represents next-neighbour node in the ring.";
      }
    }
    description
      "The disposition of the RPL ownership associated with a ring
       Interface.";
    reference "ITU-T G.8032/Y.1344 (08/2015); Section 10.1";
  }

  typedef live_ncs_reversion-mode {
    type enumeration {
      enum "revertive" {
        description
          "Represents revertive mode operation of a G.8032
           ethernet ring.";
      }
      enum "non-revertive" {
        description
          "Represents non-revertive mode operation of a
           G.8032 ethernet ring.";
      }
    }
    description
      "This typedef defines G.8032 ring protection operation mode.";
    reference "ITU-T G.8032/Y.1344 (08/2015); Section 9.1, 10.2.3.1";
  }

  typedef live_ncs_ring-name-type {
    type string {
      length "1..255";
    }
    description
      "The ring name type identifier.";
  }

  typedef live_ncs_ring-id-type {
    type uint8 {
      range "1..239";
    }
    // NCS drop default statement
    description
      "G.8032 Ring ID";
    reference "ITU-T G.8032/Y.1344 (08/2015); Section 10.1.1";
  }

  typedef live_ncs_ring-port-type {
    type enumeration {
      enum "port0" {
        description
          "Port 0 of the ring node.";
      }
      enum "port1" {
        description
          "Port 1 of the ring node.";
      }
    }
    description
      "Each ring instance has maximum of two ports. This definition
       labels these ports as port0 and port1 for identifications.";
    reference "ITU-T G.8032/Y.1344 (08/2015); Section 10.1 (Figure 10-1)";
  }

  typedef live_ncs_hold-off-timer-type {
    type uint16 {
      range "0..10000";
    }
    units "milliseconds";
    // NCS drop default statement
    description
      "The hold-off timer is used to coordinate the timing of
       protection switches.

       When a new defect or more severe defect occurs (new SF), this
       event is not to be reported immediately to protection switching
       if the provisioned hold-off timer value is non-zero. Instead,
       the hold-off timer is started. When the hold-off timer expires,
       the trail that started the timer is checked as to whether a
       defect still exists. If one does exist, that defect is
       reported to protection switching.

       Hold off timer values SHOULD be specified in multiple of 100.";
    reference "ITU-T G.8032/Y.1344 (08/2015); Section 10.1.8";
  }

  typedef live_ncs_guard-timer-type {
    type uint16 {
      range "10..2000";
    }
    units "milliseconds";
    // NCS drop default statement
    description
      "The guard timer is used to prevent Ethernet ring nodes from
       acting upon outdated R-APS messages and prevents the
       possibility of forming a closed loop.

       This timer period SHOULD be greater than the maximum expected
       forwarding delay in which an R-APS message traverses the
       entire ring.

       The period of the guard timer MAY be configured by the operator
       in 10 ms steps between 10 ms and 2 seconds.";
    reference "ITU-T G.8032/Y.1344 (08/2015); Section 10.1.5";
  }

  typedef live_ncs_wtr-timer-type {
    type uint8 {
      range "1..12";
    }
    units "minutes";
    // NCS drop default statement
    description
      "In revertive mode the 'wait to restore' (WTR) timer
       is used to prevent frequent operation of the protection
       switching due to intermittent signal failure defects.

       When recovering from a Signal fail, the delay timer
       must be long enough to allow the recovering network to
       become stable.

       WTR timer is activated on RPL owner node. When WTR
       timer is expired RPL owner node initiates the reversion
       process by transmitting an R-APS (NR, RB) message.";
    reference "ITU-T G.8032/Y.1344 (08/2015); Section 10.1.4";
  }

  typedef live_ncs_erps-instance-status-type {
    type enumeration {
      enum "clear" {
        description
          "Reason for erp-instance-state: The ring is clear (VirtRingStatus_Clear)";
      }
      enum "localSf" {
        description
          "Reason for erp-instance-state: The ring has local signal-failure (VirtRingStatus_LocalSf)";
      }
      enum "localFs" {
        description
          "Reason for erp-instance-state: Local force-switch (VirtRingStatus_LocalFs)";
      }
      enum "remoteSf" {
        description
          "Reason for erp-instance-state: Remote signal-failure (VirtRingStatus_RemoteSf)";
      }
      enum "remoteFs" {
        description
          "Reason for erp-instance-state: Remote force-switch (VirtRingStatus_RemoteFs)";
      }
      enum "provMismatch" {
        description
          "Reason for erp-instance-state: Provisioning mismatch (VirtRingStatus_ProvMismatch)";
      }
      enum "noPduRxd" {
        description
          "Reason for erp-instance-state: No PDU received (VirtRingStatus_NoPduRxd)";
      }
      enum "noRplOwner" {
        description
          "Reason for erp-instance-state: No rpl owner (VirtRingStatus_NoRplOwner)";
      }
    }
    description
      "Erps Instance Status Type";
  }

  typedef live_ncs_erps-instance-port-status-type {
    type enumeration {
      enum "clear" {
        description
          "Reason for erp-instance-port-state: LinkStatus_Clear (The link is clear)";
      }
      enum "down" {
        description
          "Reason for erp-instance-port-state: LinkStatus_Down (The link is down)";
      }
      enum "ccmFail" {
        description
          "Reason for erp-instance-port-state: LinkStatus_CcmFail (The link has CCM Failure)";
      }
      enum "localFs" {
        description
          "Reason for erp-instance-port-state: LinkStatus_LocalFs (Local force-switch)";
      }
      enum "remoteFs" {
        description
          "Reason for erp-instance-port-state: LinkStatus_RemoteFs (Remote force-switch)";
      }
      enum "remoteSf" {
        description
          "Reason for erp-instance-port-state: LinkStatus_RemoteSf (Remote signal-failure)";
      }
    }
    description
      "Erps Instance Port Status Type";
  }

  typedef rpl-type {
    type enumeration {
      enum "none" {
        description
          "No RPL.";
      }
      enum "owner" {
        description
          "An RPL owner.";
      }
      enum "neighbor" {
        description
          "An RPL neighbor owner.";
      }
      enum "next-neighbor" {
        description
          "Represents next-neighbour node in the ring.";
      }
    }
    description
      "The disposition of the RPL ownership associated with a ring
       Interface.";
    reference "ITU-T G.8032/Y.1344 (08/2015); Section 10.1";
  }

  typedef reversion-mode {
    type enumeration {
      enum "revertive" {
        description
          "Represents revertive mode operation of a G.8032
           ethernet ring.";
      }
      enum "non-revertive" {
        description
          "Represents non-revertive mode operation of a
           G.8032 ethernet ring.";
      }
    }
    description
      "This typedef defines G.8032 ring protection operation mode.";
    reference "ITU-T G.8032/Y.1344 (08/2015); Section 9.1, 10.2.3.1";
  }

  typedef ring-name-type {
    type string {
      length "1..255";
    }
    description
      "The ring name type identifier.";
  }

  typedef ring-id-type {
    type uint8 {
      range "1..239";
    }
    default "1";
    description
      "G.8032 Ring ID";
    reference "ITU-T G.8032/Y.1344 (08/2015); Section 10.1.1";
  }

  typedef ring-port-type {
    type enumeration {
      enum "port0" {
        description
          "Port 0 of the ring node.";
      }
      enum "port1" {
        description
          "Port 1 of the ring node.";
      }
    }
    description
      "Each ring instance has maximum of two ports. This definition
       labels these ports as port0 and port1 for identifications.";
    reference "ITU-T G.8032/Y.1344 (08/2015); Section 10.1 (Figure 10-1)";
  }

  typedef hold-off-timer-type {
    type uint16 {
      range "0..10000";
    }
    units "milliseconds";
    default "0";
    description
      "The hold-off timer is used to coordinate the timing of
       protection switches.

       When a new defect or more severe defect occurs (new SF), this
       event is not to be reported immediately to protection switching
       if the provisioned hold-off timer value is non-zero. Instead,
       the hold-off timer is started. When the hold-off timer expires,
       the trail that started the timer is checked as to whether a
       defect still exists. If one does exist, that defect is
       reported to protection switching.

       Hold off timer values SHOULD be specified in multiple of 100.";
    reference "ITU-T G.8032/Y.1344 (08/2015); Section 10.1.8";
  }

  typedef guard-timer-type {
    type uint16 {
      range "10..2000";
    }
    units "milliseconds";
    default "500";
    description
      "The guard timer is used to prevent Ethernet ring nodes from
       acting upon outdated R-APS messages and prevents the
       possibility of forming a closed loop.

       This timer period SHOULD be greater than the maximum expected
       forwarding delay in which an R-APS message traverses the
       entire ring.

       The period of the guard timer MAY be configured by the operator
       in 10 ms steps between 10 ms and 2 seconds.";
    reference "ITU-T G.8032/Y.1344 (08/2015); Section 10.1.5";
  }

  typedef wtr-timer-type {
    type uint8 {
      range "1..12";
    }
    units "minutes";
    default "5";
    description
      "In revertive mode the 'wait to restore' (WTR) timer
       is used to prevent frequent operation of the protection
       switching due to intermittent signal failure defects.

       When recovering from a Signal fail, the delay timer
       must be long enough to allow the recovering network to
       become stable.

       WTR timer is activated on RPL owner node. When WTR
       timer is expired RPL owner node initiates the reversion
       process by transmitting an R-APS (NR, RB) message.";
    reference "ITU-T G.8032/Y.1344 (08/2015); Section 10.1.4";
  }

  typedef erps-instance-status-type {
    type enumeration {
      enum "clear" {
        description
          "Reason for erp-instance-state: The ring is clear (VirtRingStatus_Clear)";
      }
      enum "localSf" {
        description
          "Reason for erp-instance-state: The ring has local signal-failure (VirtRingStatus_LocalSf)";
      }
      enum "localFs" {
        description
          "Reason for erp-instance-state: Local force-switch (VirtRingStatus_LocalFs)";
      }
      enum "remoteSf" {
        description
          "Reason for erp-instance-state: Remote signal-failure (VirtRingStatus_RemoteSf)";
      }
      enum "remoteFs" {
        description
          "Reason for erp-instance-state: Remote force-switch (VirtRingStatus_RemoteFs)";
      }
      enum "provMismatch" {
        description
          "Reason for erp-instance-state: Provisioning mismatch (VirtRingStatus_ProvMismatch)";
      }
      enum "noPduRxd" {
        description
          "Reason for erp-instance-state: No PDU received (VirtRingStatus_NoPduRxd)";
      }
      enum "noRplOwner" {
        description
          "Reason for erp-instance-state: No rpl owner (VirtRingStatus_NoRplOwner)";
      }
    }
    description
      "Erps Instance Status Type";
  }

  typedef erps-instance-port-status-type {
    type enumeration {
      enum "clear" {
        description
          "Reason for erp-instance-port-state: LinkStatus_Clear (The link is clear)";
      }
      enum "down" {
        description
          "Reason for erp-instance-port-state: LinkStatus_Down (The link is down)";
      }
      enum "ccmFail" {
        description
          "Reason for erp-instance-port-state: LinkStatus_CcmFail (The link has CCM Failure)";
      }
      enum "localFs" {
        description
          "Reason for erp-instance-port-state: LinkStatus_LocalFs (Local force-switch)";
      }
      enum "remoteFs" {
        description
          "Reason for erp-instance-port-state: LinkStatus_RemoteFs (Remote force-switch)";
      }
      enum "remoteSf" {
        description
          "Reason for erp-instance-port-state: LinkStatus_RemoteSf (Remote signal-failure)";
      }
    }
    description
      "Erps Instance Port Status Type";
  }

  grouping ncs_template_ring-identifier {
    description
      "This grouping defines ring-name and instance-name
       combination.";
    leaf ring-name {
      type string;
      // NCS drop mandatory statement
      description
        "G.8032 ring name.";
    }
    leaf instance-name {
      type string;
      // NCS drop mandatory statement
      description
        "ERP instance name.";
    }
  }

  grouping ncs_template_aps-statistics {
    description
      "R-APS statistics";
    leaf tx-raps {
      type string;
      // NCS drop mandatory statement
      description
        "Number of R-APS messages transmitted";
    }
    leaf rx-raps {
      type string;
      // NCS drop mandatory statement
      description
        "Number of R-APS messages received";
    }
    leaf tx-raps-nrrb {
      type string;
      description
        "Number of R-APS(NR,RB) messages transmitted";
    }
    leaf rx-raps-nrrb {
      type string;
      description
        "Number of R-APS(NR,RB) messages received";
    }
    leaf tx-raps-nr {
      type string;
      description
        "Number of R-APS(NR) messages transmitted";
    }
    leaf rx-raps-nr {
      type string;
      description
        "Number of R-APS(NR) messages received";
    }
    leaf tx-raps-sf {
      type string;
      description
        "Number of R-APS(SF) messages transmitted";
    }
    leaf rx-raps-sf {
      type string;
      description
        "Number of R-APS(SF) messages received";
    }
    leaf tx-raps-fs {
      type string;
      description
        "Number of R-APS(FS) messages transmitted";
    }
    leaf rx-raps-fs {
      type string;
      description
        "Number of R-APS(FS) messages received";
    }
    leaf tx-raps-ms {
      type string;
      description
        "Number of R-APS(MS) messages transmitted";
    }
    leaf rx-raps-ms {
      type string;
      description
        "Number of R-APS(MS) messages received";
    }
  }

  grouping ncs_rpc_notif_ring-identifier {
    description
      "This grouping defines ring-name and instance-name
       combination.";
    leaf ring-name {
      type string;
      mandatory true;
      description
        "G.8032 ring name.";
    }
    leaf instance-name {
      type string;
      mandatory true;
      description
        "ERP instance name.";
    }
  }

  grouping ncs_rpc_notif_aps-statistics {
    description
      "R-APS statistics";
    leaf tx-raps {
      type yang:counter64;
      mandatory true;
      description
        "Number of R-APS messages transmitted";
    }
    leaf rx-raps {
      type yang:counter64;
      mandatory true;
      description
        "Number of R-APS messages received";
    }
    leaf tx-raps-nrrb {
      type yang:counter64;
      description
        "Number of R-APS(NR,RB) messages transmitted";
    }
    leaf rx-raps-nrrb {
      type yang:counter64;
      description
        "Number of R-APS(NR,RB) messages received";
    }
    leaf tx-raps-nr {
      type yang:counter64;
      description
        "Number of R-APS(NR) messages transmitted";
    }
    leaf rx-raps-nr {
      type yang:counter64;
      description
        "Number of R-APS(NR) messages received";
    }
    leaf tx-raps-sf {
      type yang:counter64;
      description
        "Number of R-APS(SF) messages transmitted";
    }
    leaf rx-raps-sf {
      type yang:counter64;
      description
        "Number of R-APS(SF) messages received";
    }
    leaf tx-raps-fs {
      type yang:counter64;
      description
        "Number of R-APS(FS) messages transmitted";
    }
    leaf rx-raps-fs {
      type yang:counter64;
      description
        "Number of R-APS(FS) messages received";
    }
    leaf tx-raps-ms {
      type yang:counter64;
      description
        "Number of R-APS(MS) messages transmitted";
    }
    leaf rx-raps-ms {
      type yang:counter64;
      description
        "Number of R-APS(MS) messages received";
    }
  }

  grouping live_ncs_ring-identifier {
    description
      "This grouping defines ring-name and instance-name
       combination.";
    leaf ring-name {
      type leafref {
        path "/ncs:devices/ncs:device/ncs:live-status/g8032-rings/g8032-ring/ring-name" {
          tailf:xpath-root 3;
        }
      }
      // NCS drop mandatory statement
      description
        "G.8032 ring name.";
    }
    leaf instance-name {
      type leafref {
        path "/ncs:devices/ncs:device/ncs:live-status/g8032-rings/g8032-ring[ring-name = current()/../ring-name]/erp-instances/erp-instance/instance-name" {
          tailf:xpath-root 3;
        }
      }
      // NCS drop mandatory statement
      description
        "ERP instance name.";
    }
  }

  grouping live_ncs_aps-statistics {
    description
      "R-APS statistics";
    leaf tx-raps {
      type yang:counter64;
      // NCS drop mandatory statement
      description
        "Number of R-APS messages transmitted";
    }
    leaf rx-raps {
      type yang:counter64;
      // NCS drop mandatory statement
      description
        "Number of R-APS messages received";
    }
    leaf tx-raps-nrrb {
      type yang:counter64;
      description
        "Number of R-APS(NR,RB) messages transmitted";
    }
    leaf rx-raps-nrrb {
      type yang:counter64;
      description
        "Number of R-APS(NR,RB) messages received";
    }
    leaf tx-raps-nr {
      type yang:counter64;
      description
        "Number of R-APS(NR) messages transmitted";
    }
    leaf rx-raps-nr {
      type yang:counter64;
      description
        "Number of R-APS(NR) messages received";
    }
    leaf tx-raps-sf {
      type yang:counter64;
      description
        "Number of R-APS(SF) messages transmitted";
    }
    leaf rx-raps-sf {
      type yang:counter64;
      description
        "Number of R-APS(SF) messages received";
    }
    leaf tx-raps-fs {
      type yang:counter64;
      description
        "Number of R-APS(FS) messages transmitted";
    }
    leaf rx-raps-fs {
      type yang:counter64;
      description
        "Number of R-APS(FS) messages received";
    }
    leaf tx-raps-ms {
      type yang:counter64;
      description
        "Number of R-APS(MS) messages transmitted";
    }
    leaf rx-raps-ms {
      type yang:counter64;
      description
        "Number of R-APS(MS) messages received";
    }
  }

  grouping ring-identifier {
    description
      "This grouping defines ring-name and instance-name
       combination.";
    leaf ring-name {
      type leafref {
        path "/ncs:devices/ncs:device/ncs:config/g8032-rings/g8032-ring/ring-name" {
          tailf:xpath-root 3;
        }
      }
      mandatory true;
      description
        "G.8032 ring name.";
    }
    leaf instance-name {
      type leafref {
        path "/ncs:devices/ncs:device/ncs:config/g8032-rings/g8032-ring[ring-name = current()/../ring-name]/erp-instances/erp-instance/instance-name" {
          tailf:xpath-root 3;
        }
      }
      mandatory true;
      description
        "ERP instance name.";
    }
  }

  grouping aps-statistics {
    description
      "R-APS statistics";
    leaf tx-raps {
      type yang:counter64;
      mandatory true;
      description
        "Number of R-APS messages transmitted";
    }
    leaf rx-raps {
      type yang:counter64;
      mandatory true;
      description
        "Number of R-APS messages received";
    }
    leaf tx-raps-nrrb {
      type yang:counter64;
      description
        "Number of R-APS(NR,RB) messages transmitted";
    }
    leaf rx-raps-nrrb {
      type yang:counter64;
      description
        "Number of R-APS(NR,RB) messages received";
    }
    leaf tx-raps-nr {
      type yang:counter64;
      description
        "Number of R-APS(NR) messages transmitted";
    }
    leaf rx-raps-nr {
      type yang:counter64;
      description
        "Number of R-APS(NR) messages received";
    }
    leaf tx-raps-sf {
      type yang:counter64;
      description
        "Number of R-APS(SF) messages transmitted";
    }
    leaf rx-raps-sf {
      type yang:counter64;
      description
        "Number of R-APS(SF) messages received";
    }
    leaf tx-raps-fs {
      type yang:counter64;
      description
        "Number of R-APS(FS) messages transmitted";
    }
    leaf rx-raps-fs {
      type yang:counter64;
      description
        "Number of R-APS(FS) messages received";
    }
    leaf tx-raps-ms {
      type yang:counter64;
      description
        "Number of R-APS(MS) messages transmitted";
    }
    leaf rx-raps-ms {
      type yang:counter64;
      description
        "Number of R-APS(MS) messages received";
    }
  }

  augment "/ncs:devices/ncs:device/ncs:rpc" {
    container rpc-switch-ring {
      tailf:ncs-device-type "netconf";
      tailf:display-when "not(../../ncs:module) or ../../ncs:module[ncs:name='ciena-itut-g8032-draft']";
      tailf:action switch-ring {
        tailf:actionpoint ncsproxy {
          tailf:internal;
        }
        description
          "Perform administrative action on the ring (instance).";
        input {
          uses ncs_rpc_notif_ring-identifier {
            description
              "Uniquely identifies ring instance.";
          }
          leaf port-id {
            type string;
            mandatory true;
            description
              "Ring port to perform switch operation.";
          }
          leaf operation {
            type enumeration {
              enum "manual" {
                description
                  "Trigger manual switch. This operation is allowed
                   only when a ring instance is in idle or pending state.

                   This action allows administrator to temporarily block
                   another ring port and unblock RPL link to perform
                   maintenance operation in the ring.";
                reference "ITU-T G.8032/Y.1344 (08/2015); Section 10.2.4";
              }
              enum "forced" {
                description
                  "Trigger force switch. This operation overrides all
                   other state of the ring.";
                reference "ITU-T G.8032/Y.1344 (08/2015); Section 10.2.5";
              }
            }
            mandatory true;
            description
              "G.8032 administrative operation types.";
            reference "ITU-T G.8032/Y.1344 (08/2015); Section 8, 10.1.9";
          }
        }
        output {
          leaf errstr {
            type string;
            description
              "Error message from the device if RPC failed, including
               failures where switch operation is not permitted on the
               ring instance under protocol restrictions.";
          }
        }
      }
    }
  }
  augment "/ncs:devices/ncs:device-group/ncs:ned-id/ncs:rpc" {
    container rpc-switch-ring {
      tailf:ncs-device-type "netconf";
      tailf:display-when "/ncs:devices/ncs:device[ncs:name=current()/../../../ncs:member]/ncs:module[ncs:name='ciena-itut-g8032-draft']";
      tailf:action switch-ring {
        tailf:actionpoint ncsproxy {
          tailf:internal;
        }
        description
          "Perform administrative action on the ring (instance).";
        input {
          uses ncs_rpc_notif_ring-identifier {
            description
              "Uniquely identifies ring instance.";
          }
          leaf port-id {
            type string;
            mandatory true;
            description
              "Ring port to perform switch operation.";
          }
          leaf operation {
            type enumeration {
              enum "manual" {
                description
                  "Trigger manual switch. This operation is allowed
                   only when a ring instance is in idle or pending state.

                   This action allows administrator to temporarily block
                   another ring port and unblock RPL link to perform
                   maintenance operation in the ring.";
                reference "ITU-T G.8032/Y.1344 (08/2015); Section 10.2.4";
              }
              enum "forced" {
                description
                  "Trigger force switch. This operation overrides all
                   other state of the ring.";
                reference "ITU-T G.8032/Y.1344 (08/2015); Section 10.2.5";
              }
            }
            mandatory true;
            description
              "G.8032 administrative operation types.";
            reference "ITU-T G.8032/Y.1344 (08/2015); Section 8, 10.1.9";
          }
        }
        output {
          container "device" {
            leaf "name" {
              type string;
            }
            leaf "info" {
              type string;
            }
            container "result" {
              leaf errstr {
                type string;
                description
                  "Error message from the device if RPC failed, including
                   failures where switch operation is not permitted on the
                   ring instance under protocol restrictions.";
              }
            }
          }
        }
      }
    }
  }
  augment "/ncs:devices/ncs:device/ncs:rpc" {
    container rpc-clear-ring {
      tailf:ncs-device-type "netconf";
      tailf:display-when "not(../../ncs:module) or ../../ncs:module[ncs:name='ciena-itut-g8032-draft']";
      tailf:action clear-ring {
        tailf:actionpoint ncsproxy {
          tailf:internal;
        }
        description
          "Clear an existing Forced-Switch (FS) or Manual-Switch (MS)
           condition on the ring port.";
        reference
          "ITU-T G.8032/Y.1344 (08/2015); Sections 8, 10.1.9,
           10.2.4.1, 10.2.5.1";
        input {
          uses ncs_rpc_notif_ring-identifier {
            description
              "Uniquely identifies ring instance.";
          }
        }
        output {
          leaf errstr {
            type string;
            description
              "Error message from the device if RPC failed.";
          }
        }
      }
    }
  }
  augment "/ncs:devices/ncs:device-group/ncs:ned-id/ncs:rpc" {
    container rpc-clear-ring {
      tailf:ncs-device-type "netconf";
      tailf:display-when "/ncs:devices/ncs:device[ncs:name=current()/../../../ncs:member]/ncs:module[ncs:name='ciena-itut-g8032-draft']";
      tailf:action clear-ring {
        tailf:actionpoint ncsproxy {
          tailf:internal;
        }
        description
          "Clear an existing Forced-Switch (FS) or Manual-Switch (MS)
           condition on the ring port.";
        reference
          "ITU-T G.8032/Y.1344 (08/2015); Sections 8, 10.1.9,
           10.2.4.1, 10.2.5.1";
        input {
          uses ncs_rpc_notif_ring-identifier {
            description
              "Uniquely identifies ring instance.";
          }
        }
        output {
          container "device" {
            leaf "name" {
              type string;
            }
            leaf "info" {
              type string;
            }
            container "result" {
              leaf errstr {
                type string;
                description
                  "Error message from the device if RPC failed.";
              }
            }
          }
        }
      }
    }
  }
  augment "/ncs:devices/ncs:device/ncs:rpc" {
    container rpc-clear-statistics {
      tailf:ncs-device-type "netconf";
      tailf:display-when "not(../../ncs:module) or ../../ncs:module[ncs:name='ciena-itut-g8032-draft']";
      tailf:action clear-statistics {
        tailf:actionpoint ncsproxy {
          tailf:internal;
        }
        description
          "Clear ring statistics.";
        input {
          uses ncs_rpc_notif_ring-identifier {
            description
              "Uniquely identifies ring instance.";
          }
        }
        output {
          leaf errstr {
            type string;
            description
              "Error message from the device if RPC failed.";
          }
        }
      }
    }
  }
  augment "/ncs:devices/ncs:device-group/ncs:ned-id/ncs:rpc" {
    container rpc-clear-statistics {
      tailf:ncs-device-type "netconf";
      tailf:display-when "/ncs:devices/ncs:device[ncs:name=current()/../../../ncs:member]/ncs:module[ncs:name='ciena-itut-g8032-draft']";
      tailf:action clear-statistics {
        tailf:actionpoint ncsproxy {
          tailf:internal;
        }
        description
          "Clear ring statistics.";
        input {
          uses ncs_rpc_notif_ring-identifier {
            description
              "Uniquely identifies ring instance.";
          }
        }
        output {
          container "device" {
            leaf "name" {
              type string;
            }
            leaf "info" {
              type string;
            }
            container "result" {
              leaf errstr {
                type string;
                description
                  "Error message from the device if RPC failed.";
              }
            }
          }
        }
      }
    }
  }
  augment "/ncs:devices/ncs:device/ncs:notifications/ncs:received-notifications/ncs:notification/ncs:data" {
    container fop-events {
      presence "";
      config false;
      description
        "Failure of Protocol (FOP) events.";
      reference "ITU-T G.8032/Y.1344 (08/2015); Section 10.4, and ITU-T G.8021/Y.1341 (04/2015); Section 6.1.4.3";
      list fop-event {
        leaf ring-name {
          type string;
        }
        list erp-instance-list {
          leaf instance-name {
            type string;
            description
              "The G.8032 ERP instance name.";
          }
          list events-list {
            leaf event-type {
              type identityref {
                base fop-event-type;
              }
              description
                "G.8032 Failure of Protocol event types.";
            }
            leaf status {
              type boolean;
              default "false";
              description
                "Status of FOP events.";
            }
          }
        }
      }
    }
  }
  augment "/ncs:devices/ncs:device/ncs:notifications/ncs:received-notifications/ncs:notification/ncs:data" {
    container ring-state-change-events {
      presence "";
      config false;
      description
        "Notify ring state change events.";
      list ring-state-change-event {
        leaf ring-name {
          type string;
        }
        list erp-instance-list {
          leaf instance-name {
            type string;
            description
              "The G.8032 ERP instance name.";
          }
          leaf current-state {
            type identityref {
              base ring-state-type;
            }
            description
              "New state of the ring instance.";
            reference "ITU-T G.8032/Y.1344 (08/2015); Section 10.1.2 (Table 10-2)";
          }
          leaf previous-state {
            type identityref {
              base ring-state-type;
            }
            description
              "Previous state of the ring instance.";
            reference "ITU-T G.8032/Y.1344 (08/2015); Section 10.1.2 (Table 10-2)";
          }
        }
      }
    }
  }
  augment "/ncs:devices/ncs:device/ncs:notifications/ncs:received-notifications/ncs:notification/ncs:data" {
    container fop-event {
      presence "";
      config false;
      description
        "Failure of Protocol (FOP) events.";
      reference "ITU-T G.8032/Y.1344 (08/2015); Section 10.4, and ITU-T G.8021/Y.1341 (04/2015); Section 6.1.4.3";
      uses ncs_rpc_notif_ring-identifier {
        description
          "Uniquely identifies a ring instance.";
      }
      leaf event-type {
        type identityref {
          base fop-event-type;
        }
        description
          "G.8032 Failure of Protocol event types.";
      }
    }
  }
  augment "/ncs:devices/ncs:device/ncs:notifications/ncs:received-notifications/ncs:notification/ncs:data" {
    container ring-state-change-event {
      presence "";
      config false;
      description
        "Notify ring state change events.";
      uses ncs_rpc_notif_ring-identifier {
        description
          "Uniquely identifies a ring instance.";
      }
      leaf current-state {
        type identityref {
          base ring-state-type;
        }
        // NCS drop mandatory statement
        description
          "New state of the ring instance.";
        reference "ITU-T G.8032/Y.1344 (08/2015); Section 10.1.2 (Table 10-2)";
      }
      leaf previous-state {
        type identityref {
          base ring-state-type;
        }
        // NCS drop mandatory statement
        description
          "Previous state of the ring instance.";
        reference "ITU-T G.8032/Y.1344 (08/2015); Section 10.1.2 (Table 10-2)";
      }
    }
  }
  augment "/ncs:devices/ncs:device/ncs:netconf-notifications/ncs:received-notifications/ncs:notification/ncs:data" {
    container fop-events {
      presence "";
      config false;
      description
        "Failure of Protocol (FOP) events.";
      reference "ITU-T G.8032/Y.1344 (08/2015); Section 10.4, and ITU-T G.8021/Y.1341 (04/2015); Section 6.1.4.3";
      list fop-event {
        leaf ring-name {
          type string;
        }
        list erp-instance-list {
          leaf instance-name {
            type string;
            description
              "The G.8032 ERP instance name.";
          }
          list events-list {
            leaf event-type {
              type identityref {
                base fop-event-type;
              }
              description
                "G.8032 Failure of Protocol event types.";
            }
            leaf status {
              type boolean;
              default "false";
              description
                "Status of FOP events.";
            }
          }
        }
      }
    }
  }
  augment "/ncs:devices/ncs:device/ncs:netconf-notifications/ncs:received-notifications/ncs:notification/ncs:data" {
    container ring-state-change-events {
      presence "";
      config false;
      description
        "Notify ring state change events.";
      list ring-state-change-event {
        leaf ring-name {
          type string;
        }
        list erp-instance-list {
          leaf instance-name {
            type string;
            description
              "The G.8032 ERP instance name.";
          }
          leaf current-state {
            type identityref {
              base ring-state-type;
            }
            description
              "New state of the ring instance.";
            reference "ITU-T G.8032/Y.1344 (08/2015); Section 10.1.2 (Table 10-2)";
          }
          leaf previous-state {
            type identityref {
              base ring-state-type;
            }
            description
              "Previous state of the ring instance.";
            reference "ITU-T G.8032/Y.1344 (08/2015); Section 10.1.2 (Table 10-2)";
          }
        }
      }
    }
  }
  augment "/ncs:devices/ncs:device/ncs:netconf-notifications/ncs:received-notifications/ncs:notification/ncs:data" {
    container fop-event {
      presence "";
      config false;
      description
        "Failure of Protocol (FOP) events.";
      reference "ITU-T G.8032/Y.1344 (08/2015); Section 10.4, and ITU-T G.8021/Y.1341 (04/2015); Section 6.1.4.3";
      uses ncs_rpc_notif_ring-identifier {
        description
          "Uniquely identifies a ring instance.";
      }
      leaf event-type {
        type identityref {
          base fop-event-type;
        }
        description
          "G.8032 Failure of Protocol event types.";
      }
    }
  }
  augment "/ncs:devices/ncs:device/ncs:netconf-notifications/ncs:received-notifications/ncs:notification/ncs:data" {
    container ring-state-change-event {
      presence "";
      config false;
      description
        "Notify ring state change events.";
      uses ncs_rpc_notif_ring-identifier {
        description
          "Uniquely identifies a ring instance.";
      }
      leaf current-state {
        type identityref {
          base ring-state-type;
        }
        // NCS drop mandatory statement
        description
          "New state of the ring instance.";
        reference "ITU-T G.8032/Y.1344 (08/2015); Section 10.1.2 (Table 10-2)";
      }
      leaf previous-state {
        type identityref {
          base ring-state-type;
        }
        // NCS drop mandatory statement
        description
          "Previous state of the ring instance.";
        reference "ITU-T G.8032/Y.1344 (08/2015); Section 10.1.2 (Table 10-2)";
      }
    }
  }
  augment "/ncs:devices/ncs:device/ncs:config" {
    container g8032-rings {
      tailf:ncs-device-type "netconf";
      tailf:display-when "not(../../ncs:module) or ../../ncs:module[ncs:name='ciena-itut-g8032-draft']";
      description
        "Contains all the G.8032 system specific related
         configuration.";
      leaf ring-system-control {
        type enumeration {
          enum "disabled" {
            description
              "Disables G.8032 ring protection on a system wide
               basis. There may be occasions during troubleshooting
               that requires the operator to globally disable.";
          }
          enum "enabled" {
            description
              "Enables G.8032 ring protection on a system wide
               basis.";
          }
        }
        default "enabled";
        description
          "Setting this control allows the enablement or disablement
           of the G.8032 protection switching on a system wide
           basis.";
      }
      leaf notification-enabled {
        type boolean;
        default "false";
        description
          "Enable/disable ring status change notification. If true,
           any change in ring state will be notified via
           ring-state-change notification.";
      }
      leaf raps-version {
        type identityref {
          base g8032-version-type;
        }
        description
          "The version of the ERP R-APS protocol being used.";
        reference "ITU-T G.8032/Y.1344 (08/2015); Section 10.1.13";
      }
      list g8032-ring {
        key "ring-name";
        description
          "Provides configuration nodes in support of ERP instances
           on the device.";
        leaf ring-name {
          type ring-name-type;
          description
            "G.8032 ring name.";
        }
        leaf ring-id {
          type ring-id-type;
          default "1";
          description
            "The Ring ID.";
          reference "ITU-T G.8032 (08/2015); Section 10.1.1";
        }
        leaf ring-description {
          type string {
            length "1..255";
          }
          description
            "Textual description of the ring.";
        }
        container ring-ports {
          description
            "Ring port configurations.";
          list ring-port {
            key "port-id";
            min-elements 2;
            max-elements 2;
            description
              "List of the ring ports.
               If all of the ERP instances for this ring are sub-rings
               that terminate at this node, this list may have only 1
               entry.";
            leaf port-id {
              type ring-port-type;
              description
                "Port identifier (port0 or port1).";
            }
            leaf interface {
              type if:interface-ref;
              mandatory true;
              description
                "Port interface reference of the Ring.";
            }
          }
        }
        container erp-instances {
          description
            "Collection of ring instances.";
          list erp-instance {
            key "instance-name";
            description
              "There can be multiple ERP instances associated with a
               given G.8032 ring. Each ERP instance must have a
               separate set of data member VLAN identifiers.";
            leaf instance-name {
              type ring-name-type;
              description
                "The ERP instance name.";
            }
            leaf instance-description {
              type string {
                length "1..255";
              }
              description
                "Textual description of the instance.";
            }
            leaf raps-vid {
              type ieee:vlanid;
              mandatory true;
              description
                "The VLAN identifier used by the ERP instance for
                 ring APS control messages.";
              reference "ITU-T G.8032/Y.1344 (08/2015); Section 9.5";
            }
            leaf raps-level {
              type uint8 {
                range "0..7";
              }
              mandatory true;
              description
                "The Maintenance Entity Level used by the ERP instance
                 for ring APS control messages.";
              reference "ITU-T G.8032/Y.1344 (08/2015); Section 10.3";
            }
            leaf raps-priority {
              type dot1q-types:priority-type;
              description
                "The priority assigned to the R-APS PDUs.";
            }
            leaf-list data-members {
              type dot1q-types:vid-range-type;
              min-elements 1;
              description
                "The range of data member identifiers protected
                 by the ERP instance.";
            }
            leaf erp-instance-construct {
              type identityref {
                base erp-instance-type;
              }
              mandatory true;
              description
                "Type of ERP instance.";
              reference "ITU-T G.8032/Y.1344 (08/2015); Section 9.3, 9.7";
            }
            leaf reversion {
              type reversion-mode;
              default "revertive";
              description
                "Configuration node specifying the reversion
                 capabilities of this ERP instance.";
              reference "ITU-T G.8032/Y.1344 (08/2015); Section 9.1, 10.2.3.1";
            }
            leaf wtr-timer {
              type wtr-timer-type;
              description
                "The wait-to-restore timer associated with the ERP
                 instance.";
              reference "ITU-T G.8032/Y.1344 (08/2015); Section 10.1.4";
            }
            leaf guard-timer {
              type guard-timer-type;
              description
                "The guard timer is used to prevent Ethernet ring nodes
                 from acting upon outdated R-APS messages and prevents
                 the possibility of forming a closed loop.";
              reference "ITU-T G.8032/Y.1344 (08/2015); Section 10.1.5";
            }
            leaf hold-off-time {
              type hold-off-timer-type;
              description
                "The hold-off timer is used to coordinate the
                 timing of protection switches.";
              reference "ITU-T G.8032/Y.1344 (08/2015); Section 10.1.8";
            }
            container ports {
              must "../erp-instance-construct != 'major-ring' or count(port) = 2" {
                tailf:xpath-root 3;
                error-message "A major ring must have 2 ring ports";
                description
                  "A major ring must have 2 ring ports";
              }
              description
                "Port specific configurations for ring instances.";
              list port {
                key "port-id";
                min-elements 1;
                max-elements 2;
                description
                  "List of the ring ports.
                   If this is a major ring, or this node is in a
                   sub-ring but is not the interconnection node where
                   the sub-ring terminates, then this list must have 2
                   entries.
                   If this is a sub-ring (with or without a virtual
                   channel), and this is an interconnection node where
                   the sub-ring terminates, then this list must have
                   only 1 entry.";
                leaf port-id {
                  type leafref {
                    path "../../../../../ring-ports/ring-port/port-id";
                  }
                  description
                    "Port id of the ring instance. This leaf
                     identifies one of the two ring ports.";
                }
                leaf rpl {
                  type rpl-type;
                  default "none";
                  description
                    "RPL port role for the ring instance.";
                  reference "ITU-T G.8032/Y.1344 (08/2015); Section 10.1";
                }
              }
            }
          }
        }
      }
    }
    // NCS drop config false container 'g8032-rings-state'
  }
  augment "/ncs:devices/ncs:device/ncs:live-status" {
    container g8032-rings {
      tailf:ncs-device-type "netconf";
      tailf:display-when "not(../../ncs:module) or ../../ncs:module[ncs:name='ciena-itut-g8032-draft'] or (../../ncs:live-status-protocol[not(ncs:capability)]) or (../../ncs:live-status-protocol/ncs:capability/ncs:module[.='ciena-itut-g8032-draft'])";
      description
        "Contains all the G.8032 system specific related
         configuration.";
      leaf ring-system-control {
        type enumeration {
          enum "disabled" {
            description
              "Disables G.8032 ring protection on a system wide
               basis. There may be occasions during troubleshooting
               that requires the operator to globally disable.";
          }
          enum "enabled" {
            description
              "Enables G.8032 ring protection on a system wide
               basis.";
          }
        }
        // NCS drop default statement
        description
          "Setting this control allows the enablement or disablement
           of the G.8032 protection switching on a system wide
           basis.";
      }
      leaf notification-enabled {
        type boolean;
        // NCS drop default statement
        description
          "Enable/disable ring status change notification. If true,
           any change in ring state will be notified via
           ring-state-change notification.";
      }
      leaf raps-version {
        type identityref {
          base g8032-version-type;
        }
        description
          "The version of the ERP R-APS protocol being used.";
        reference "ITU-T G.8032/Y.1344 (08/2015); Section 10.1.13";
      }
      list g8032-ring {
        key "ring-name";
        description
          "Provides configuration nodes in support of ERP instances
           on the device.";
        leaf ring-name {
          type live_ncs_ring-name-type;
          description
            "G.8032 ring name.";
        }
        leaf ring-id {
          type live_ncs_ring-id-type;
          // NCS drop default statement
          description
            "The Ring ID.";
          reference "ITU-T G.8032 (08/2015); Section 10.1.1";
        }
        leaf ring-description {
          type string {
            length "1..255";
          }
          description
            "Textual description of the ring.";
        }
        container ring-ports {
          description
            "Ring port configurations.";
          list ring-port {
            key "port-id";
            // NCS drop min-elements statement
            // NCS drop max-elements statement
            description
              "List of the ring ports.
               If all of the ERP instances for this ring are sub-rings
               that terminate at this node, this list may have only 1
               entry.";
            leaf port-id {
              type live_ncs_ring-port-type;
              description
                "Port identifier (port0 or port1).";
            }
            leaf interface {
              type if:live_ncs_interface-ref;
              // NCS drop mandatory statement
              description
                "Port interface reference of the Ring.";
            }
          }
        }
        container erp-instances {
          description
            "Collection of ring instances.";
          list erp-instance {
            key "instance-name";
            description
              "There can be multiple ERP instances associated with a
               given G.8032 ring. Each ERP instance must have a
               separate set of data member VLAN identifiers.";
            leaf instance-name {
              type live_ncs_ring-name-type;
              description
                "The ERP instance name.";
            }
            leaf instance-description {
              type string {
                length "1..255";
              }
              description
                "Textual description of the instance.";
            }
            leaf raps-vid {
              type ieee:live_ncs_vlanid;
              // NCS drop mandatory statement
              description
                "The VLAN identifier used by the ERP instance for
                 ring APS control messages.";
              reference "ITU-T G.8032/Y.1344 (08/2015); Section 9.5";
            }
            leaf raps-level {
              type uint8 {
                range "0..7";
              }
              // NCS drop mandatory statement
              description
                "The Maintenance Entity Level used by the ERP instance
                 for ring APS control messages.";
              reference "ITU-T G.8032/Y.1344 (08/2015); Section 10.3";
            }
            leaf raps-priority {
              type dot1q-types:live_ncs_priority-type;
              description
                "The priority assigned to the R-APS PDUs.";
            }
            leaf-list data-members {
              type dot1q-types:live_ncs_vid-range-type;
              // NCS drop min-elements statement
              description
                "The range of data member identifiers protected
                 by the ERP instance.";
            }
            leaf erp-instance-construct {
              type identityref {
                base erp-instance-type;
              }
              // NCS drop mandatory statement
              description
                "Type of ERP instance.";
              reference "ITU-T G.8032/Y.1344 (08/2015); Section 9.3, 9.7";
            }
            leaf reversion {
              type live_ncs_reversion-mode;
              // NCS drop default statement
              description
                "Configuration node specifying the reversion
                 capabilities of this ERP instance.";
              reference "ITU-T G.8032/Y.1344 (08/2015); Section 9.1, 10.2.3.1";
            }
            leaf wtr-timer {
              type live_ncs_wtr-timer-type;
              description
                "The wait-to-restore timer associated with the ERP
                 instance.";
              reference "ITU-T G.8032/Y.1344 (08/2015); Section 10.1.4";
            }
            leaf guard-timer {
              type live_ncs_guard-timer-type;
              description
                "The guard timer is used to prevent Ethernet ring nodes
                 from acting upon outdated R-APS messages and prevents
                 the possibility of forming a closed loop.";
              reference "ITU-T G.8032/Y.1344 (08/2015); Section 10.1.5";
            }
            leaf hold-off-time {
              type live_ncs_hold-off-timer-type;
              description
                "The hold-off timer is used to coordinate the
                 timing of protection switches.";
              reference "ITU-T G.8032/Y.1344 (08/2015); Section 10.1.8";
            }
            container ports {
              // NCS drop must statement
              description
                "Port specific configurations for ring instances.";
              list port {
                key "port-id";
                // NCS drop min-elements statement
                // NCS drop max-elements statement
                description
                  "List of the ring ports.
                   If this is a major ring, or this node is in a
                   sub-ring but is not the interconnection node where
                   the sub-ring terminates, then this list must have 2
                   entries.
                   If this is a sub-ring (with or without a virtual
                   channel), and this is an interconnection node where
                   the sub-ring terminates, then this list must have
                   only 1 entry.";
                leaf port-id {
                  type leafref {
                    path "../../../../../ring-ports/ring-port/port-id";
                  }
                  description
                    "Port id of the ring instance. This leaf
                     identifies one of the two ring ports.";
                }
                leaf rpl {
                  type live_ncs_rpl-type;
                  // NCS drop default statement
                  description
                    "RPL port role for the ring instance.";
                  reference "ITU-T G.8032/Y.1344 (08/2015); Section 10.1";
                }
              }
            }
          }
        }
      }
    }
    container g8032-rings-state {
      presence "In NCS this node is optional";
      tailf:ncs-device-type "netconf";
      tailf:display-when "not(../../ncs:module) or ../../ncs:module[ncs:name='ciena-itut-g8032-draft'] or (../../ncs:live-status-protocol[not(ncs:capability)]) or (../../ncs:live-status-protocol/ncs:capability/ncs:module[.='ciena-itut-g8032-draft'])";
      description
        "Contains all the G.8032 system specific related
         operational state nodes.";
      leaf max-instances-supported {
        type uint32;
        // NCS drop mandatory statement
        description
          "Maximum number of G.8032 rings instances supported on the
           device.";
      }
      list g8032-ring {
        key "ring-name";
        description
          "Provides configuration nodes in support of ERP instances
           on the device.";
        leaf ring-name {
          type leafref {
            path "/ncs:devices/ncs:device/ncs:live-status/g8032-rings/g8032-ring/ring-name" {
              tailf:xpath-root 3;
            }
          }
          description
            "G.8032 ring name.";
        }
        container erp-instances {
          description
            "Collection of ring instances.";
          list erp-instance {
            key "instance-name";
            description
              "There can be multiple ERP instances associated with a
               given G.8032 ring. Each ERP instance must have a
               separate set of data member VLAN identifiers.";
            leaf instance-name {
              type leafref {
                path "/ncs:devices/ncs:device/ncs:live-status/g8032-rings/g8032-ring[ring-name = current()/../../../ring-name]/erp-instances/erp-instance/instance-name" {
                  tailf:xpath-root 3;
                }
              }
              description
                "The G.8032 ERP instance name.";
            }
            leaf wtb-timer {
              type uint16 {
                range "5010..7000";
              }
              units "milliseconds";
              description
                "The WTB timer is used when clearing Forced switch and
                 Manual switch commands. As multiple Forced switch
                 commands are allowed to co-exist in an Ethernet ring,
                 the WTB timer ensures that clearing of a single Forced
                 switch command does not trigger the re-blocking of the
                 RPL. The timer is defined to be 5 seconds longer than
                 the Guard Timer.";
              reference "ITU-T G.8032/Y.1344 (08/2015); Section 10.1.4";
            }
            container ports {
              description
                "Operational state for the ring instance ports.";
              list port {
                key "port-id";
                // NCS drop min-elements statement
                // NCS drop max-elements statement
                description
                  "Collection of ring port states.";
                leaf port-id {
                  type leafref {
                    path "/ncs:devices/ncs:device/ncs:live-status/g8032-rings/g8032-ring[ring-name = current()/../../../../../ring-name]/erp-instances/erp-instance[instance-name = current()/../../../instance-name]/ports/port/port-id" {
                      tailf:xpath-root 3;
                    }
                  }
                  description
                    "Port id of the ring instance. This leaf identifies
                     one of the two ring ports.";
                }
                container flush-logic-remote {
                  description
                    "Remote node-id, bpr values, used by flush logic
                     of the ERP control process.";
                  reference "ITU-T G.8032/Y.1344 (08/2015); Section 10.1.10";
                  leaf node-id {
                    type ieee:live_ncs_mac-address;
                    // NCS drop mandatory statement
                    description
                      "Node ID of the last R-APS message received
                       over the ring port.

                       During initialization this value is set to
                       00:00:00:00:00:00 by ERP control process.";
                    reference "ITU-T G.8032/Y.1344 (08/2015); Section 10.1.10";
                  }
                  leaf bpr {
                    type uint8 {
                      range "0 | 1";
                    }
                    // NCS drop mandatory statement
                    description
                      "Blocked port reference (BPR) of the last
                       R-APS message received over the ring port.

                       During initialization this value is set to 0
                       by ERP control process.";
                    reference "ITU-T G.8032/Y.1344 (08/2015); Section 10.1.10";
                  }
                }
                leaf port-state {
                  type identityref {
                    base port-state-type;
                  }
                  // NCS drop mandatory statement
                  description
                    "Ring port state";
                }
                leaf erps-instance-port-status {
                  type live_ncs_erps-instance-port-status-type;
                  description
                    "This object specifies the reason of the link state";
                }
                leaf force-switch {
                  type boolean;
                  // NCS drop default statement
                  description
                    "Force switch trigger information";
                }
                container raps-statistics {
                  description
                    "R-APS packet statistics";
                  uses live_ncs_aps-statistics;
                }
              }
            }
            leaf ring-instance-state {
              type identityref {
                base ring-state-type;
              }
              // NCS drop mandatory statement
              description
                "Ring instance state. This represent protocol state
                 machine state.";
              reference
                "ITU-T G.8032/Y.1344 (08/2015); Section 10.1.2
                 (Table 10-2)";
            }
            leaf erps-instance-status {
              type live_ncs_erps-instance-status-type;
              description
                "This object specifies the reason of the ring state";
            }
            leaf number-of-switchovers {
              type uint32;
              description
                "This object specifies the number of switchovers";
            }
            leaf uptime-from-last-failure {
              type uint32;
              description
                "This object specifies the time for which the node has been up";
            }
            leaf total-down-time {
              type uint32;
              description
                "This object specifies the total time for which the node has been down";
            }
          }
        }
      }
    }
  }
  augment "/ncs:devices/ncs:template/ncs:ned-id/ncs:config" {
    container g8032-rings {
      description
        "Contains all the G.8032 system specific related
         configuration.";
      leaf ring-system-control {
        type string;
        // NCS drop default statement
        description
          "Setting this control allows the enablement or disablement
           of the G.8032 protection switching on a system wide
           basis.";
      }
      leaf notification-enabled {
        type string;
        // NCS drop default statement
        description
          "Enable/disable ring status change notification. If true,
           any change in ring state will be notified via
           ring-state-change notification.";
      }
      leaf raps-version {
        type string;
        description
          "The version of the ERP R-APS protocol being used.";
        reference "ITU-T G.8032/Y.1344 (08/2015); Section 10.1.13";
      }
      list g8032-ring {
        // NCS patched for predictable order
        ordered-by user;
        key "ring-name";
        description
          "Provides configuration nodes in support of ERP instances
           on the device.";
        leaf ring-name {
          type ncs_template_ring-name-type;
          description
            "G.8032 ring name.";
        }
        leaf ring-id {
          type ncs_template_ring-id-type;
          // NCS drop default statement
          description
            "The Ring ID.";
          reference "ITU-T G.8032 (08/2015); Section 10.1.1";
        }
        leaf ring-description {
          type string;
          description
            "Textual description of the ring.";
        }
        container ring-ports {
          description
            "Ring port configurations.";
          list ring-port {
            // NCS patched for predictable order
            ordered-by user;
            key "port-id";
            // NCS drop min-elements statement
            // NCS drop max-elements statement
            description
              "List of the ring ports.
               If all of the ERP instances for this ring are sub-rings
               that terminate at this node, this list may have only 1
               entry.";
            leaf port-id {
              type ncs_template_ring-port-type;
              description
                "Port identifier (port0 or port1).";
            }
            leaf interface {
              type if:ncs_template_interface-ref;
              // NCS drop mandatory statement
              description
                "Port interface reference of the Ring.";
            }
          }
        }
        container erp-instances {
          description
            "Collection of ring instances.";
          list erp-instance {
            // NCS patched for predictable order
            ordered-by user;
            key "instance-name";
            description
              "There can be multiple ERP instances associated with a
               given G.8032 ring. Each ERP instance must have a
               separate set of data member VLAN identifiers.";
            leaf instance-name {
              type ncs_template_ring-name-type;
              description
                "The ERP instance name.";
            }
            leaf instance-description {
              type string;
              description
                "Textual description of the instance.";
            }
            leaf raps-vid {
              type ieee:ncs_template_vlanid;
              // NCS drop mandatory statement
              description
                "The VLAN identifier used by the ERP instance for
                 ring APS control messages.";
              reference "ITU-T G.8032/Y.1344 (08/2015); Section 9.5";
            }
            leaf raps-level {
              type string;
              // NCS drop mandatory statement
              description
                "The Maintenance Entity Level used by the ERP instance
                 for ring APS control messages.";
              reference "ITU-T G.8032/Y.1344 (08/2015); Section 10.3";
            }
            leaf raps-priority {
              type dot1q-types:ncs_template_priority-type;
              description
                "The priority assigned to the R-APS PDUs.";
            }
            leaf-list data-members {
              // NCS patched for predictable order
              ordered-by user;
              type dot1q-types:ncs_template_vid-range-type;
              // NCS drop min-elements statement
              description
                "The range of data member identifiers protected
                 by the ERP instance.";
            }
            leaf erp-instance-construct {
              type string;
              // NCS drop mandatory statement
              description
                "Type of ERP instance.";
              reference "ITU-T G.8032/Y.1344 (08/2015); Section 9.3, 9.7";
            }
            leaf reversion {
              type ncs_template_reversion-mode;
              // NCS drop default statement
              description
                "Configuration node specifying the reversion
                 capabilities of this ERP instance.";
              reference "ITU-T G.8032/Y.1344 (08/2015); Section 9.1, 10.2.3.1";
            }
            leaf wtr-timer {
              type ncs_template_wtr-timer-type;
              description
                "The wait-to-restore timer associated with the ERP
                 instance.";
              reference "ITU-T G.8032/Y.1344 (08/2015); Section 10.1.4";
            }
            leaf guard-timer {
              type ncs_template_guard-timer-type;
              description
                "The guard timer is used to prevent Ethernet ring nodes
                 from acting upon outdated R-APS messages and prevents
                 the possibility of forming a closed loop.";
              reference "ITU-T G.8032/Y.1344 (08/2015); Section 10.1.5";
            }
            leaf hold-off-time {
              type ncs_template_hold-off-timer-type;
              description
                "The hold-off timer is used to coordinate the
                 timing of protection switches.";
              reference "ITU-T G.8032/Y.1344 (08/2015); Section 10.1.8";
            }
            container ports {
              // NCS drop must statement
              description
                "Port specific configurations for ring instances.";
              list port {
                // NCS patched for predictable order
                ordered-by user;
                key "port-id";
                // NCS drop min-elements statement
                // NCS drop max-elements statement
                description
                  "List of the ring ports.
                   If this is a major ring, or this node is in a
                   sub-ring but is not the interconnection node where
                   the sub-ring terminates, then this list must have 2
                   entries.
                   If this is a sub-ring (with or without a virtual
                   channel), and this is an interconnection node where
                   the sub-ring terminates, then this list must have
                   only 1 entry.";
                leaf port-id {
                  type string;
                  description
                    "Port id of the ring instance. This leaf
                     identifies one of the two ring ports.";
                }
                leaf rpl {
                  type ncs_template_rpl-type;
                  // NCS drop default statement
                  description
                    "RPL port role for the ring instance.";
                  reference "ITU-T G.8032/Y.1344 (08/2015); Section 10.1";
                }
              }
            }
          }
        }
      }
    }
    // NCS drop config false container 'g8032-rings-state'
  }

  identity any {
    base fop-event-type;
    description
      "This is used is telemetry for any event";
    reference "ITU-T G.8032/Y.1344 (08/2015); Section 10.4";
  }

  identity fop-norpl-clear {
    base fop-event-type;
    description
      "This event is generated when Protocol, Timeout (FOP-NORPL)
       defect is cleared";
    reference "ITU-T G.8032/Y.1344 (08/2015); Section 10.4";
  }

  identity fop-norpl {
    base fop-event-type;
    description
      "Failure of Protocol, Timeout (FOP-NORPL) event.
       This event is generated when ERP control process does not
       receive periodic R-APS frame).";
    reference "ITU-T G.8032/Y.1344 (08/2015); Section 10.4";
  }

  identity fop-to-clear {
    base fop-event-type;
    description
      "This event is generated when Protocol, Timeout (FOP-TO)
       defect is cleared";
    reference "ITU-T G.8032/Y.1344 (08/2015); Section 10.4";
  }

  identity fop-to {
    base fop-event-type;
    description
      "Failure of Protocol, Timeout (FOP-TO) event.

       This event is generated when ERP control process does not
       receive periodic R-APS frame for a defined timeout
       interval (>= 3.5 times R-APS interval).";
    reference "ITU-T G.8032/Y.1344 (08/2015); Section 10.4";
  }

  identity fop-pm-clear {
    base fop-event-type;
    description
      "This event is generated when Protocol, Provisioning
       Mismatch (FOP-PM) defect is cleared.";
    reference "ITU-T G.8032/Y.1344 (08/2015); Section 10.4";
  }

  identity fop-pm {
    base fop-event-type;
    description
      "Failure of Protocol, Provisioning Mismatch (FOP-PM)
       event.

       This event is generated when a node ID mismatch is
       detected by ERP control process by comparing the node ID
       of the RPL owner and the node ID in a received
       R-APS(NR, RB) frame.";
    reference "ITU-T G.8032/Y.1344 (08/2015); Section 10.4";
  }

  identity fop-event-type {
    description
      "Represents Failure of Protocol events";
  }

  identity local-fs {
    base port-state-type;
    description
      "Ring port has been blocked by administrative force switch
       action.";
  }

  identity local-ms {
    base port-state-type;
    description
      "Ring port has been blocked by administrative manual
       switch action.";
  }

  identity failed {
    base port-state-type;
    description
      "Ring port has local failure. Port is blocked and it is
       not forwarding any traffic.";
  }

  identity blocking {
    base port-state-type;
    description
      "Ring port is blocked and it is not forwarding any data
       traffic. In normal operations a port is blocked if it is
       a RPL port.";
  }

  identity forwarding {
    base port-state-type;
    description
      "Ring port is in normal state and ready to forward
       traffic ring controlled data traffic.";
  }

  identity port-state-type {
    description
      "States associated with a ring port.";
  }

  identity force-switch {
    base ring-state-type;
    description
      "User has force-switched ring. This state overrides
       protection state.";
    reference "ITU-T G.8032/Y.1344 (08/2015); Section 10.1.2 (Table 10-2)";
  }

  identity manual-switch {
    base ring-state-type;
    description
      "User has manually switched ring. This is usually done to
       perform maintenance operation on the ring node.";
    reference "ITU-T G.8032/Y.1344 (08/2015); Section 10.1.2 (Table 10-2)";
  }

  identity protection {
    base ring-state-type;
    description
      "One or more failure condition exists on the ring. Failed
       nodes are transmitting R-APS (SF) PDUs. Upon reaching to
       protection state ring unblocks RPL link to allow user
       traffic.";
    reference "ITU-T G.8032/Y.1344 (08/2015); Section 10.1.2 (Table 10-2)";
  }

  identity pending {
    base ring-state-type;
    description
      "Ring does not have any failure or administrative
       condition however RPL is blocked. In case of revertive
       mode operation wait-to-restore timer is running.";
    reference "ITU-T G.8032/Y.1344 (08/2015); Section 10.1.2 (Table 10-2)";
  }

  identity idle {
    base ring-state-type;
    description
      "Ring is operational in normal state, RPL link is blocked
       and no failure or administrative condition exists. Owner
       node is transmitting R-APS (NR, RB) PDUs.";
    reference "ITU-T G.8032/Y.1344 (08/2015); Section 10.1.2 (Table 10-2)";
  }

  identity initializing {
    base ring-state-type;
    description
      "Ring protocol state machine is initializing and it is not
       yet operational.";
    reference "ITU-T G.8032/Y.1344 (08/2015); Section 10.1.2 (Table 10-2)";
  }

  identity ring-state-type {
    description
      "Protocol states for a ring instance.";
  }

  identity g8032-version2 {
    base g8032-version-type;
    description
      "ITU-T G.8032 version 2";
    reference "ITU-T G.8032/Y.1344 (08/2015); Section 10.1.13";
  }

  identity g8032-version1 {
    base g8032-version-type;
    description
      "ITU-T G.8032 version 1";
    reference "ITU-T G.8032/Y.1344 (08/2015); Section 10.1.13";
  }

  identity g8032-version-type {
    description
      "The G.8032 protocol version.";
  }

  identity major-ring {
    base erp-instance-type;
    description
      "Identify for a major-ring.";
    reference "ITU-T G.8032/Y.1344 (08/2015); Section 9.3";
  }

  identity sub-ring-virtual-channel {
    base erp-instance-type;
    description
      "Identify for a sub-ring with a virtual channel.";
    reference "ITU-T G.8032/Y.1344 (08/2015); Section 9.7.1";
  }

  identity sub-ring-no-virtual-channel {
    base erp-instance-type;
    description
      "Identify for a sub-ring without a virtual channel.";
    reference "ITU-T G.8032/Y.1344 (08/2015); Section 9.7.2, 10.1.14";
  }

  identity erp-instance-type {
    description
      "Represents the configured ERP ring type.";
  }
}
