module ciena-openconfig-system {
  // Generated by yanger -t ncs
  tailf:mount-id "ciena107-nc-1.0:ciena107-nc-1.0";
  tailf:ncs-device-type "netconf";

  namespace "http://www.ciena.com/ns/yang/ciena-openconfig-system";
  prefix ciena-oc-sys;

  import openconfig-system {
    prefix oc-sys;
  }
  import yuma-ncx {
    prefix ncx;
  }
  import ietf-yang-types {
    prefix yang;
  }
  import ciena-ssh-types {
    prefix sshtypes;
  }
  import ciena-file-transfer-types {
    prefix ciena-ftt;
  }
  import ciena-types {
    prefix cn-type;
  }
  import tailf-common {
    prefix tailf;
  }
  import tailf-ncs {
    prefix ncs;
  }

  organization
    "Ciena Corporation";
  contact
    "Web URL: http://www.ciena.com/
     E-mail:  yang@ciena.com
     Postal:  7035 Ridge Road
              Hanover, Maryland 21076
              U.S.A.
     Phone:   +1 800-921-1144
     Fax:     +1 410-694-5750";
  description
    "This YANG module defines Ciena's augmentations to openconfig-system.

      Copyright (c) 2018 Ciena Corporation.  All rights
      reserved.

      All information contained herein is, and remains
      the property of Ciena Corporation. Dissemination of this
      information or reproduction of this material is strictly
      forbidden unless prior written permission is obtained from
      Ciena Corporation.";

  revision 2021-07-30 {
    description
      "Added leaf data node to display MD5 and SHA1 fingerprint of
       installed SSH User Public Keys";
    reference "No specific reference or standard available.";
  }
  revision 2020-10-29 {
    description
      "User generated keys are not part of SSH server configurations,
       hence moving their state out of SSH server state hierarchy";
    reference "No specific reference or standard available.";
  }
  revision 2020-09-29 {
    description
      "Added supported objects for SSH server configurations";
    reference "RFC 4253: The Secure Shell (SSH) Transport Layer Protocol.";
  }
  revision 2018-01-29 {
    description
      "Initial version";
    reference
      "RFC 6020: YANG - A Data Modeling Language for
       the Network Configuration Protocol (NETCONF).
       No specific reference; standard not available.";
  }

  augment "/ncs:devices/ncs:device/ncs:rpc" {
    container rpc-ssh-user-pubkey-delete {
      tailf:ncs-device-type "netconf";
      tailf:display-when "not(../../ncs:module) or ../../ncs:module[ncs:name='ciena-openconfig-system']";
      tailf:action ssh-user-pubkey-delete {
        tailf:actionpoint ncsproxy {
          tailf:internal;
        }
        description
          "delete user's public key";
        input {
          leaf user {
            type string;
            mandatory true;
            description
              "The user for which public key needs to be deleted.";
          }
        }
        output {
          leaf status {
            type cn-type:ncs_rpc_notif_status;
            description
              "Status indicating if the operation has succeeded or not.";
          }
        }
      }
    }
  }
  augment "/ncs:devices/ncs:device-group/ncs:ned-id/ncs:rpc" {
    container rpc-ssh-user-pubkey-delete {
      tailf:ncs-device-type "netconf";
      tailf:display-when "/ncs:devices/ncs:device[ncs:name=current()/../../../ncs:member]/ncs:module[ncs:name='ciena-openconfig-system']";
      tailf:action ssh-user-pubkey-delete {
        tailf:actionpoint ncsproxy {
          tailf:internal;
        }
        description
          "delete user's public key";
        input {
          leaf user {
            type string;
            mandatory true;
            description
              "The user for which public key needs to be deleted.";
          }
        }
        output {
          container "device" {
            leaf "name" {
              type string;
            }
            leaf "info" {
              type string;
            }
            container "result" {
              leaf status {
                type cn-type:ncs_rpc_notif_status;
                description
                  "Status indicating if the operation has succeeded or not.";
              }
            }
          }
        }
      }
    }
  }
  augment "/ncs:devices/ncs:device/ncs:rpc" {
    container rpc-ssh-user-pubkey-install {
      tailf:ncs-device-type "netconf";
      tailf:display-when "not(../../ncs:module) or ../../ncs:module[ncs:name='ciena-openconfig-system']";
      tailf:action ssh-user-pubkey-install {
        tailf:actionpoint ncsproxy {
          tailf:internal;
        }
        description
          "Install SSH client's public key.";
        input {
          leaf user {
            type string;
            mandatory true;
            description
              "The user to which this public key belongs.";
          }
          uses ciena-ftt:ncs_rpc_notif_file-transfer-parameters;
        }
        output {
          leaf status {
            type cn-type:ncs_rpc_notif_status;
            description
              "Status indicating if the operation has succeeded or not.";
          }
        }
      }
    }
  }
  augment "/ncs:devices/ncs:device-group/ncs:ned-id/ncs:rpc" {
    container rpc-ssh-user-pubkey-install {
      tailf:ncs-device-type "netconf";
      tailf:display-when "/ncs:devices/ncs:device[ncs:name=current()/../../../ncs:member]/ncs:module[ncs:name='ciena-openconfig-system']";
      tailf:action ssh-user-pubkey-install {
        tailf:actionpoint ncsproxy {
          tailf:internal;
        }
        description
          "Install SSH client's public key.";
        input {
          leaf user {
            type string;
            mandatory true;
            description
              "The user to which this public key belongs.";
          }
          uses ciena-ftt:ncs_rpc_notif_file-transfer-parameters;
        }
        output {
          container "device" {
            leaf "name" {
              type string;
            }
            leaf "info" {
              type string;
            }
            container "result" {
              leaf status {
                type cn-type:ncs_rpc_notif_status;
                description
                  "Status indicating if the operation has succeeded or not.";
              }
            }
          }
        }
      }
    }
  }
  augment "/ncs:devices/ncs:device/ncs:rpc" {
    container rpc-ssh-server-host-key {
      tailf:ncs-device-type "netconf";
      tailf:display-when "not(../../ncs:module) or ../../ncs:module[ncs:name='ciena-openconfig-system']";
      tailf:action ssh-server-host-key {
        tailf:actionpoint ncsproxy {
          tailf:internal;
        }
        description
          "SSH server host key generate or delete operation.";
        input {
          leaf operation {
            type enumeration {
              enum "generate" {
                description
                  "Generate SSH server host key.";
              }
              enum "delete" {
                description
                  "Delete SSH server host key.";
              }
            }
            mandatory true;
            description
              "Generate or delete user generated SSH server host key";
          }
          leaf algorithm {
            type identityref {
              base sshtypes:pka-algo;
            }
            default "sshtypes:ssh-rsa";
            description
              "Public key authentication to generate SSH server host key";
          }
        }
        output {
          leaf status {
            type cn-type:ncs_rpc_notif_status;
            description
              "Status indicating if the operation has succeeded or not.";
          }
        }
      }
    }
  }
  augment "/ncs:devices/ncs:device-group/ncs:ned-id/ncs:rpc" {
    container rpc-ssh-server-host-key {
      tailf:ncs-device-type "netconf";
      tailf:display-when "/ncs:devices/ncs:device[ncs:name=current()/../../../ncs:member]/ncs:module[ncs:name='ciena-openconfig-system']";
      tailf:action ssh-server-host-key {
        tailf:actionpoint ncsproxy {
          tailf:internal;
        }
        description
          "SSH server host key generate or delete operation.";
        input {
          leaf operation {
            type enumeration {
              enum "generate" {
                description
                  "Generate SSH server host key.";
              }
              enum "delete" {
                description
                  "Delete SSH server host key.";
              }
            }
            mandatory true;
            description
              "Generate or delete user generated SSH server host key";
          }
          leaf algorithm {
            type identityref {
              base sshtypes:pka-algo;
            }
            default "sshtypes:ssh-rsa";
            description
              "Public key authentication to generate SSH server host key";
          }
        }
        output {
          container "device" {
            leaf "name" {
              type string;
            }
            leaf "info" {
              type string;
            }
            container "result" {
              leaf status {
                type cn-type:ncs_rpc_notif_status;
                description
                  "Status indicating if the operation has succeeded or not.";
              }
            }
          }
        }
      }
    }
  }
  augment "/ncs:devices/ncs:template/ncs:ned-id/ncs:config/oc-sys:system/oc-sys:aaa/oc-sys:authentication/oc-sys:users/oc-sys:user/oc-sys:config" {
    leaf password {
      type string;
      ncx:password;
      description
        "The user password in cleartext, only the hashed
         value will be stored";
    }
  }
  augment "/ncs:devices/ncs:device/ncs:live-status/oc-sys:system/oc-sys:aaa/oc-sys:authentication/oc-sys:users/oc-sys:user/oc-sys:config" {
    leaf password {
      tailf:ncs-device-type "netconf";
      tailf:display-when "not(../../../../../../../../ncs:module) or ../../../../../../../../ncs:module[ncs:name='ciena-openconfig-system'] or (../../../../../../../../ncs:live-status-protocol[not(ncs:capability)]) or (../../../../../../../../ncs:live-status-protocol/ncs:capability/ncs:module[.='ciena-openconfig-system'])";
      type string;
      ncx:password;
      description
        "The user password in cleartext, only the hashed
         value will be stored";
    }
  }
  augment "/ncs:devices/ncs:device/ncs:config/oc-sys:system/oc-sys:aaa/oc-sys:authentication/oc-sys:users/oc-sys:user/oc-sys:config" {
    leaf password {
      tailf:ncs-device-type "netconf";
      tailf:display-when "not(../../../../../../../../ncs:module) or ../../../../../../../../ncs:module[ncs:name='ciena-openconfig-system']";
      type string;
      ncx:password;
      description
        "The user password in cleartext, only the hashed
         value will be stored";
    }
  }
  augment "/ncs:devices/ncs:device/ncs:live-status/oc-sys:system/oc-sys:aaa/oc-sys:authentication/oc-sys:users/oc-sys:user/oc-sys:state" {
    leaf lockout-time {
      tailf:ncs-device-type "netconf";
      tailf:display-when "not(../../../../../../../../ncs:module) or ../../../../../../../../ncs:module[ncs:name='ciena-openconfig-system'] or (../../../../../../../../ncs:live-status-protocol[not(ncs:capability)]) or (../../../../../../../../ncs:live-status-protocol/ncs:capability/ncs:module[.='ciena-openconfig-system'])";
      type uint16;
      description
        "Amount of time left before the lockout ends";
    }
    leaf last-failure {
      tailf:ncs-device-type "netconf";
      tailf:display-when "not(../../../../../../../../ncs:module) or ../../../../../../../../ncs:module[ncs:name='ciena-openconfig-system'] or (../../../../../../../../ncs:live-status-protocol[not(ncs:capability)]) or (../../../../../../../../ncs:live-status-protocol/ncs:capability/ncs:module[.='ciena-openconfig-system'])";
      type yang:date-and-time;
      description
        "Last timestamp of user login failure";
    }
  }
  augment "/ncs:devices/ncs:template/ncs:ned-id/ncs:config/oc-sys:system/oc-sys:ssh-server/oc-sys:config" {
    description
      "Augmenting SSH server attributes to SSH server config";
    leaf public-key-authentication {
      type cn-type:ncs_template_admin-state;
      // NCS drop default statement
      description
        "Admin state of public key authentication on SSH server";
    }
    leaf-list encryption-algorithm {
      // NCS patched for predictable order
      ordered-by user;
      type string;
      description
        "Encryption algorithm configuration on  SSH server";
    }
    leaf-list kex-algorithm {
      // NCS patched for predictable order
      ordered-by user;
      type string;
      description
        "Key exchange algorithm configuration on  SSH server";
    }
    leaf-list mac-algorithm {
      // NCS patched for predictable order
      ordered-by user;
      type string;
      description
        "Mac algorithm configuration on  SSH server";
    }
    leaf-list pka-algorithm {
      // NCS patched for predictable order
      ordered-by user;
      type string;
      description
        "Public key algorithm configuration on SSH server";
    }
    leaf rekey-limit {
      type string;
      description
        "Max number of bytes that are transmitted before the
         session key is renegotiated.";
    }
    leaf rekey-time {
      type string;
      units "seconds";
      description
        "Max time in seconds after which SSH key is renegotiated.
         0 represents default value of rekey-time as per OpenSSH default configuration.";
    }
  }
  augment "/ncs:devices/ncs:device/ncs:live-status/oc-sys:system/oc-sys:ssh-server/oc-sys:config" {
    description
      "Augmenting SSH server attributes to SSH server config";
    leaf public-key-authentication {
      tailf:ncs-device-type "netconf";
      tailf:display-when "not(../../../../../ncs:module) or ../../../../../ncs:module[ncs:name='ciena-openconfig-system'] or (../../../../../ncs:live-status-protocol[not(ncs:capability)]) or (../../../../../ncs:live-status-protocol/ncs:capability/ncs:module[.='ciena-openconfig-system'])";
      type cn-type:live_ncs_admin-state;
      // NCS drop default statement
      description
        "Admin state of public key authentication on SSH server";
    }
    leaf-list encryption-algorithm {
      tailf:ncs-device-type "netconf";
      tailf:display-when "not(../../../../../ncs:module) or ../../../../../ncs:module[ncs:name='ciena-openconfig-system'] or (../../../../../ncs:live-status-protocol[not(ncs:capability)]) or (../../../../../ncs:live-status-protocol/ncs:capability/ncs:module[.='ciena-openconfig-system'])";
      type identityref {
        base sshtypes:encryption-algo;
      }
      description
        "Encryption algorithm configuration on  SSH server";
    }
    leaf-list kex-algorithm {
      tailf:ncs-device-type "netconf";
      tailf:display-when "not(../../../../../ncs:module) or ../../../../../ncs:module[ncs:name='ciena-openconfig-system'] or (../../../../../ncs:live-status-protocol[not(ncs:capability)]) or (../../../../../ncs:live-status-protocol/ncs:capability/ncs:module[.='ciena-openconfig-system'])";
      type identityref {
        base sshtypes:kex-algo;
      }
      description
        "Key exchange algorithm configuration on  SSH server";
    }
    leaf-list mac-algorithm {
      tailf:ncs-device-type "netconf";
      tailf:display-when "not(../../../../../ncs:module) or ../../../../../ncs:module[ncs:name='ciena-openconfig-system'] or (../../../../../ncs:live-status-protocol[not(ncs:capability)]) or (../../../../../ncs:live-status-protocol/ncs:capability/ncs:module[.='ciena-openconfig-system'])";
      type identityref {
        base sshtypes:mac-algo;
      }
      description
        "Mac algorithm configuration on  SSH server";
    }
    leaf-list pka-algorithm {
      tailf:ncs-device-type "netconf";
      tailf:display-when "not(../../../../../ncs:module) or ../../../../../ncs:module[ncs:name='ciena-openconfig-system'] or (../../../../../ncs:live-status-protocol[not(ncs:capability)]) or (../../../../../ncs:live-status-protocol/ncs:capability/ncs:module[.='ciena-openconfig-system'])";
      type identityref {
        base sshtypes:pka-algo;
      }
      description
        "Public key algorithm configuration on SSH server";
    }
    leaf rekey-limit {
      tailf:ncs-device-type "netconf";
      tailf:display-when "not(../../../../../ncs:module) or ../../../../../ncs:module[ncs:name='ciena-openconfig-system'] or (../../../../../ncs:live-status-protocol[not(ncs:capability)]) or (../../../../../ncs:live-status-protocol/ncs:capability/ncs:module[.='ciena-openconfig-system'])";
      type enumeration {
        enum "1G" {
          description
            "Rekey after transmitting 1G bytes.";
        }
        enum "500M" {
          description
            "Rekey after transmitting 500M bytes.";
        }
        enum "default" {
          description
            "default value of rekey limit as per OpenSSH default configuration.";
        }
      }
      description
        "Max number of bytes that are transmitted before the
         session key is renegotiated.";
    }
    leaf rekey-time {
      tailf:ncs-device-type "netconf";
      tailf:display-when "not(../../../../../ncs:module) or ../../../../../ncs:module[ncs:name='ciena-openconfig-system'] or (../../../../../ncs:live-status-protocol[not(ncs:capability)]) or (../../../../../ncs:live-status-protocol/ncs:capability/ncs:module[.='ciena-openconfig-system'])";
      type uint32 {
        range "0..3600";
      }
      units "seconds";
      description
        "Max time in seconds after which SSH key is renegotiated.
         0 represents default value of rekey-time as per OpenSSH default configuration.";
    }
  }
  augment "/ncs:devices/ncs:device/ncs:config/oc-sys:system/oc-sys:ssh-server/oc-sys:config" {
    description
      "Augmenting SSH server attributes to SSH server config";
    leaf public-key-authentication {
      tailf:ncs-device-type "netconf";
      tailf:display-when "not(../../../../../ncs:module) or ../../../../../ncs:module[ncs:name='ciena-openconfig-system']";
      type cn-type:admin-state;
      default "enabled";
      description
        "Admin state of public key authentication on SSH server";
    }
    leaf-list encryption-algorithm {
      tailf:ncs-device-type "netconf";
      tailf:display-when "not(../../../../../ncs:module) or ../../../../../ncs:module[ncs:name='ciena-openconfig-system']";
      type identityref {
        base sshtypes:encryption-algo;
      }
      description
        "Encryption algorithm configuration on  SSH server";
    }
    leaf-list kex-algorithm {
      tailf:ncs-device-type "netconf";
      tailf:display-when "not(../../../../../ncs:module) or ../../../../../ncs:module[ncs:name='ciena-openconfig-system']";
      type identityref {
        base sshtypes:kex-algo;
      }
      description
        "Key exchange algorithm configuration on  SSH server";
    }
    leaf-list mac-algorithm {
      tailf:ncs-device-type "netconf";
      tailf:display-when "not(../../../../../ncs:module) or ../../../../../ncs:module[ncs:name='ciena-openconfig-system']";
      type identityref {
        base sshtypes:mac-algo;
      }
      description
        "Mac algorithm configuration on  SSH server";
    }
    leaf-list pka-algorithm {
      tailf:ncs-device-type "netconf";
      tailf:display-when "not(../../../../../ncs:module) or ../../../../../ncs:module[ncs:name='ciena-openconfig-system']";
      type identityref {
        base sshtypes:pka-algo;
      }
      description
        "Public key algorithm configuration on SSH server";
    }
    leaf rekey-limit {
      tailf:ncs-device-type "netconf";
      tailf:display-when "not(../../../../../ncs:module) or ../../../../../ncs:module[ncs:name='ciena-openconfig-system']";
      type enumeration {
        enum "1G" {
          description
            "Rekey after transmitting 1G bytes.";
        }
        enum "500M" {
          description
            "Rekey after transmitting 500M bytes.";
        }
        enum "default" {
          description
            "default value of rekey limit as per OpenSSH default configuration.";
        }
      }
      description
        "Max number of bytes that are transmitted before the
         session key is renegotiated.";
    }
    leaf rekey-time {
      tailf:ncs-device-type "netconf";
      tailf:display-when "not(../../../../../ncs:module) or ../../../../../ncs:module[ncs:name='ciena-openconfig-system']";
      type uint32 {
        range "0..3600";
      }
      units "seconds";
      description
        "Max time in seconds after which SSH key is renegotiated.
         0 represents default value of rekey-time as per OpenSSH default configuration.";
    }
  }
  augment "/ncs:devices/ncs:device/ncs:live-status/oc-sys:system/oc-sys:state" {
    description
      "State of User generated keys either host key or client public key";
    container user-generated-host-key {
      tailf:ncs-device-type "netconf";
      tailf:display-when "not(../../../../ncs:module) or ../../../../ncs:module[ncs:name='ciena-openconfig-system'] or (../../../../ncs:live-status-protocol[not(ncs:capability)]) or (../../../../ncs:live-status-protocol/ncs:capability/ncs:module[.='ciena-openconfig-system'])";
      description
        "SSH server host key information.";
      leaf host-key-status {
        type enumeration {
          enum "generated" {
            description
              "SSH server host key is generated.";
          }
          enum "not-generated" {
            description
              "SSH server host key is not generated.";
          }
        }
        description
          "This leaf specifies the status of the
           SSH host key.";
      }
      leaf host-key-fingerprint {
        type string;
        description
          "This leaf displays the SHA256 fingerprint
           of SSH host key if it has been generated";
      }
      leaf host-key-type {
        type identityref {
          base sshtypes:pka-algo;
        }
        description
          "This leaf displays the public key algorithm
           used to generate host key";
      }
    }
    container user-public-keys {
      tailf:ncs-device-type "netconf";
      tailf:display-when "not(../../../../ncs:module) or ../../../../ncs:module[ncs:name='ciena-openconfig-system'] or (../../../../ncs:live-status-protocol[not(ncs:capability)]) or (../../../../ncs:live-status-protocol/ncs:capability/ncs:module[.='ciena-openconfig-system'])";
      description
        "SSH client public key information.";
      list user {
        key "user";
        description
          "User list.";
        leaf user {
          type string;
          description
            "The user for which public key has been installed.";
        }
        leaf fingerprint-md5 {
          type string;
          description
            "This leaf displays the MD5 fingerprint of user public key.";
        }
        leaf fingerprint-sha1 {
          type string;
          description
            "This leaf displays the SHA1 fingerprint of user public key.";
        }
      }
    }
  }
}
