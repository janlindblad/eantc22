module ciena-bfd-mpls-tp {
  // Generated by yanger -t ncs
  tailf:mount-id "ciena107-nc-1.0:ciena107-nc-1.0";
  tailf:ncs-device-type "netconf";

  namespace "http://ciena.com/ns/yang/ciena-bfd-mpls-tp";
  prefix ciena-bfd-mpls-tp;

  import ciena-bfd-types {
    prefix bfd-types;
  }
  import ciena-bfd-mpls {
    prefix bfd-mpls;
  }
  import ietf-yang-types {
    prefix yang;
  }
  import ciena-mpls-tp-corouted {
    prefix mpls-tp;
  }
  import tailf-common {
    prefix tailf;
  }
  import tailf-ncs {
    prefix ncs;
  }

  organization
    "Ciena Corporation";
  contact
    "Web URL: http://www.ciena.com/
     E-mail:  yang@ciena.com
     Postal:  7035 Ridge Road
     Hanover, Maryland 21076
     U.S.A.
     Phone:   +1 800-921-1144
     Fax:     +1 410-694-5750";
  description
    "This YANG module defines Ciena's MPLS-TP BFD protocol.
     Copyright (c) 2020  Ciena Corporation.  All rights
     reserved.
     All information contained herein is, and remains the
     property of Ciena Corporation. Dissemination of this
     information or reproduction of this material is strictly
     forbidden unless prior written permission is obtained
     from Ciena Corporation.";

  revision 2020-01-27 {
    description
      "Initial revision of MPLS-TP BFD model.";
  }

  grouping ncs_template_cv-packet-count {
    leaf cv-receive-packet-count {
      type string;
      description
        "Count of received BFD cv packets for this session. This includes
         valid and invalid received packets.";
    }
    leaf cv-send-packet-count {
      type string;
      description
        "Count of sent BFD cv packets for this session.";
    }
    description
      "BFD CV packet counters";
  }

  grouping ncs_template_lsp-bfd-cfg-params {
    container bfd-cfg-parms {
      description
        "BFD configuration on MPLS-TP LSP";
      // NCS expand uses statement
      // NCS expand uses statement
      leaf local-multiplier {
        type bfd-types:ncs_template_multiplier;
        // NCS drop default statement
        description
          "Multiplier transmitted by local system.";
      }
      leaf desired-min-tx-interval {
        type bfd-types:ncs_template_intervals;
        units "microseconds";
        // NCS drop default statement
        description
          "Desired minimum transmit interval of control packets in microseconds.";
      }
      leaf required-min-rx-interval {
        type bfd-types:ncs_template_intervals;
        units "microseconds";
        // NCS drop default statement
        description
          "Required minimum receive interval of control packets in microseconds.";
      }
      leaf accelerate {
        // NCS drop if-feature statement
        type string;
        // NCS drop default statement
        description
          "If enabled, BFD will run in an accelerated mode (for example, in hardware).";
      }
      leaf statistics-collection {
        // NCS drop when statement
        // NCS drop if-feature statement
        type string;
        // NCS drop default statement
        description
          "Determines whether statistics collection will be turned on or off for accelerated BFD session.";
      }
      leaf admin-down {
        type string;
        description
          "Is the BFD session administratively down.";
        // NCS drop default statement
      }
      uses bfd-mpls:ncs_template_encap-cfg;
      leaf gach-type {
        type bfd-mpls:ncs_template_gach-value;
        description
          "Gach-value for LSP BFD session";
      }
      leaf enable-cv {
        description
          "Enable Connectivity-verification(CV) feature ";
        // NCS drop when statement
        type empty;
      }
    }
  }

  grouping ncs_rpc_notif_cv-packet-count {
    leaf cv-receive-packet-count {
      type yang:counter64;
      description
        "Count of received BFD cv packets for this session. This includes
         valid and invalid received packets.";
    }
    leaf cv-send-packet-count {
      type yang:counter64;
      description
        "Count of sent BFD cv packets for this session.";
    }
    description
      "BFD CV packet counters";
  }

  grouping ncs_rpc_notif_lsp-bfd-cfg-params {
    container bfd-cfg-parms {
      description
        "BFD configuration on MPLS-TP LSP";
      // NCS expand uses statement
      // NCS expand uses statement
      leaf local-multiplier {
        type bfd-types:ncs_rpc_notif_multiplier;
        default "3";
        description
          "Multiplier transmitted by local system.";
      }
      leaf desired-min-tx-interval {
        type bfd-types:ncs_rpc_notif_intervals;
        units "microseconds";
        default "100000";
        description
          "Desired minimum transmit interval of control packets in microseconds.";
      }
      leaf required-min-rx-interval {
        type bfd-types:ncs_rpc_notif_intervals;
        units "microseconds";
        default "100000";
        description
          "Required minimum receive interval of control packets in microseconds.";
      }
      leaf accelerate {
        tailf:display-when "not(../../ncs:module) or boolean(/ncs:devices/ncs:device[ncs:name=current()/../../ncs:name]/capability/feature='accelerated-bfd')";
        type boolean;
        default "false";
        description
          "If enabled, BFD will run in an accelerated mode (for example, in hardware).";
      }
      leaf statistics-collection {
        when "../accelerate = 'true'" {
          tailf:xpath-root 3;
        }
        tailf:display-when "not(../../ncs:module) or boolean(/ncs:devices/ncs:device[ncs:name=current()/../../ncs:name]/capability/feature='accelerated-bfd')";
        type enumeration {
          enum "on" {
            value 0;
            description
              "Statistics-collection will be on for accelerated BFD session";
          }
          enum "off" {
            value 1;
            description
              "Statistics-collection will be off for accelerated BFD session";
          }
        }
        default "off";
        description
          "Determines whether statistics collection will be turned on or off for accelerated BFD session.";
      }
      leaf admin-down {
        type boolean;
        description
          "Is the BFD session administratively down.";
        default "true";
      }
      uses bfd-mpls:ncs_rpc_notif_encap-cfg;
      leaf gach-type {
        type bfd-mpls:ncs_rpc_notif_gach-value;
        description
          "Gach-value for LSP BFD session";
      }
      leaf enable-cv {
        description
          "Enable Connectivity-verification(CV) feature ";
        when "../gach-type = 'mpls-tp-cc'" {
          tailf:xpath-root 3;
        }
        type empty;
      }
    }
  }

  grouping live_ncs_cv-packet-count {
    leaf cv-receive-packet-count {
      type yang:counter64;
      description
        "Count of received BFD cv packets for this session. This includes
         valid and invalid received packets.";
    }
    leaf cv-send-packet-count {
      type yang:counter64;
      description
        "Count of sent BFD cv packets for this session.";
    }
    description
      "BFD CV packet counters";
  }

  grouping live_ncs_lsp-bfd-cfg-params {
    container bfd-cfg-parms {
      description
        "BFD configuration on MPLS-TP LSP";
      // NCS expand uses statement
      // NCS expand uses statement
      leaf local-multiplier {
        type bfd-types:live_ncs_multiplier;
        // NCS drop default statement
        description
          "Multiplier transmitted by local system.";
      }
      leaf desired-min-tx-interval {
        type bfd-types:live_ncs_intervals;
        units "microseconds";
        // NCS drop default statement
        description
          "Desired minimum transmit interval of control packets in microseconds.";
      }
      leaf required-min-rx-interval {
        type bfd-types:live_ncs_intervals;
        units "microseconds";
        // NCS drop default statement
        description
          "Required minimum receive interval of control packets in microseconds.";
      }
      leaf accelerate {
        // NCS drop if-feature statement
        type boolean;
        // NCS drop default statement
        description
          "If enabled, BFD will run in an accelerated mode (for example, in hardware).";
      }
      leaf statistics-collection {
        // NCS drop when statement
        // NCS drop if-feature statement
        type enumeration {
          enum "on" {
            value 0;
            description
              "Statistics-collection will be on for accelerated BFD session";
          }
          enum "off" {
            value 1;
            description
              "Statistics-collection will be off for accelerated BFD session";
          }
        }
        // NCS drop default statement
        description
          "Determines whether statistics collection will be turned on or off for accelerated BFD session.";
      }
      leaf admin-down {
        type boolean;
        description
          "Is the BFD session administratively down.";
        // NCS drop default statement
      }
      uses bfd-mpls:live_ncs_encap-cfg;
      leaf gach-type {
        type bfd-mpls:live_ncs_gach-value;
        description
          "Gach-value for LSP BFD session";
      }
      leaf enable-cv {
        description
          "Enable Connectivity-verification(CV) feature ";
        // NCS drop when statement
        type empty;
      }
    }
  }

  grouping cv-packet-count {
    leaf cv-receive-packet-count {
      type yang:counter64;
      description
        "Count of received BFD cv packets for this session. This includes
         valid and invalid received packets.";
    }
    leaf cv-send-packet-count {
      type yang:counter64;
      description
        "Count of sent BFD cv packets for this session.";
    }
    description
      "BFD CV packet counters";
  }

  grouping lsp-bfd-cfg-params {
    container bfd-cfg-parms {
      description
        "BFD configuration on MPLS-TP LSP";
      // NCS expand uses statement
      // NCS expand uses statement
      leaf local-multiplier {
        type bfd-types:multiplier;
        default "3";
        description
          "Multiplier transmitted by local system.";
      }
      leaf desired-min-tx-interval {
        type bfd-types:intervals;
        units "microseconds";
        default "100000";
        description
          "Desired minimum transmit interval of control packets in microseconds.";
      }
      leaf required-min-rx-interval {
        type bfd-types:intervals;
        units "microseconds";
        default "100000";
        description
          "Required minimum receive interval of control packets in microseconds.";
      }
      leaf accelerate {
        tailf:display-when "not(../../ncs:module) or boolean(/ncs:devices/ncs:device[ncs:name=current()/../../ncs:name]/capability/feature='accelerated-bfd')";
        type boolean;
        default "false";
        description
          "If enabled, BFD will run in an accelerated mode (for example, in hardware).";
      }
      leaf statistics-collection {
        when "../accelerate = 'true'" {
          tailf:xpath-root 3;
        }
        tailf:display-when "not(../../ncs:module) or boolean(/ncs:devices/ncs:device[ncs:name=current()/../../ncs:name]/capability/feature='accelerated-bfd')";
        type enumeration {
          enum "on" {
            value 0;
            description
              "Statistics-collection will be on for accelerated BFD session";
          }
          enum "off" {
            value 1;
            description
              "Statistics-collection will be off for accelerated BFD session";
          }
        }
        default "off";
        description
          "Determines whether statistics collection will be turned on or off for accelerated BFD session.";
      }
      leaf admin-down {
        type boolean;
        description
          "Is the BFD session administratively down.";
        default "true";
      }
      uses bfd-mpls:encap-cfg;
      leaf gach-type {
        type bfd-mpls:gach-value;
        description
          "Gach-value for LSP BFD session";
      }
      leaf enable-cv {
        description
          "Enable Connectivity-verification(CV) feature ";
        when "../gach-type = 'mpls-tp-cc'" {
          tailf:xpath-root 3;
        }
        type empty;
      }
    }
  }

  augment "/ncs:devices/ncs:template/ncs:ned-id/ncs:config/mpls-tp:tp-corouted-tunnels/mpls-tp:tunnel" {
    description
      "BFD configuration on MPLS-TP LSP.";
    uses ncs_template_lsp-bfd-cfg-params;
  }
  augment "/ncs:devices/ncs:device/ncs:live-status/mpls-tp:tp-corouted-tunnels/mpls-tp:tunnel" {
    description
      "BFD configuration on MPLS-TP LSP.";
    uses live_ncs_lsp-bfd-cfg-params {
      refine bfd-cfg-parms {
        tailf:ncs-device-type "netconf";
        tailf:display-when "not(../../../../ncs:module) or ../../../../ncs:module[ncs:name='ciena-bfd-mpls-tp'] or (../../../../ncs:live-status-protocol[not(ncs:capability)]) or (../../../../ncs:live-status-protocol/ncs:capability/ncs:module[.='ciena-bfd-mpls-tp'])";
      }
    }
  }
  augment "/ncs:devices/ncs:device/ncs:config/mpls-tp:tp-corouted-tunnels/mpls-tp:tunnel" {
    description
      "BFD configuration on MPLS-TP LSP.";
    uses lsp-bfd-cfg-params {
      refine bfd-cfg-parms {
        tailf:ncs-device-type "netconf";
        tailf:display-when "not(../../../../ncs:module) or ../../../../ncs:module[ncs:name='ciena-bfd-mpls-tp']";
      }
    }
  }
  augment "/ncs:devices/ncs:device/ncs:live-status/mpls-tp:tp-corouted-tunnel-state/mpls-tp:tunnel" {
    description
      "Augmenting MPLS-TP state information with BFD Session state information.";
    container bfd-state {
      tailf:ncs-device-type "netconf";
      tailf:display-when "not(../../../../ncs:module) or ../../../../ncs:module[ncs:name='ciena-bfd-mpls-tp'] or (../../../../ncs:live-status-protocol[not(ncs:capability)]) or (../../../../ncs:live-status-protocol/ncs:capability/ncs:module[.='ciena-bfd-mpls-tp'])";
      description
        "MPLS-TP BFD session state information.";
      uses bfd-types:live_ncs_common-cfg-parms;
      uses bfd-mpls:live_ncs_encap-cfg;
      leaf gach-type {
        description
          "Gach-value for LSP BFD session";
        type bfd-mpls:live_ncs_gach-value;
      }
      leaf enable-cv {
        description
          "Enable Connectivity-verification(CV) feature ";
        type empty;
      }
      uses bfd-types:live_ncs_all-session {
        augment "session-statistics" {
          uses live_ncs_cv-packet-count;
        }
      }
    }
  }

  identity path-lsp {
    base bfd-types:path-type;
    description
      "BFD on Label Switched Paths.";
    reference
      "RFC 5884: Bidirectional Forwarding Detection (BFD)
       for MPLS Label Switched Paths (LSPs)";
  }
}
