module ciena-ietf-twamp-deviation-saos {
  // Generated by yanger -t ncs
  tailf:mount-id "ciena107-nc-1.0:ciena107-nc-1.0";
  tailf:ncs-device-type "netconf";

  namespace "urn:ciena:params:xml:ns:yang:ciena-pn:ciena-ietf-twamp-deviation-saos";
  prefix ciena-ietf-twamp-deviation-saos;

  import ietf-twamp {
    prefix ietf-twamp;
  }
  import ietf-inet-types {
    prefix inet;
  }
  import tailf-common {
    prefix tailf;
  }
  import tailf-ncs {
    prefix ncs;
  }

  organization
    "Ciena Corporation";
  contact
    "Web URL: http://www.ciena.com/
     E-mail:  yang@ciena.com
     Postal:  7035 Ridge Road
              Hanover, Maryland 21076
              U.S.A.
     Phone:   +1 800-921-1144
     Fax:     +1 410-694-5750";
  description
    "This YANG module defines Ciena's deviations from the ietf-twamp model.

     Copyright (c) 2018 Ciena Corporation.  All rights
     reserved.

     All information contained herein is, and remains
     the property of Ciena Corporation. Dissemination of this
     information or reproduction of this material is strictly
     forbidden unless prior written permission is obtained from
     Ciena Corporation.";

  revision 2015-12-03 {
    description
      "Initial revision.";
    reference "ietf-twamp-yang";
  }

  deviation "/ncs:devices/ncs:template/ncs:ned-id/ncs:config/ietf-twamp:twamp/ietf-twamp:server/ietf-twamp:admin-state" {
    deviate replace {
      // NCS drop mandatory statement
    }
    deviate add {
      // NCS drop default statement
    }
  }
  deviation "/ncs:devices/ncs:device/ncs:live-status/ietf-twamp:twamp/ietf-twamp:server/ietf-twamp:admin-state" {
    deviate replace {
      // NCS drop mandatory statement
    }
    deviate add {
      // NCS drop default statement
    }
  }
  deviation "/ncs:devices/ncs:device/ncs:config/ietf-twamp:twamp/ietf-twamp:server/ietf-twamp:admin-state" {
    deviate replace {
      mandatory false;
    }
    deviate add {
      default "false";
    }
  }
  deviation "/ncs:devices/ncs:template/ncs:ned-id/ncs:config/ietf-twamp:twamp/ietf-twamp:server/ietf-twamp:servwait" {
    deviate replace {
      // NCS drop default statement
    }
  }
  deviation "/ncs:devices/ncs:device/ncs:live-status/ietf-twamp:twamp/ietf-twamp:server/ietf-twamp:servwait" {
    deviate replace {
      // NCS drop default statement
    }
  }
  deviation "/ncs:devices/ncs:device/ncs:config/ietf-twamp:twamp/ietf-twamp:server/ietf-twamp:servwait" {
    deviate replace {
      default "90";
    }
  }
  deviation "/ncs:devices/ncs:template/ncs:ned-id/ncs:config/ietf-twamp:twamp/ietf-twamp:server/ietf-twamp:control-packet-dscp" {
    deviate add {
      // NCS drop default statement
    }
  }
  deviation "/ncs:devices/ncs:device/ncs:live-status/ietf-twamp:twamp/ietf-twamp:server/ietf-twamp:control-packet-dscp" {
    deviate add {
      // NCS drop default statement
    }
  }
  deviation "/ncs:devices/ncs:device/ncs:config/ietf-twamp:twamp/ietf-twamp:server/ietf-twamp:control-packet-dscp" {
    deviate add {
      default "0";
    }
  }
  deviation "/ncs:devices/ncs:template/ncs:ned-id/ncs:config/ietf-twamp:twamp/ietf-twamp:server/ietf-twamp:count" {
    deviate not-supported;
  }
  deviation "/ncs:devices/ncs:device/ncs:live-status/ietf-twamp:twamp/ietf-twamp:server/ietf-twamp:count" {
    deviate not-supported;
  }
  deviation "/ncs:devices/ncs:device/ncs:config/ietf-twamp:twamp/ietf-twamp:server/ietf-twamp:count" {
    deviate not-supported;
  }
  deviation "/ncs:devices/ncs:template/ncs:ned-id/ncs:config/ietf-twamp:twamp/ietf-twamp:server/ietf-twamp:max-count" {
    deviate not-supported;
  }
  deviation "/ncs:devices/ncs:device/ncs:live-status/ietf-twamp:twamp/ietf-twamp:server/ietf-twamp:max-count" {
    deviate not-supported;
  }
  deviation "/ncs:devices/ncs:device/ncs:config/ietf-twamp:twamp/ietf-twamp:server/ietf-twamp:max-count" {
    deviate not-supported;
  }
  deviation "/ncs:devices/ncs:template/ncs:ned-id/ncs:config/ietf-twamp:twamp/ietf-twamp:server/ietf-twamp:modes" {
    deviate add {
      // NCS drop default statement
    }
  }
  deviation "/ncs:devices/ncs:device/ncs:live-status/ietf-twamp:twamp/ietf-twamp:server/ietf-twamp:modes" {
    deviate add {
      // NCS drop default statement
    }
  }
  deviation "/ncs:devices/ncs:device/ncs:config/ietf-twamp:twamp/ietf-twamp:server/ietf-twamp:modes" {
    deviate add {
      default "unauthenticated";
    }
  }
  deviation "/ncs:devices/ncs:template/ncs:ned-id/ncs:config/ietf-twamp:twamp/ietf-twamp:server/ietf-twamp:key-chain" {
    deviate not-supported;
  }
  deviation "/ncs:devices/ncs:device/ncs:live-status/ietf-twamp:twamp/ietf-twamp:server/ietf-twamp:key-chain" {
    deviate not-supported;
  }
  deviation "/ncs:devices/ncs:device/ncs:config/ietf-twamp:twamp/ietf-twamp:server/ietf-twamp:key-chain" {
    deviate not-supported;
  }
  deviation "/ncs:devices/ncs:template/ncs:ned-id/ncs:config/ietf-twamp:twamp/ietf-twamp:session-reflector/ietf-twamp:admin-state" {
    deviate replace {
      // NCS drop mandatory statement
    }
    deviate add {
      // NCS drop default statement
    }
  }
  deviation "/ncs:devices/ncs:device/ncs:live-status/ietf-twamp:twamp/ietf-twamp:session-reflector/ietf-twamp:admin-state" {
    deviate replace {
      // NCS drop mandatory statement
    }
    deviate add {
      // NCS drop default statement
    }
  }
  deviation "/ncs:devices/ncs:device/ncs:config/ietf-twamp:twamp/ietf-twamp:session-reflector/ietf-twamp:admin-state" {
    deviate replace {
      mandatory false;
    }
    deviate add {
      default "false";
    }
  }
  deviation "/ncs:devices/ncs:template/ncs:ned-id/ncs:config/ietf-twamp:twamp/ietf-twamp:session-reflector/ietf-twamp:refwait" {
    deviate replace {
      // NCS drop default statement
    }
  }
  deviation "/ncs:devices/ncs:device/ncs:live-status/ietf-twamp:twamp/ietf-twamp:session-reflector/ietf-twamp:refwait" {
    deviate replace {
      // NCS drop default statement
    }
  }
  deviation "/ncs:devices/ncs:device/ncs:config/ietf-twamp:twamp/ietf-twamp:session-reflector/ietf-twamp:refwait" {
    deviate replace {
      default "90";
    }
  }
  deviation "/ncs:devices/ncs:device/ncs:live-status/ietf-twamp:twamp/ietf-twamp:server/ietf-twamp:ctrl-connection/ietf-twamp:key-id" {
    deviate not-supported;
  }
  deviation "/ncs:devices/ncs:device/ncs:live-status/ietf-twamp:twamp/ietf-twamp:server/ietf-twamp:ctrl-connection/ietf-twamp:count" {
    deviate not-supported;
  }
  deviation "/ncs:devices/ncs:device/ncs:live-status/ietf-twamp:twamp/ietf-twamp:server/ietf-twamp:ctrl-connection/ietf-twamp:max-count" {
    deviate not-supported;
  }
  deviation "/ncs:devices/ncs:device/ncs:live-status/ietf-twamp:twamp/ietf-twamp:server/ietf-twamp:ctrl-connection/ietf-twamp:salt" {
    deviate not-supported;
  }
  deviation "/ncs:devices/ncs:device/ncs:live-status/ietf-twamp:twamp/ietf-twamp:server/ietf-twamp:ctrl-connection/ietf-twamp:server-iv" {
    deviate not-supported;
  }
  deviation "/ncs:devices/ncs:device/ncs:live-status/ietf-twamp:twamp/ietf-twamp:server/ietf-twamp:ctrl-connection/ietf-twamp:challenge" {
    deviate not-supported;
  }
  deviation "/ncs:devices/ncs:device/ncs:live-status/ietf-twamp:twamp/ietf-twamp:session-reflector/ietf-twamp:test-session/ietf-twamp:sender-udp-port" {
    deviate replace {
      type inet:port-number;
    }
  }
  deviation "/ncs:devices/ncs:device/ncs:live-status/ietf-twamp:twamp/ietf-twamp:session-reflector/ietf-twamp:test-session/ietf-twamp:reflector-udp-port" {
    deviate replace {
      type inet:port-number;
    }
  }
}
