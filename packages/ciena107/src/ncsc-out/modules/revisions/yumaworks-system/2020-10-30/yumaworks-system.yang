module yumaworks-system {
  // Generated by yanger -t ncs
  tailf:mount-id "ciena107-nc-1.0:ciena107-nc-1.0";
  tailf:ncs-device-type "netconf";

  namespace "http://yumaworks.com/ns/yumaworks-system";
  prefix ysys;

  import ietf-netconf {
    prefix nc;
  }
  import ietf-netconf-acm {
    prefix nacm;
  }
  import ietf-netconf-monitoring {
    prefix ncm;
  }
  import ietf-yang-types {
    prefix yang;
  }
  import yuma-app-common {
    prefix yumaapp;
  }
  import yuma-ncx {
    prefix ncx;
  }
  import yuma-types {
    prefix nt;
  }
  import yumaworks-app-common {
    prefix ywapp;
  }
  import yumaworks-restconf {
    prefix rc;
  }
  import yumaworks-types {
    prefix ywt;
  }
  import tailf-common {
    prefix tailf;
  }
  import tailf-ncs {
    prefix ncs;
  }

  organization
    "YumaWorks, Inc.";
  contact
    "Support <support at yumaworks.com>";
  description
    "Common system operations for the netconfd-pro server.

     Copyright (c) 2013 - 2020 YumaWorks, Inc. All rights reserved.

     Redistribution and use in source and binary forms, with or
     without modification, is permitted pursuant to, and subject
     to the license terms contained in, the BSD 3-Clause License
     http://opensource.org/licenses/BSD-3-Clause";

  revision 2020-10-30 {
    description
      "Add log-stream parameter to the set-log-level operation";
  }
  revision 2020-03-06 {
    description
      "Change backup file name to use NcxFileName type.";
  }
  revision 2019-01-22 {
    description
      "Move <replay-config> to yumaworks-internal module.";
  }
  revision 2018-04-24 {
    description
      "Add module-tag parameter to NACM.";
  }
  revision 2018-04-14 {
    description
      "Add module-tag parameter to get and get-config.
       Add get-module-tags RPC operation.
       Add copy of set-log-level RPC operation from yuma-system.";
  }
  revision 2017-12-22 {
    description
      "Copy load rpc into this module so yuma-system
       can be removed.";
  }
  revision 2017-10-06 {
    description
      "Add save-config parameter to the load and
       load-bundle operations.
       Add delete-config parameter to the unload and
       unload-bundle operations.";
  }
  revision 2016-08-24 {
    description
      "Add unload-bundle operation.";
  }
  revision 2016-04-27 {
    description
      "Add deviation parameter to load-bundle input params.";
  }
  revision 2015-09-26 {
    description
      "Add depth parameter to get, get-config, and
       copy-config operations.";
  }
  revision 2014-10-16 {
    description
      "Add with-owners parameter to get, get-config, and
       copy-config operations.";
  }
  revision 2014-05-27 {
    description
      "Add overwrite parameter to backup operation.";
  }
  revision 2014-01-09 {
    description
      "Add load-bundle operation.";
  }
  revision 2013-11-13 {
    description
      "Add replay-config internal operation.
       Add module-type leaf to netconf-state schema list";
  }
  revision 2013-09-19 {
    description
      "Add comment parameter to commit operation.";
  }
  revision 2013-08-30 {
    description
      "Add unload operation.";
  }
  revision 2013-07-16 {
    description
      "Add cancel-subscription operation.";
  }
  revision 2013-01-06 {
    description
      "Initial version.";
  }

  grouping ncs_template_with-owners-parm {
    leaf with-owners {
      type empty;
      description
        "Include the 'ywx:owner' attribute in the response for nodes
         that have stored owner names.  The --save-owners CLI parameter
         for the server must be set to 'complex' or 'all' for any
         owner names to be saved.";
    }
  }

  grouping ncs_template_save-config-parm {
    leaf save-config {
      type string;
      // NCS drop default statement
      description
        "If 'true' then save the module or bundle load
         configuration in the --confdir directory, if the
         load or load-bundle operation is completed without
         errors.

         Ignored if the --no-config CLI parameter is used
         or the --confdir CLI parameter is not specified
         and no default configuration directory is found.

         A configuration file is created or replaced in this
         directory with the name <module-name>.conf.";
    }
  }

  grouping ncs_template_delete-config-parm {
    leaf delete-config {
      type string;
      // NCS drop default statement
      description
        "If 'true' then delete the module or bundle load
         configuration in the --confdir directory, if the unload
         or unload-bundle operation is completed without errors.

         Ignored if the --no-config CLI parameter is used
         or the --confdir CLI parameter is not specified
         and no default configuration directory is found.

         A configuration file is deleted in this
         directory with the name <module-name>.conf.";
    }
  }

  grouping ncs_rpc_notif_with-owners-parm {
    leaf with-owners {
      type empty;
      description
        "Include the 'ywx:owner' attribute in the response for nodes
         that have stored owner names.  The --save-owners CLI parameter
         for the server must be set to 'complex' or 'all' for any
         owner names to be saved.";
    }
  }

  grouping ncs_rpc_notif_save-config-parm {
    leaf save-config {
      type boolean;
      default "false";
      description
        "If 'true' then save the module or bundle load
         configuration in the --confdir directory, if the
         load or load-bundle operation is completed without
         errors.

         Ignored if the --no-config CLI parameter is used
         or the --confdir CLI parameter is not specified
         and no default configuration directory is found.

         A configuration file is created or replaced in this
         directory with the name <module-name>.conf.";
    }
  }

  grouping ncs_rpc_notif_delete-config-parm {
    leaf delete-config {
      type boolean;
      default "false";
      description
        "If 'true' then delete the module or bundle load
         configuration in the --confdir directory, if the unload
         or unload-bundle operation is completed without errors.

         Ignored if the --no-config CLI parameter is used
         or the --confdir CLI parameter is not specified
         and no default configuration directory is found.

         A configuration file is deleted in this
         directory with the name <module-name>.conf.";
    }
  }

  grouping live_ncs_with-owners-parm {
    leaf with-owners {
      type empty;
      description
        "Include the 'ywx:owner' attribute in the response for nodes
         that have stored owner names.  The --save-owners CLI parameter
         for the server must be set to 'complex' or 'all' for any
         owner names to be saved.";
    }
  }

  grouping live_ncs_save-config-parm {
    leaf save-config {
      type boolean;
      // NCS drop default statement
      description
        "If 'true' then save the module or bundle load
         configuration in the --confdir directory, if the
         load or load-bundle operation is completed without
         errors.

         Ignored if the --no-config CLI parameter is used
         or the --confdir CLI parameter is not specified
         and no default configuration directory is found.

         A configuration file is created or replaced in this
         directory with the name <module-name>.conf.";
    }
  }

  grouping live_ncs_delete-config-parm {
    leaf delete-config {
      type boolean;
      // NCS drop default statement
      description
        "If 'true' then delete the module or bundle load
         configuration in the --confdir directory, if the unload
         or unload-bundle operation is completed without errors.

         Ignored if the --no-config CLI parameter is used
         or the --confdir CLI parameter is not specified
         and no default configuration directory is found.

         A configuration file is deleted in this
         directory with the name <module-name>.conf.";
    }
  }

  grouping with-owners-parm {
    leaf with-owners {
      type empty;
      description
        "Include the 'ywx:owner' attribute in the response for nodes
         that have stored owner names.  The --save-owners CLI parameter
         for the server must be set to 'complex' or 'all' for any
         owner names to be saved.";
    }
  }

  grouping save-config-parm {
    leaf save-config {
      type boolean;
      default "false";
      description
        "If 'true' then save the module or bundle load
         configuration in the --confdir directory, if the
         load or load-bundle operation is completed without
         errors.

         Ignored if the --no-config CLI parameter is used
         or the --confdir CLI parameter is not specified
         and no default configuration directory is found.

         A configuration file is created or replaced in this
         directory with the name <module-name>.conf.";
    }
  }

  grouping delete-config-parm {
    leaf delete-config {
      type boolean;
      default "false";
      description
        "If 'true' then delete the module or bundle load
         configuration in the --confdir directory, if the unload
         or unload-bundle operation is completed without errors.

         Ignored if the --no-config CLI parameter is used
         or the --confdir CLI parameter is not specified
         and no default configuration directory is found.

         A configuration file is deleted in this
         directory with the name <module-name>.conf.";
    }
  }

  augment "/ncs:devices/ncs:device/ncs:rpc" {
    container rpc-set-log-level {
      tailf:ncs-device-type "netconf";
      tailf:display-when "not(../../ncs:module) or ../../ncs:module[ncs:name='yumaworks-system']";
      tailf:action set-log-level {
        tailf:actionpoint ncsproxy {
          tailf:internal;
        }
        nacm:default-deny-all;
        description
          "Sets the server log verbosity level.
           Copied from deprecated yuma-system.yang/";
        input {
          ncx:default-parm "log-level";
          leaf log-level {
            description
              "The desired verbosity level for system logging
               messages generated by the server.
               The current value can be obtained by retrieving
               the /system/sysLogLevel object.";
            type nt:ncs_rpc_notif_NcDebugType;
            mandatory true;
          }
          leaf log-stream {
            type enumeration {
              enum "main" {
                description
                  "The main logging stream is used, associated
                   with the --log parameter file, or direct output
                   to STDOUT or STDERR, or the vendor-specific
                   output if the --log-vendor parameter is used.

                   The --log-level parameter value for the next
                   reboot is not affected by this operation.";
              }
              enum "audit" {
                description
                  "The audit logging stream associated with
                   the --audit-log parameter, or the default audit
                   log, which is only created if --fileloc-fhs=true
                   is used.

                   The --audit-log-level parameter value for the next
                   reboot is not affected by this operation.

                   Audit logging is only done when the audit-log-level
                   is greater or equal to the current log-level.";
              }
              enum "syslog" {
                description
                  "The syslog logging stream associated with
                   the --log-syslog parameter is used.

                   The --log-syslog-level parameter value for the next
                   reboot is not affected by this operation.";
              }
            }
            default "main";
            description
              "The desired logging stream to use when changing
               the log level.";
          }
        }
      }
    }
  }
  augment "/ncs:devices/ncs:device-group/ncs:ned-id/ncs:rpc" {
    container rpc-set-log-level {
      tailf:ncs-device-type "netconf";
      tailf:display-when "/ncs:devices/ncs:device[ncs:name=current()/../../../ncs:member]/ncs:module[ncs:name='yumaworks-system']";
      tailf:action set-log-level {
        tailf:actionpoint ncsproxy {
          tailf:internal;
        }
        nacm:default-deny-all;
        description
          "Sets the server log verbosity level.
           Copied from deprecated yuma-system.yang/";
        input {
          ncx:default-parm "log-level";
          leaf log-level {
            description
              "The desired verbosity level for system logging
               messages generated by the server.
               The current value can be obtained by retrieving
               the /system/sysLogLevel object.";
            type nt:ncs_rpc_notif_NcDebugType;
            mandatory true;
          }
          leaf log-stream {
            type enumeration {
              enum "main" {
                description
                  "The main logging stream is used, associated
                   with the --log parameter file, or direct output
                   to STDOUT or STDERR, or the vendor-specific
                   output if the --log-vendor parameter is used.

                   The --log-level parameter value for the next
                   reboot is not affected by this operation.";
              }
              enum "audit" {
                description
                  "The audit logging stream associated with
                   the --audit-log parameter, or the default audit
                   log, which is only created if --fileloc-fhs=true
                   is used.

                   The --audit-log-level parameter value for the next
                   reboot is not affected by this operation.

                   Audit logging is only done when the audit-log-level
                   is greater or equal to the current log-level.";
              }
              enum "syslog" {
                description
                  "The syslog logging stream associated with
                   the --log-syslog parameter is used.

                   The --log-syslog-level parameter value for the next
                   reboot is not affected by this operation.";
              }
            }
            default "main";
            description
              "The desired logging stream to use when changing
               the log level.";
          }
        }
      }
    }
  }
  augment "/ncs:devices/ncs:device/ncs:rpc" {
    container rpc-get-module-tags {
      tailf:ncs-device-type "netconf";
      tailf:display-when "not(../../ncs:module) or ../../ncs:module[ncs:name='yumaworks-system']";
      tailf:action get-module-tags {
        tailf:actionpoint ncsproxy {
          tailf:internal;
        }
        description
          "Get the list of configured module-tags.
           The --module-tagmap parameter is used to configure
           a module-tag.";
        output {
          list module-tag {
            key "tag";
            leaf tag {
              type string;
              description
                "The module-tag value";
            }
            leaf-list module {
              type string;
              description
                "A module-name mapped to this module-tag";
            }
          }
        }
      }
    }
  }
  augment "/ncs:devices/ncs:device-group/ncs:ned-id/ncs:rpc" {
    container rpc-get-module-tags {
      tailf:ncs-device-type "netconf";
      tailf:display-when "/ncs:devices/ncs:device[ncs:name=current()/../../../ncs:member]/ncs:module[ncs:name='yumaworks-system']";
      tailf:action get-module-tags {
        tailf:actionpoint ncsproxy {
          tailf:internal;
        }
        description
          "Get the list of configured module-tags.
           The --module-tagmap parameter is used to configure
           a module-tag.";
        output {
          container "device" {
            leaf "name" {
              type string;
            }
            leaf "info" {
              type string;
            }
            container "result" {
              list module-tag {
                key "tag";
                leaf tag {
                  type string;
                  description
                    "The module-tag value";
                }
                leaf-list module {
                  type string;
                  description
                    "A module-name mapped to this module-tag";
                }
              }
            }
          }
        }
      }
    }
  }
  augment "/ncs:devices/ncs:device/ncs:rpc" {
    container rpc-load {
      tailf:ncs-device-type "netconf";
      tailf:display-when "not(../../ncs:module) or ../../ncs:module[ncs:name='yumaworks-system']";
      tailf:action load {
        tailf:actionpoint ncsproxy {
          tailf:internal;
        }
        nacm:default-deny-all;
        description
          "Load a module into the server, if it is not already loaded.
           Returns the module revision date (or today's date if none),
           of the module that was loaded, or an error if not found
           or the module found had errors and was not loaded
           successfully.  If the module is already loaded, then the
           revision date will simply be returned.";
        input {
          ncx:default-parm "module";
          leaf module {
            description
              "Name of the module to load.";
            mandatory true;
            type nt:ncs_rpc_notif_NcxName;
          }
          leaf revision {
            description
              "Module revision to load.";
            type nt:ncs_rpc_notif_Date;
          }
          uses yumaapp:ncs_rpc_notif_DeviationParm;
          uses ncs_rpc_notif_save-config-parm;
        }
        output {
          leaf mod-revision {
            description
              "Revision date of the module in use by the server.
               Will only be present if the module has a version";
            type nt:ncs_rpc_notif_Date;
          }
        }
      }
    }
  }
  augment "/ncs:devices/ncs:device-group/ncs:ned-id/ncs:rpc" {
    container rpc-load {
      tailf:ncs-device-type "netconf";
      tailf:display-when "/ncs:devices/ncs:device[ncs:name=current()/../../../ncs:member]/ncs:module[ncs:name='yumaworks-system']";
      tailf:action load {
        tailf:actionpoint ncsproxy {
          tailf:internal;
        }
        nacm:default-deny-all;
        description
          "Load a module into the server, if it is not already loaded.
           Returns the module revision date (or today's date if none),
           of the module that was loaded, or an error if not found
           or the module found had errors and was not loaded
           successfully.  If the module is already loaded, then the
           revision date will simply be returned.";
        input {
          ncx:default-parm "module";
          leaf module {
            description
              "Name of the module to load.";
            mandatory true;
            type nt:ncs_rpc_notif_NcxName;
          }
          leaf revision {
            description
              "Module revision to load.";
            type nt:ncs_rpc_notif_Date;
          }
          uses yumaapp:ncs_rpc_notif_DeviationParm;
          uses ncs_rpc_notif_save-config-parm;
        }
        output {
          container "device" {
            leaf "name" {
              type string;
            }
            leaf "info" {
              type string;
            }
            container "result" {
              leaf mod-revision {
                description
                  "Revision date of the module in use by the server.
                   Will only be present if the module has a version";
                type nt:ncs_rpc_notif_Date;
              }
            }
          }
        }
      }
    }
  }
  augment "/ncs:devices/ncs:device/ncs:rpc" {
    container rpc-unload-bundle {
      tailf:ncs-device-type "netconf";
      tailf:display-when "not(../../ncs:module) or ../../ncs:module[ncs:name='yumaworks-system']";
      tailf:action unload-bundle {
        tailf:actionpoint ncsproxy {
          tailf:internal;
        }
        nacm:default-deny-all;
        description
          "Unload a SIL bundle from the server, if it is loaded.";
        input {
          ncx:default-parm "bundle";
          leaf bundle {
            description
              "Name of the SIL bundle to unload.";
            mandatory true;
            type nt:ncs_rpc_notif_NcxName;
          }
          uses ncs_rpc_notif_delete-config-parm;
        }
      }
    }
  }
  augment "/ncs:devices/ncs:device-group/ncs:ned-id/ncs:rpc" {
    container rpc-unload-bundle {
      tailf:ncs-device-type "netconf";
      tailf:display-when "/ncs:devices/ncs:device[ncs:name=current()/../../../ncs:member]/ncs:module[ncs:name='yumaworks-system']";
      tailf:action unload-bundle {
        tailf:actionpoint ncsproxy {
          tailf:internal;
        }
        nacm:default-deny-all;
        description
          "Unload a SIL bundle from the server, if it is loaded.";
        input {
          ncx:default-parm "bundle";
          leaf bundle {
            description
              "Name of the SIL bundle to unload.";
            mandatory true;
            type nt:ncs_rpc_notif_NcxName;
          }
          uses ncs_rpc_notif_delete-config-parm;
        }
      }
    }
  }
  augment "/ncs:devices/ncs:device/ncs:rpc" {
    container rpc-load-bundle {
      tailf:ncs-device-type "netconf";
      tailf:display-when "not(../../ncs:module) or ../../ncs:module[ncs:name='yumaworks-system']";
      tailf:action load-bundle {
        tailf:actionpoint ncsproxy {
          tailf:internal;
        }
        nacm:default-deny-all;
        description
          "Load a SIL bundle into the server, if it is not already loaded.";
        input {
          ncx:default-parm "bundle";
          leaf bundle {
            description
              "Name of the SIL bundle to load.";
            mandatory true;
            type nt:ncs_rpc_notif_NcxName;
          }
          uses yumaapp:ncs_rpc_notif_DeviationParm;
          uses ncs_rpc_notif_save-config-parm;
        }
      }
    }
  }
  augment "/ncs:devices/ncs:device-group/ncs:ned-id/ncs:rpc" {
    container rpc-load-bundle {
      tailf:ncs-device-type "netconf";
      tailf:display-when "/ncs:devices/ncs:device[ncs:name=current()/../../../ncs:member]/ncs:module[ncs:name='yumaworks-system']";
      tailf:action load-bundle {
        tailf:actionpoint ncsproxy {
          tailf:internal;
        }
        nacm:default-deny-all;
        description
          "Load a SIL bundle into the server, if it is not already loaded.";
        input {
          ncx:default-parm "bundle";
          leaf bundle {
            description
              "Name of the SIL bundle to load.";
            mandatory true;
            type nt:ncs_rpc_notif_NcxName;
          }
          uses yumaapp:ncs_rpc_notif_DeviationParm;
          uses ncs_rpc_notif_save-config-parm;
        }
      }
    }
  }
  augment "/ncs:devices/ncs:device/ncs:rpc" {
    container rpc-unload {
      tailf:ncs-device-type "netconf";
      tailf:display-when "not(../../ncs:module) or ../../ncs:module[ncs:name='yumaworks-system']";
      tailf:action unload {
        tailf:actionpoint ncsproxy {
          tailf:internal;
        }
        nacm:default-deny-all;
        description
          "Unload a module from the server. Remove the associated
           server instrumentation library (SIL). Remove any data
           nodes in the system from the module. Remove the module
           from the server capabilities and NETCONF monitoring
           data. Remove the module namespace from the system.

           Note: this operation does not remove the --module parameter
           from the server configuration file if it exists.

           The following conditions must be true for the unload to be
           attempted by the server:

             * The module is allowed to be unloaded. It is data-model
               and vendor specific whether a module can be
               removed at run-time.

             * There are no dependencies on the module being removed.
               No modules that import this module are also loaded.

             * The module was loaded into the server, either via the
               <load> operation or the --module configuration parameter.

             * No datastores are currently locked.  The server will
               attempt to lock all datastores on behalf of the client
               for the entire unload operation.

             * The candidate datastore does not contain any edits
               that have not been committed.

             * No confirmed-commit operation is in progress.

           If all these conditions are met then the server will
           attempt to unload the specified module.  The unload
           operation can fail for various reasons:

             * The client does not have write privileges for
               all data being deleted. This includes any
               top-level data nodes and any nested augment
               nodes in other modules.

             * The deletion of one or more nodes would cause the
               running datastore to fail any YANG validation
               tests in RFC 6020, sec. 8.3.3.

             * Server resource errors occur
          ";
        input {
          ncx:default-parm "module";
          leaf module {
            type nt:ncs_rpc_notif_NcxName;
            mandatory true;
            description
              "The name of the module to unload.";
          }
          uses ncs_rpc_notif_delete-config-parm;
        }
      }
    }
  }
  augment "/ncs:devices/ncs:device-group/ncs:ned-id/ncs:rpc" {
    container rpc-unload {
      tailf:ncs-device-type "netconf";
      tailf:display-when "/ncs:devices/ncs:device[ncs:name=current()/../../../ncs:member]/ncs:module[ncs:name='yumaworks-system']";
      tailf:action unload {
        tailf:actionpoint ncsproxy {
          tailf:internal;
        }
        nacm:default-deny-all;
        description
          "Unload a module from the server. Remove the associated
           server instrumentation library (SIL). Remove any data
           nodes in the system from the module. Remove the module
           from the server capabilities and NETCONF monitoring
           data. Remove the module namespace from the system.

           Note: this operation does not remove the --module parameter
           from the server configuration file if it exists.

           The following conditions must be true for the unload to be
           attempted by the server:

             * The module is allowed to be unloaded. It is data-model
               and vendor specific whether a module can be
               removed at run-time.

             * There are no dependencies on the module being removed.
               No modules that import this module are also loaded.

             * The module was loaded into the server, either via the
               <load> operation or the --module configuration parameter.

             * No datastores are currently locked.  The server will
               attempt to lock all datastores on behalf of the client
               for the entire unload operation.

             * The candidate datastore does not contain any edits
               that have not been committed.

             * No confirmed-commit operation is in progress.

           If all these conditions are met then the server will
           attempt to unload the specified module.  The unload
           operation can fail for various reasons:

             * The client does not have write privileges for
               all data being deleted. This includes any
               top-level data nodes and any nested augment
               nodes in other modules.

             * The deletion of one or more nodes would cause the
               running datastore to fail any YANG validation
               tests in RFC 6020, sec. 8.3.3.

             * Server resource errors occur
          ";
        input {
          ncx:default-parm "module";
          leaf module {
            type nt:ncs_rpc_notif_NcxName;
            mandatory true;
            description
              "The name of the module to unload.";
          }
          uses ncs_rpc_notif_delete-config-parm;
        }
      }
    }
  }
  augment "/ncs:devices/ncs:device/ncs:rpc" {
    container rpc-cancel-subscription {
      tailf:ncs-device-type "netconf";
      tailf:display-when "not(../../ncs:module) or ../../ncs:module[ncs:name='yumaworks-system']";
      tailf:action cancel-subscription {
        tailf:actionpoint ncsproxy {
          tailf:internal;
        }
        description
          "Cancel a notification subscription for the session,
           if this session has an active subscription.  If not,
           just return OK.";
      }
    }
  }
  augment "/ncs:devices/ncs:device-group/ncs:ned-id/ncs:rpc" {
    container rpc-cancel-subscription {
      tailf:ncs-device-type "netconf";
      tailf:display-when "/ncs:devices/ncs:device[ncs:name=current()/../../../ncs:member]/ncs:module[ncs:name='yumaworks-system']";
      tailf:action cancel-subscription {
        tailf:actionpoint ncsproxy {
          tailf:internal;
        }
        description
          "Cancel a notification subscription for the session,
           if this session has an active subscription.  If not,
           just return OK.";
      }
    }
  }
  augment "/ncs:devices/ncs:device/ncs:rpc" {
    container rpc-restore {
      tailf:ncs-device-type "netconf";
      tailf:display-when "not(../../ncs:module) or ../../ncs:module[ncs:name='yumaworks-system']";
      tailf:action restore {
        tailf:actionpoint ncsproxy {
          tailf:internal;
        }
        nacm:default-deny-all;
        description
          "Restore a saved configuration on the device to the
           running configuration.";
        input {
          ncx:default-parm "filename";
          leaf filename {
            type ywt:ncs_rpc_notif_NcxFileName;
            mandatory true;
            description
              "File name for the restore. A simple identifier name
               is expected with no directory specifications or
               file extensions added. (e.g., 'backup1').";
          }
        }
      }
    }
  }
  augment "/ncs:devices/ncs:device-group/ncs:ned-id/ncs:rpc" {
    container rpc-restore {
      tailf:ncs-device-type "netconf";
      tailf:display-when "/ncs:devices/ncs:device[ncs:name=current()/../../../ncs:member]/ncs:module[ncs:name='yumaworks-system']";
      tailf:action restore {
        tailf:actionpoint ncsproxy {
          tailf:internal;
        }
        nacm:default-deny-all;
        description
          "Restore a saved configuration on the device to the
           running configuration.";
        input {
          ncx:default-parm "filename";
          leaf filename {
            type ywt:ncs_rpc_notif_NcxFileName;
            mandatory true;
            description
              "File name for the restore. A simple identifier name
               is expected with no directory specifications or
               file extensions added. (e.g., 'backup1').";
          }
        }
      }
    }
  }
  augment "/ncs:devices/ncs:device/ncs:rpc" {
    container rpc-delete-backup {
      tailf:ncs-device-type "netconf";
      tailf:display-when "not(../../ncs:module) or ../../ncs:module[ncs:name='yumaworks-system']";
      tailf:action delete-backup {
        tailf:actionpoint ncsproxy {
          tailf:internal;
        }
        nacm:default-deny-all;
        description
          "Delete the specified backup file on the device.";
        input {
          ncx:default-parm "filename";
          leaf filename {
            type ywt:ncs_rpc_notif_NcxFileName;
            mandatory true;
            description
              "File name to delete";
          }
        }
      }
    }
  }
  augment "/ncs:devices/ncs:device-group/ncs:ned-id/ncs:rpc" {
    container rpc-delete-backup {
      tailf:ncs-device-type "netconf";
      tailf:display-when "/ncs:devices/ncs:device[ncs:name=current()/../../../ncs:member]/ncs:module[ncs:name='yumaworks-system']";
      tailf:action delete-backup {
        tailf:actionpoint ncsproxy {
          tailf:internal;
        }
        nacm:default-deny-all;
        description
          "Delete the specified backup file on the device.";
        input {
          ncx:default-parm "filename";
          leaf filename {
            type ywt:ncs_rpc_notif_NcxFileName;
            mandatory true;
            description
              "File name to delete";
          }
        }
      }
    }
  }
  augment "/ncs:devices/ncs:device/ncs:rpc" {
    container rpc-backup {
      tailf:ncs-device-type "netconf";
      tailf:display-when "not(../../ncs:module) or ../../ncs:module[ncs:name='yumaworks-system']";
      tailf:action backup {
        tailf:actionpoint ncsproxy {
          tailf:internal;
        }
        nacm:default-deny-all;
        description
          "Backup the current running configuration to a file
           on the device.";
        input {
          ncx:default-parm "filename";
          leaf filename {
            type ywt:ncs_rpc_notif_NcxFileName;
            mandatory true;
            description
              "File name for the backup. A simple identifier name
               is expected with no directory specifications or
               file extensions added. (e.g., 'backup1').";
          }
          leaf overwrite {
            type boolean;
            default "false";
            description
              "If 'true' then allow an existing backup with the same
               'filename' value to be overwritten. If 'false' then return
               an error if the file already exists.";
          }
        }
      }
    }
  }
  augment "/ncs:devices/ncs:device-group/ncs:ned-id/ncs:rpc" {
    container rpc-backup {
      tailf:ncs-device-type "netconf";
      tailf:display-when "/ncs:devices/ncs:device[ncs:name=current()/../../../ncs:member]/ncs:module[ncs:name='yumaworks-system']";
      tailf:action backup {
        tailf:actionpoint ncsproxy {
          tailf:internal;
        }
        nacm:default-deny-all;
        description
          "Backup the current running configuration to a file
           on the device.";
        input {
          ncx:default-parm "filename";
          leaf filename {
            type ywt:ncs_rpc_notif_NcxFileName;
            mandatory true;
            description
              "File name for the backup. A simple identifier name
               is expected with no directory specifications or
               file extensions added. (e.g., 'backup1').";
          }
          leaf overwrite {
            type boolean;
            default "false";
            description
              "If 'true' then allow an existing backup with the same
               'filename' value to be overwritten. If 'false' then return
               an error if the file already exists.";
          }
        }
      }
    }
  }
  augment "/ncs:devices/ncs:device/ncs:live-status/ncm:netconf-state" {
    container backup-files {
      tailf:ncs-device-type "netconf";
      tailf:display-when "not(../../../ncs:module) or ../../../ncs:module[ncs:name='yumaworks-system'] or (../../../ncs:live-status-protocol[not(ncs:capability)]) or (../../../ncs:live-status-protocol/ncs:capability/ncs:module[.='yumaworks-system'])";
      description
        "Reports the backup files currently available
         on the server. Only present if backup commands
         in this module are supported by the server";
      list backup-file {
        key "name";
        leaf name {
          type ywt:live_ncs_NcxFileName;
          description
            "File name for the backup.";
        }
        leaf backup-time {
          type yang:date-and-time;
          description
            "Date and time the backup file was created.";
        }
      }
    }
  }
  augment "/ncs:devices/ncs:device/ncs:live-status/ncm:netconf-state/ncm:schemas/ncm:schema" {
    leaf conformance {
      tailf:ncs-device-type "netconf";
      tailf:display-when "not(../../../../../ncs:module) or ../../../../../ncs:module[ncs:name='yumaworks-system'] or (../../../../../ncs:live-status-protocol[not(ncs:capability)]) or (../../../../../ncs:live-status-protocol/ncs:capability/ncs:module[.='yumaworks-system'])";
      type boolean;
      description
        "Indicates whether the server is claiming conformance
         to the module represented by this schema or not.
         If 'true', the server implements the module
         represented by the indicated schema,
         according to the YANG module capability URI.
         If 'false', the server just imports definitions
         from the module represented by the indicated schema.";
    }
    leaf module-type {
      tailf:ncs-device-type "netconf";
      tailf:display-when "not(../../../../../ncs:module) or ../../../../../ncs:module[ncs:name='yumaworks-system'] or (../../../../../ncs:live-status-protocol[not(ncs:capability)]) or (../../../../../ncs:live-status-protocol/ncs:capability/ncs:module[.='yumaworks-system'])";
      type enumeration {
        enum "module" {
          description
            "Schema represents a YANG module";
        }
        enum "submodule" {
          description
            "Schema represents a YANG submodule";
        }
      }
      description
        "Indicates the type of module for this entry";
    }
  }
  augment "/ncs:devices/ncs:device/ncs:rpc/nc:rpc-commit/nc:commit/nc:input" {
    leaf comment {
      type string {
        length "0 .. 1024";
      }
      description
        "User provided comment to add to audit log for this
         commit operation.";
    }
  }
  augment "/ncs:devices/ncs:device/ncs:rpc/nc:rpc-get-config/nc:get-config/nc:input" {
    uses ncs_rpc_notif_with-owners-parm;
    uses rc:ncs_rpc_notif_depth-parameter;
    uses ywapp:ncs_rpc_notif_ModuleTagParm;
  }
  augment "/ncs:devices/ncs:device/ncs:rpc/nc:rpc-get/nc:get/nc:input" {
    uses ncs_rpc_notif_with-owners-parm;
    uses rc:ncs_rpc_notif_depth-parameter;
    uses ywapp:ncs_rpc_notif_ModuleTagParm;
  }
  augment "/ncs:devices/ncs:device/ncs:rpc/nc:rpc-copy-config/nc:copy-config/nc:input" {
    uses ncs_rpc_notif_with-owners-parm;
    uses rc:ncs_rpc_notif_depth-parameter;
  }
  augment "/ncs:devices/ncs:template/ncs:ned-id/ncs:config/nacm:nacm/nacm:rule-list/nacm:rule/nacm:rule-type" {
    case module-tags {
      uses ywapp:ncs_template_ModuleTagParm;
    }
  }
  augment "/ncs:devices/ncs:device/ncs:live-status/nacm:nacm/nacm:rule-list/nacm:rule/nacm:rule-type" {
    case module-tags {
      uses ywapp:live_ncs_ModuleTagParm;
    }
  }
  augment "/ncs:devices/ncs:device/ncs:config/nacm:nacm/nacm:rule-list/nacm:rule/nacm:rule-type" {
    case module-tags {
      uses ywapp:ModuleTagParm;
    }
  }
}
