module ciena-bfd-deviation {
  // Generated by yanger -t ncs
  tailf:mount-id "ciena107-nc-1.0:ciena107-nc-1.0";
  tailf:ncs-device-type "netconf";

  yang-version 1.1;
  namespace "http://ciena.com/ns/yang/ciena-bfd-deviation";
  prefix bfd-deviation;

  import ciena-bfd {
    prefix bfd;
  }
  import tailf-common {
    prefix tailf;
  }
  import tailf-ncs {
    prefix ncs;
  }

  organization
    "Ciena Corporation";
  contact
    "Web URL: http://www.ciena.com/
     E-mail:  yang@ciena.com
     Postal:  7035 Ridge Road
              Hanover, Maryland 21076
              U.S.A.
     Phone:   +1 800-921-1144
     Fax:     +1 410-694-5750";
  description
    "This YANG module defines Ciena proprietary YANG deviations
     of BFD protocol.

     Copyright (c) 2020  Ciena Corporation.  All rights
     reserved.

     All information contained herein is, and remains the
     property of Ciena Corporation. Dissemination of this
     information or reproduction of this material is strictly
     forbidden unless prior written permission is obtained
     from Ciena Corporation.";

  revision 2021-05-21 {
    description
      "MH BFD on IPv6 is not supported.";
  }
  revision 2020-10-17 {
    description
      "Initial Version of bfd deviation model.";
  }

  deviation "/ncs:devices/ncs:template/ncs:ned-id/ncs:config/bfd:bfd/bfd:global" {
    deviate add {
      // NCS drop must statement
    }
  }
  deviation "/ncs:devices/ncs:device/ncs:live-status/bfd:bfd/bfd:global" {
    deviate add {
      // NCS drop must statement
    }
  }
  deviation "/ncs:devices/ncs:device/ncs:config/bfd:bfd/bfd:global" {
    deviate add {
      must "admin-down != 'true'" {
        tailf:xpath-root 3;
        error-message "admin-down must be set to false.";
      }
    }
  }
  deviation "/ncs:devices/ncs:template/ncs:ned-id/ncs:config/bfd:bfd/bfd:session-config-entry/bfd:ip/bfd:multi-hop/bfd:vrf/bfd:ipv6" {
    deviate not-supported;
  }
  deviation "/ncs:devices/ncs:device/ncs:live-status/bfd:bfd/bfd:session-config-entry/bfd:ip/bfd:multi-hop/bfd:vrf/bfd:ipv6" {
    deviate not-supported;
  }
  deviation "/ncs:devices/ncs:device/ncs:config/bfd:bfd/bfd:session-config-entry/bfd:ip/bfd:multi-hop/bfd:vrf/bfd:ipv6" {
    deviate not-supported;
  }
  deviation "/ncs:devices/ncs:device/ncs:live-status/bfd:bfd/bfd:session-config-entry-state/bfd:ip/bfd:multi-hop/bfd:vrf/bfd:ipv6" {
    deviate not-supported;
  }
}
