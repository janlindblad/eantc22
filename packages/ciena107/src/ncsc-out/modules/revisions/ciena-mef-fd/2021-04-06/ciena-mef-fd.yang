module ciena-mef-fd {
  // Generated by yanger -t ncs
  tailf:mount-id "ciena107-nc-1.0:ciena107-nc-1.0";
  tailf:ncs-device-type "netconf";

  namespace "urn:ciena:params:xml:ns:yang:ciena-pn:ciena-mef-fd";
  prefix mef-fd;

  import ciena-mef-l2cp-profile {
    prefix mef-l2cp;
  }
  import ciena-mef-flood-containment-profile {
    prefix mef-fc;
  }
  import ciena-mef-pfg-profile {
    prefix mef-pfg;
  }
  import ciena-mef-egress-qos {
    prefix mef-egress-qos;
  }
  import ciena-mef-cos-to-frame-map {
    prefix ctf;
  }
  import ciena-mef-frame-to-cos-map {
    prefix ftc;
  }
  import tailf-common {
    prefix tailf;
  }
  import tailf-ncs {
    prefix ncs;
  }

  organization
    "Ciena Corporation";
  contact
    "Web URL: http://www.ciena.com/
     E-mail:  yang@ciena.com
     Postal:  7035 Ridge Road
              Hanover, Maryland 21076
              U.S.A.
     Phone:   +1 800-921-1144
     Fax:     +1 410-694-5750";
  description
    "This YANG module defines Ciena's configuration of
     the Forwarding Domain (Bridge Domain, Virtual Switch,
     VPLS representation for the NETCONF protocol).";

  revision 2021-04-06 {
    description
      "Added descriptions";
  }
  revision 2020-04-08 {
    description
      "1) Added tdm-vpls, tdm-vpws, evpn-vpws and evpn-fpls modes to fds container
       2) vlan mode is obsolete";
  }
  revision 2019-10-21 {
    description
      "deprecate vlan mode";
  }
  revision 2019-09-13 {
    description
      "Add fxc to fd mode";
  }
  revision 2019-05-20 {
    description
      "Remove constraint for the leaf of vlan-id";
  }
  revision 2016-01-25 {
    description
      "Initial version";
  }

  typedef ncs_template_vlan-id {
    type string;
    description
      "Represents a IEEE 802.1Q VLAN-ID.";
  }

  typedef ncs_rpc_notif_vlan-id {
    type uint16 {
      range "1..4094";
    }
    description
      "Represents a IEEE 802.1Q VLAN-ID.";
  }

  typedef live_ncs_vlan-id {
    type uint16 {
      range "1..4094";
    }
    description
      "Represents a IEEE 802.1Q VLAN-ID.";
  }

  typedef vlan-id {
    type uint16 {
      range "1..4094";
    }
    description
      "Represents a IEEE 802.1Q VLAN-ID.";
  }

  grouping ncs_template_l2-transform {
    choice frame-type {
      case stack {
        list vlan-stack {
          // NCS patched for predictable order
          ordered-by user;
          key "tag";
          description
            "For an L2-frame that is initiated/injected via this forwarding domain, this specifies the VLAN related l2-transform to be applied to the frame.";
          leaf tag {
            type string;
            description
              "Dependent on the transform operation, the tag numbers are
               push => '1' represents push outermost, '2' represents push outermost (always push to outer)";
          }
          choice action {
            case push {
              leaf push-tpid {
                type string;
                // NCS drop default statement
                description
                  "Represents the TPID value of the vlan tag for the tag being pushed";
              }
              leaf push-pcp {
                type string;
                description
                  "Represents the PCP value of the vlan tag for the tag being pushed.
                   When the PCP value is mapped using a cos-to-frame-map, 'map' is specified.";
              }
              leaf push-dei {
                type string;
                description
                  "Represents the DEI value of the vlan tag for the tag being pushed.";
              }
              leaf push-vid {
                type ncs_template_vlan-id;
                // NCS drop mandatory statement
                description
                  "Represents the VID value of the vlan tag for the tag being pushed";
              }
            }
          }
        }
      }
    }
  }

  grouping ncs_rpc_notif_l2-transform {
    choice frame-type {
      case stack {
        list vlan-stack {
          key "tag";
          description
            "For an L2-frame that is initiated/injected via this forwarding domain, this specifies the VLAN related l2-transform to be applied to the frame.";
          leaf tag {
            type uint8;
            description
              "Dependent on the transform operation, the tag numbers are
               push => '1' represents push outermost, '2' represents push outermost (always push to outer)";
          }
          choice action {
            case push {
              leaf push-tpid {
                type enumeration {
                  enum "tpid-8100" {
                    value 33024;
                  }
                  enum "tpid-88a8" {
                    value 34984;
                  }
                  enum "tpid-9100" {
                    value 37120;
                  }
                }
                default "tpid-8100";
                description
                  "Represents the TPID value of the vlan tag for the tag being pushed";
              }
              leaf push-pcp {
                type enumeration {
                  enum "pcp-0" {
                    value 0;
                  }
                  enum "pcp-1" {
                    value 1;
                  }
                  enum "pcp-2" {
                    value 2;
                  }
                  enum "pcp-3" {
                    value 3;
                  }
                  enum "pcp-4" {
                    value 4;
                  }
                  enum "pcp-5" {
                    value 5;
                  }
                  enum "pcp-6" {
                    value 6;
                  }
                  enum "pcp-7" {
                    value 7;
                  }
                  enum "map";
                }
                description
                  "Represents the PCP value of the vlan tag for the tag being pushed.
                   When the PCP value is mapped using a cos-to-frame-map, 'map' is specified.";
              }
              leaf push-dei {
                type enumeration {
                  enum "enabled";
                  enum "disabled";
                }
                description
                  "Represents the DEI value of the vlan tag for the tag being pushed.";
              }
              leaf push-vid {
                type ncs_rpc_notif_vlan-id;
                mandatory true;
                description
                  "Represents the VID value of the vlan tag for the tag being pushed";
              }
            }
          }
        }
      }
    }
  }

  grouping live_ncs_l2-transform {
    choice frame-type {
      case stack {
        list vlan-stack {
          key "tag";
          description
            "For an L2-frame that is initiated/injected via this forwarding domain, this specifies the VLAN related l2-transform to be applied to the frame.";
          leaf tag {
            type uint8;
            description
              "Dependent on the transform operation, the tag numbers are
               push => '1' represents push outermost, '2' represents push outermost (always push to outer)";
          }
          choice action {
            case push {
              leaf push-tpid {
                type enumeration {
                  enum "tpid-8100" {
                    value 33024;
                  }
                  enum "tpid-88a8" {
                    value 34984;
                  }
                  enum "tpid-9100" {
                    value 37120;
                  }
                }
                // NCS drop default statement
                description
                  "Represents the TPID value of the vlan tag for the tag being pushed";
              }
              leaf push-pcp {
                type enumeration {
                  enum "pcp-0" {
                    value 0;
                  }
                  enum "pcp-1" {
                    value 1;
                  }
                  enum "pcp-2" {
                    value 2;
                  }
                  enum "pcp-3" {
                    value 3;
                  }
                  enum "pcp-4" {
                    value 4;
                  }
                  enum "pcp-5" {
                    value 5;
                  }
                  enum "pcp-6" {
                    value 6;
                  }
                  enum "pcp-7" {
                    value 7;
                  }
                  enum "map";
                }
                description
                  "Represents the PCP value of the vlan tag for the tag being pushed.
                   When the PCP value is mapped using a cos-to-frame-map, 'map' is specified.";
              }
              leaf push-dei {
                type enumeration {
                  enum "enabled";
                  enum "disabled";
                }
                description
                  "Represents the DEI value of the vlan tag for the tag being pushed.";
              }
              leaf push-vid {
                type live_ncs_vlan-id;
                // NCS drop mandatory statement
                description
                  "Represents the VID value of the vlan tag for the tag being pushed";
              }
            }
          }
        }
      }
    }
  }

  grouping l2-transform {
    choice frame-type {
      case stack {
        list vlan-stack {
          key "tag";
          description
            "For an L2-frame that is initiated/injected via this forwarding domain, this specifies the VLAN related l2-transform to be applied to the frame.";
          leaf tag {
            type uint8;
            description
              "Dependent on the transform operation, the tag numbers are
               push => '1' represents push outermost, '2' represents push outermost (always push to outer)";
          }
          choice action {
            case push {
              leaf push-tpid {
                type enumeration {
                  enum "tpid-8100" {
                    value 33024;
                  }
                  enum "tpid-88a8" {
                    value 34984;
                  }
                  enum "tpid-9100" {
                    value 37120;
                  }
                }
                default "tpid-8100";
                description
                  "Represents the TPID value of the vlan tag for the tag being pushed";
              }
              leaf push-pcp {
                type enumeration {
                  enum "pcp-0" {
                    value 0;
                  }
                  enum "pcp-1" {
                    value 1;
                  }
                  enum "pcp-2" {
                    value 2;
                  }
                  enum "pcp-3" {
                    value 3;
                  }
                  enum "pcp-4" {
                    value 4;
                  }
                  enum "pcp-5" {
                    value 5;
                  }
                  enum "pcp-6" {
                    value 6;
                  }
                  enum "pcp-7" {
                    value 7;
                  }
                  enum "map";
                }
                description
                  "Represents the PCP value of the vlan tag for the tag being pushed.
                   When the PCP value is mapped using a cos-to-frame-map, 'map' is specified.";
              }
              leaf push-dei {
                type enumeration {
                  enum "enabled";
                  enum "disabled";
                }
                description
                  "Represents the DEI value of the vlan tag for the tag being pushed.";
              }
              leaf push-vid {
                type vlan-id;
                mandatory true;
                description
                  "Represents the VID value of the vlan tag for the tag being pushed";
              }
            }
          }
        }
      }
    }
  }

  augment "/ncs:devices/ncs:device/ncs:config" {
    container fds {
      tailf:ncs-device-type "netconf";
      tailf:display-when "not(../../ncs:module) or ../../ncs:module[ncs:name='ciena-mef-fd']";
      description
        "List of forwarding-domains. Forwarding domains are layer 2 forwarding domains
         to which various entities attach (flow-points, MPLS-PWs etc).";
      list fd {
        key "name";
        description
          "The list of configured forwarding domains on the device.";
        leaf name {
          type string;
          description
            "An administratively assigned string, which may be used
             to identify the forwarding domain.";
        }
        leaf description {
          type string;
          description
            "This is string used to describe the Forwarding Domain.";
        }
        leaf mode {
          type enumeration {
            enum "vlan" {
              status obsolete;
            }
            enum "vpls" {
              description
                "Forwarding mode is based on l2 mac-lookups involving 2 or more endpoints";
            }
            enum "vpws" {
              description
                "Forwarding mode is based on exactly 2 endpoints";
            }
            enum "fxc" {
              description
                "Forwarding mode is based on flexible cross-connects for evpn-fxc within an evpn-instance";
            }
            enum "tdm-vpls" {
              description
                "Forwarding mode is based on l2 mac-lookups involving 2 or more endpoints where some of the endpoints are over TDM ports";
            }
            enum "tdm-vpws" {
              description
                "Forwarding mode is based on exactly 2 endpoints where some of the endpoints are over TDM ports";
            }
            enum "evpn-vpws" {
              description
                "Forwarding mode is based on exactly 2 endpoints within an evpn-instance";
            }
            enum "evpn-vpls" {
              description
                "Forwarding mode is based on l2 mac-lookups involving 2 or more endpoints within an evpn-instance";
            }
          }
          description
            "Forwarding mode of the forwarding-domain";
        }
        leaf vlan-id {
          type uint16 {
            range "1..4094";
          }
          description
            "The id of VLAN associated with forwarding-domain.";
        }
        leaf mac-learning {
          type enumeration {
            enum "enabled";
            enum "disabled";
          }
          description
            "Enable/disable MAC learning for this forwarding-domain.";
        }
        leaf l2cp-profile {
          type mef-l2cp:l2cp-profile-ref;
          description
            "Reference to a Layer 2 Control Protocol Tunneling Profile.";
        }
        leaf flood-containment-profile {
          type mef-fc:flood-containment-profile-ref;
          description
            "Reference to a Flood Containment Profile definition.";
        }
        leaf pfg-profile {
          type mef-pfg:pfg-profile-ref;
          description
            "Reference to a Private Forwarding Group Profile.";
        }
        leaf cos-queue-map {
          type mef-egress-qos:cos-queue-map-ref;
          description
            "Reference to queue-map for hierarchical shaping/scheduling.";
        }
        leaf queue-group-indirection {
          type mef-egress-qos:queue-group-indirection-ref;
          description
            "Reference to queue-group-indirection for hierarchical shaping/scheduling.";
        }
        container initiate-l2-transform {
          uses l2-transform;
          description
            "For an L2-frame that is initiated/injected via this forwarding domain, this specifies the l2-transform
             to be applied to the frame. e.g. an L3-frame injected via this forwarding domain to L2 datapath.";
        }
        leaf initiate-cos-to-frame-map {
          type ctf:cos-to-frame-ref;
          description
            "For an L2-frame that is initiated/injected via this forwarding domain, this specifies the cos-to-frame map to
             use for a cos-to-frame map policy of 'mapped' from the initiate-l2-transform config.";
        }
        choice initiate-frame-to-cos {
          case map {
            leaf initiate-frame-to-cos-map-policy {
              type enumeration {
                enum "outer-tag";
                enum "inner-tag";
                enum "mpls-tc";
                enum "dscp";
              }
              description
                "For an L2-frame that is initiated/injected via this forwarding domain, this specifies the frame-to-cos-map sub-policy to
                 use when when the policy is mapped.";
            }
            leaf initiate-frame-to-cos-map {
              type ftc:frame-to-cos-ref;
              description
                "For an L2-frame that is initiated/injected via this forwarding domain, this specifies the frame-to-cos map to
                 use for an initiate frame-to-cos map policy of 'mapped'.";
            }
          }
          case fixed {
            leaf cos {
              type uint8 {
                range "0..63";
              }
              description
                "For an L2-frame that is initiated/injected via this forwarding domain, this specifies the fixed cos value to
                 use when when the policy is fixed.";
            }
            leaf color {
              type enumeration {
                enum "green";
                enum "yellow";
                enum "red";
              }
              description
                "For an L2-frame that is initiated/injected via this forwarding domain, this specifies the fixed color value to
                 use when when the policy is fixed.";
            }
          }
        }
      }
    }
  }
  augment "/ncs:devices/ncs:device/ncs:live-status" {
    container fds {
      tailf:ncs-device-type "netconf";
      tailf:display-when "not(../../ncs:module) or ../../ncs:module[ncs:name='ciena-mef-fd'] or (../../ncs:live-status-protocol[not(ncs:capability)]) or (../../ncs:live-status-protocol/ncs:capability/ncs:module[.='ciena-mef-fd'])";
      description
        "List of forwarding-domains. Forwarding domains are layer 2 forwarding domains
         to which various entities attach (flow-points, MPLS-PWs etc).";
      list fd {
        key "name";
        description
          "The list of configured forwarding domains on the device.";
        leaf name {
          type string;
          description
            "An administratively assigned string, which may be used
             to identify the forwarding domain.";
        }
        leaf description {
          type string;
          description
            "This is string used to describe the Forwarding Domain.";
        }
        leaf mode {
          type enumeration {
            enum "vlan" {
              status obsolete;
            }
            enum "vpls" {
              description
                "Forwarding mode is based on l2 mac-lookups involving 2 or more endpoints";
            }
            enum "vpws" {
              description
                "Forwarding mode is based on exactly 2 endpoints";
            }
            enum "fxc" {
              description
                "Forwarding mode is based on flexible cross-connects for evpn-fxc within an evpn-instance";
            }
            enum "tdm-vpls" {
              description
                "Forwarding mode is based on l2 mac-lookups involving 2 or more endpoints where some of the endpoints are over TDM ports";
            }
            enum "tdm-vpws" {
              description
                "Forwarding mode is based on exactly 2 endpoints where some of the endpoints are over TDM ports";
            }
            enum "evpn-vpws" {
              description
                "Forwarding mode is based on exactly 2 endpoints within an evpn-instance";
            }
            enum "evpn-vpls" {
              description
                "Forwarding mode is based on l2 mac-lookups involving 2 or more endpoints within an evpn-instance";
            }
          }
          description
            "Forwarding mode of the forwarding-domain";
        }
        leaf vlan-id {
          type uint16 {
            range "1..4094";
          }
          description
            "The id of VLAN associated with forwarding-domain.";
        }
        leaf mac-learning {
          type enumeration {
            enum "enabled";
            enum "disabled";
          }
          description
            "Enable/disable MAC learning for this forwarding-domain.";
        }
        leaf l2cp-profile {
          type mef-l2cp:live_ncs_l2cp-profile-ref;
          description
            "Reference to a Layer 2 Control Protocol Tunneling Profile.";
        }
        leaf flood-containment-profile {
          type mef-fc:live_ncs_flood-containment-profile-ref;
          description
            "Reference to a Flood Containment Profile definition.";
        }
        leaf pfg-profile {
          type mef-pfg:live_ncs_pfg-profile-ref;
          description
            "Reference to a Private Forwarding Group Profile.";
        }
        leaf cos-queue-map {
          type mef-egress-qos:live_ncs_cos-queue-map-ref;
          description
            "Reference to queue-map for hierarchical shaping/scheduling.";
        }
        leaf queue-group-indirection {
          type mef-egress-qos:live_ncs_queue-group-indirection-ref;
          description
            "Reference to queue-group-indirection for hierarchical shaping/scheduling.";
        }
        container initiate-l2-transform {
          uses live_ncs_l2-transform;
          description
            "For an L2-frame that is initiated/injected via this forwarding domain, this specifies the l2-transform
             to be applied to the frame. e.g. an L3-frame injected via this forwarding domain to L2 datapath.";
        }
        leaf initiate-cos-to-frame-map {
          type ctf:live_ncs_cos-to-frame-ref;
          description
            "For an L2-frame that is initiated/injected via this forwarding domain, this specifies the cos-to-frame map to
             use for a cos-to-frame map policy of 'mapped' from the initiate-l2-transform config.";
        }
        choice initiate-frame-to-cos {
          case map {
            leaf initiate-frame-to-cos-map-policy {
              type enumeration {
                enum "outer-tag";
                enum "inner-tag";
                enum "mpls-tc";
                enum "dscp";
              }
              description
                "For an L2-frame that is initiated/injected via this forwarding domain, this specifies the frame-to-cos-map sub-policy to
                 use when when the policy is mapped.";
            }
            leaf initiate-frame-to-cos-map {
              type ftc:live_ncs_frame-to-cos-ref;
              description
                "For an L2-frame that is initiated/injected via this forwarding domain, this specifies the frame-to-cos map to
                 use for an initiate frame-to-cos map policy of 'mapped'.";
            }
          }
          case fixed {
            leaf cos {
              type uint8 {
                range "0..63";
              }
              description
                "For an L2-frame that is initiated/injected via this forwarding domain, this specifies the fixed cos value to
                 use when when the policy is fixed.";
            }
            leaf color {
              type enumeration {
                enum "green";
                enum "yellow";
                enum "red";
              }
              description
                "For an L2-frame that is initiated/injected via this forwarding domain, this specifies the fixed color value to
                 use when when the policy is fixed.";
            }
          }
        }
      }
    }
  }
  augment "/ncs:devices/ncs:template/ncs:ned-id/ncs:config" {
    container fds {
      description
        "List of forwarding-domains. Forwarding domains are layer 2 forwarding domains
         to which various entities attach (flow-points, MPLS-PWs etc).";
      list fd {
        // NCS patched for predictable order
        ordered-by user;
        key "name";
        description
          "The list of configured forwarding domains on the device.";
        leaf name {
          type string;
          description
            "An administratively assigned string, which may be used
             to identify the forwarding domain.";
        }
        leaf description {
          type string;
          description
            "This is string used to describe the Forwarding Domain.";
        }
        leaf mode {
          type string;
          description
            "Forwarding mode of the forwarding-domain";
        }
        leaf vlan-id {
          type string;
          description
            "The id of VLAN associated with forwarding-domain.";
        }
        leaf mac-learning {
          type string;
          description
            "Enable/disable MAC learning for this forwarding-domain.";
        }
        leaf l2cp-profile {
          type mef-l2cp:ncs_template_l2cp-profile-ref;
          description
            "Reference to a Layer 2 Control Protocol Tunneling Profile.";
        }
        leaf flood-containment-profile {
          type mef-fc:ncs_template_flood-containment-profile-ref;
          description
            "Reference to a Flood Containment Profile definition.";
        }
        leaf pfg-profile {
          type mef-pfg:ncs_template_pfg-profile-ref;
          description
            "Reference to a Private Forwarding Group Profile.";
        }
        leaf cos-queue-map {
          type mef-egress-qos:ncs_template_cos-queue-map-ref;
          description
            "Reference to queue-map for hierarchical shaping/scheduling.";
        }
        leaf queue-group-indirection {
          type mef-egress-qos:ncs_template_queue-group-indirection-ref;
          description
            "Reference to queue-group-indirection for hierarchical shaping/scheduling.";
        }
        container initiate-l2-transform {
          uses ncs_template_l2-transform;
          description
            "For an L2-frame that is initiated/injected via this forwarding domain, this specifies the l2-transform
             to be applied to the frame. e.g. an L3-frame injected via this forwarding domain to L2 datapath.";
        }
        leaf initiate-cos-to-frame-map {
          type ctf:ncs_template_cos-to-frame-ref;
          description
            "For an L2-frame that is initiated/injected via this forwarding domain, this specifies the cos-to-frame map to
             use for a cos-to-frame map policy of 'mapped' from the initiate-l2-transform config.";
        }
        choice initiate-frame-to-cos {
          case map {
            leaf initiate-frame-to-cos-map-policy {
              type string;
              description
                "For an L2-frame that is initiated/injected via this forwarding domain, this specifies the frame-to-cos-map sub-policy to
                 use when when the policy is mapped.";
            }
            leaf initiate-frame-to-cos-map {
              type ftc:ncs_template_frame-to-cos-ref;
              description
                "For an L2-frame that is initiated/injected via this forwarding domain, this specifies the frame-to-cos map to
                 use for an initiate frame-to-cos map policy of 'mapped'.";
            }
          }
          case fixed {
            leaf cos {
              type string;
              description
                "For an L2-frame that is initiated/injected via this forwarding domain, this specifies the fixed cos value to
                 use when when the policy is fixed.";
            }
            leaf color {
              type string;
              description
                "For an L2-frame that is initiated/injected via this forwarding domain, this specifies the fixed color value to
                 use when when the policy is fixed.";
            }
          }
        }
      }
    }
  }
}
