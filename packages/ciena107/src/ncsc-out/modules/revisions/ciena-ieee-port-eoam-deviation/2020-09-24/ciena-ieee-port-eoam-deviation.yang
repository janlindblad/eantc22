module ciena-ieee-port-eoam-deviation {
  // Generated by yanger -t ncs
  tailf:mount-id "ciena107-nc-1.0:ciena107-nc-1.0";
  tailf:ncs-device-type "netconf";

  namespace "urn:ciena:params:xml:ns:yang:ciena-pn:ieee-port-eoam-dev";
  prefix ciena-ieee-port-eoam-dev;

  import ciena-ieee-port-eoam {
    prefix eoam;
  }
  import openconfig-interfaces {
    prefix oc-if;
  }
  import tailf-common {
    prefix tailf;
  }
  import tailf-ncs {
    prefix ncs;
  }

  revision 2020-09-24 {
    description
      "EFP loopback process settings are supported now. So, removing deviation.";
  }
  revision 2018-01-24 {
    description
      "Updated to reflect move from ietf-interfaces to openconfig-interfaces.";
  }
  revision 2017-12-27 {
    description
      "Modified as per ciena-ieee-port-eoam.yang file changes.";
  }
  revision 2015-04-02 {
    description
      "Initial revision.";
  }

  deviation "/ncs:devices/ncs:template/ncs:ned-id/ncs:config/oc-if:interfaces/oc-if:interface/oc-if:config/eoam:eoam-port-config/eoam:pdu-timer" {
    deviate replace {
      type string;
    }
    deviate add {
      // NCS drop default statement
    }
  }
  deviation "/ncs:devices/ncs:device/ncs:live-status/oc-if:interfaces/oc-if:interface/oc-if:config/eoam:eoam-port-config/eoam:pdu-timer" {
    deviate replace {
      type uint16 {
        range "100..1000";
      }
    }
    deviate add {
      // NCS drop default statement
    }
  }
  deviation "/ncs:devices/ncs:device/ncs:config/oc-if:interfaces/oc-if:interface/oc-if:config/eoam:eoam-port-config/eoam:pdu-timer" {
    deviate replace {
      type uint16 {
        range "100..1000";
      }
    }
    deviate add {
      default "1000";
    }
  }
  deviation "/ncs:devices/ncs:template/ncs:ned-id/ncs:config/oc-if:interfaces/oc-if:interface/oc-if:config/eoam:eoam-port-config/eoam:link-lost-timer" {
    deviate replace {
      type string;
    }
    deviate add {
      // NCS drop default statement
    }
  }
  deviation "/ncs:devices/ncs:device/ncs:live-status/oc-if:interfaces/oc-if:interface/oc-if:config/eoam:eoam-port-config/eoam:link-lost-timer" {
    deviate replace {
      type uint16 {
        range "500..5000";
      }
    }
    deviate add {
      // NCS drop default statement
    }
  }
  deviation "/ncs:devices/ncs:device/ncs:config/oc-if:interfaces/oc-if:interface/oc-if:config/eoam:eoam-port-config/eoam:link-lost-timer" {
    deviate replace {
      type uint16 {
        range "500..5000";
      }
    }
    deviate add {
      default "5000";
    }
  }
  deviation "/ncs:devices/ncs:template/ncs:ned-id/ncs:config/oc-if:interfaces/oc-if:interface/oc-if:config/eoam:eoam-port-event-config/eoam:error-frame-window" {
    deviate replace {
      type string;
    }
  }
  deviation "/ncs:devices/ncs:device/ncs:live-status/oc-if:interfaces/oc-if:interface/oc-if:config/eoam:eoam-port-event-config/eoam:error-frame-window" {
    deviate replace {
      type uint32 {
        range "10..600";
      }
    }
  }
  deviation "/ncs:devices/ncs:device/ncs:config/oc-if:interfaces/oc-if:interface/oc-if:config/eoam:eoam-port-event-config/eoam:error-frame-window" {
    deviate replace {
      type uint32 {
        range "10..600";
      }
    }
  }
  deviation "/ncs:devices/ncs:template/ncs:ned-id/ncs:config/oc-if:interfaces/oc-if:interface/oc-if:config/eoam:eoam-port-event-config/eoam:error-frame-period-threshold" {
    deviate replace {
      type string;
    }
  }
  deviation "/ncs:devices/ncs:device/ncs:live-status/oc-if:interfaces/oc-if:interface/oc-if:config/eoam:eoam-port-event-config/eoam:error-frame-period-threshold" {
    deviate replace {
      type uint32 {
        range "0..4294967293";
      }
    }
  }
  deviation "/ncs:devices/ncs:device/ncs:config/oc-if:interfaces/oc-if:interface/oc-if:config/eoam:eoam-port-event-config/eoam:error-frame-period-threshold" {
    deviate replace {
      type uint32 {
        range "0..4294967293";
      }
    }
  }
  deviation "/ncs:devices/ncs:template/ncs:ned-id/ncs:config/oc-if:interfaces/oc-if:interface/oc-if:config/eoam:eoam-port-event-config/eoam:error-frame-threshold" {
    deviate replace {
      type string;
    }
  }
  deviation "/ncs:devices/ncs:device/ncs:live-status/oc-if:interfaces/oc-if:interface/oc-if:config/eoam:eoam-port-event-config/eoam:error-frame-threshold" {
    deviate replace {
      type uint32 {
        range "0..4294967293";
      }
    }
  }
  deviation "/ncs:devices/ncs:device/ncs:config/oc-if:interfaces/oc-if:interface/oc-if:config/eoam:eoam-port-event-config/eoam:error-frame-threshold" {
    deviate replace {
      type uint32 {
        range "0..4294967293";
      }
    }
  }
  deviation "/ncs:devices/ncs:template/ncs:ned-id/ncs:config/oc-if:interfaces/oc-if:interface/oc-if:config/eoam:eoam-port-event-config/eoam:error-frame-seconds-summary-threshold" {
    deviate replace {
      type string;
    }
  }
  deviation "/ncs:devices/ncs:device/ncs:live-status/oc-if:interfaces/oc-if:interface/oc-if:config/eoam:eoam-port-event-config/eoam:error-frame-seconds-summary-threshold" {
    deviate replace {
      type uint32 {
        range "0..65535";
      }
    }
  }
  deviation "/ncs:devices/ncs:device/ncs:config/oc-if:interfaces/oc-if:interface/oc-if:config/eoam:eoam-port-event-config/eoam:error-frame-seconds-summary-threshold" {
    deviate replace {
      type uint32 {
        range "0..65535";
      }
    }
  }
}
