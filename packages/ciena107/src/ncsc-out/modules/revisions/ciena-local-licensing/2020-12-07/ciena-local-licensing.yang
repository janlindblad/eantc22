module ciena-local-licensing {
  // Generated by yanger -t ncs
  tailf:mount-id "ciena107-nc-1.0:ciena107-nc-1.0";
  tailf:ncs-device-type "netconf";

  namespace "urn:ciena:params:xml:ns:yang:ciena:ciena-local-licensing";
  prefix local-license;

  import ietf-inet-types {
    prefix inet;
  }
  import tailf-common {
    prefix tailf;
  }
  import tailf-ncs {
    prefix ncs;
  }

  organization
    "Ciena Corporation";
  contact
    "Web URL: http://www.ciena.com/
     Postal:  7035 Ridge Road
              Hanover, Maryland 21076
              U.S.A.
     Phone:   +1 800-921-1144
     Fax:     +1 410-694-5750";
  description
    "This YANG module defines Ciena's local licensing interfaces. ";

  revision 2020-12-07 {
    description
      "1. In this revision, the built-in-trial-license-activate and
       startup-license-activate RPCs has been added";
    reference "No specific reference; standard not available.";
  }
  revision 2017-05-05 {
    description
      "1.0";
    reference "No specific reference; standard not available.";
  }

  typedef ncs_template_string-max-256 {
    type string;
  }

  typedef ncs_rpc_notif_string-max-256 {
    type string {
      length "1..256";
    }
  }

  typedef live_ncs_string-max-256 {
    type string {
      length "1..256";
    }
  }

  typedef string-max-256 {
    type string {
      length "1..256";
    }
  }

  augment "/ncs:devices/ncs:device/ncs:rpc" {
    container rpc-startup-license-activate {
      tailf:ncs-device-type "netconf";
      tailf:display-when "not(../../ncs:module) or ../../ncs:module[ncs:name='ciena-local-licensing']";
      tailf:action startup-license-activate {
        tailf:actionpoint ncsproxy {
          tailf:internal;
        }
        description
          "Applies the startup license that is included with the box.";
        output {
          leaf response {
            type ncs_rpc_notif_string-max-256;
            description
              "The response to the startup-license-activate action could be
               'success', or the reason for startup license activation
               failure";
          }
        }
      }
    }
  }
  augment "/ncs:devices/ncs:device-group/ncs:ned-id/ncs:rpc" {
    container rpc-startup-license-activate {
      tailf:ncs-device-type "netconf";
      tailf:display-when "/ncs:devices/ncs:device[ncs:name=current()/../../../ncs:member]/ncs:module[ncs:name='ciena-local-licensing']";
      tailf:action startup-license-activate {
        tailf:actionpoint ncsproxy {
          tailf:internal;
        }
        description
          "Applies the startup license that is included with the box.";
        output {
          container "device" {
            leaf "name" {
              type string;
            }
            leaf "info" {
              type string;
            }
            container "result" {
              leaf response {
                type ncs_rpc_notif_string-max-256;
                description
                  "The response to the startup-license-activate action could be
                   'success', or the reason for startup license activation
                   failure";
              }
            }
          }
        }
      }
    }
  }
  augment "/ncs:devices/ncs:device/ncs:rpc" {
    container rpc-built-in-trial-license-activate {
      tailf:ncs-device-type "netconf";
      tailf:display-when "not(../../ncs:module) or ../../ncs:module[ncs:name='ciena-local-licensing']";
      tailf:action built-in-trial-license-activate {
        tailf:actionpoint ncsproxy {
          tailf:internal;
        }
        description
          "Applies the trial license that is included with the box.";
        output {
          leaf response {
            type ncs_rpc_notif_string-max-256;
            description
              "The response to the built-in-trial-license-activate action could be
               'success', or the reason for trial license activation
               failure";
          }
        }
      }
    }
  }
  augment "/ncs:devices/ncs:device-group/ncs:ned-id/ncs:rpc" {
    container rpc-built-in-trial-license-activate {
      tailf:ncs-device-type "netconf";
      tailf:display-when "/ncs:devices/ncs:device[ncs:name=current()/../../../ncs:member]/ncs:module[ncs:name='ciena-local-licensing']";
      tailf:action built-in-trial-license-activate {
        tailf:actionpoint ncsproxy {
          tailf:internal;
        }
        description
          "Applies the trial license that is included with the box.";
        output {
          container "device" {
            leaf "name" {
              type string;
            }
            leaf "info" {
              type string;
            }
            container "result" {
              leaf response {
                type ncs_rpc_notif_string-max-256;
                description
                  "The response to the built-in-trial-license-activate action could be
                   'success', or the reason for trial license activation
                   failure";
              }
            }
          }
        }
      }
    }
  }
  augment "/ncs:devices/ncs:device/ncs:rpc" {
    container rpc-licensekey-activate {
      tailf:ncs-device-type "netconf";
      tailf:display-when "not(../../ncs:module) or ../../ncs:module[ncs:name='ciena-local-licensing']";
      tailf:action licensekey-activate {
        tailf:actionpoint ncsproxy {
          tailf:internal;
        }
        description
          "The licensekey-activate rpc would apply the license-key
           on the device. The filename of the license-key is supplied
           as input in this rpc.";
        input {
          leaf filename {
            type ncs_rpc_notif_string-max-256;
            description
              "This is the name of the licensekey file that is to be
               activated.";
          }
        }
        output {
          leaf response {
            type ncs_rpc_notif_string-max-256;
            description
              "The response to the licensekey-activate action could be
               'success', or the reason for license key activation
               failure";
          }
        }
      }
    }
  }
  augment "/ncs:devices/ncs:device-group/ncs:ned-id/ncs:rpc" {
    container rpc-licensekey-activate {
      tailf:ncs-device-type "netconf";
      tailf:display-when "/ncs:devices/ncs:device[ncs:name=current()/../../../ncs:member]/ncs:module[ncs:name='ciena-local-licensing']";
      tailf:action licensekey-activate {
        tailf:actionpoint ncsproxy {
          tailf:internal;
        }
        description
          "The licensekey-activate rpc would apply the license-key
           on the device. The filename of the license-key is supplied
           as input in this rpc.";
        input {
          leaf filename {
            type ncs_rpc_notif_string-max-256;
            description
              "This is the name of the licensekey file that is to be
               activated.";
          }
        }
        output {
          container "device" {
            leaf "name" {
              type string;
            }
            leaf "info" {
              type string;
            }
            container "result" {
              leaf response {
                type ncs_rpc_notif_string-max-256;
                description
                  "The response to the licensekey-activate action could be
                   'success', or the reason for license key activation
                   failure";
              }
            }
          }
        }
      }
    }
  }
  augment "/ncs:devices/ncs:device/ncs:rpc" {
    container rpc-regid-generate {
      tailf:ncs-device-type "netconf";
      tailf:display-when "not(../../ncs:module) or ../../ncs:module[ncs:name='ciena-local-licensing']";
      tailf:action regid-generate {
        tailf:actionpoint ncsproxy {
          tailf:internal;
        }
        description
          "The regid-generate rpc would trigger the generation of the
           device registration identification file. The path to the file
           is returned as output filepath.";
        output {
          leaf filepath {
            type inet:uri;
            description
              "This is the path of the generated regid file. The regid
               file can be upload from the device from this path.";
          }
          leaf response {
            type ncs_rpc_notif_string-max-256;
            description
              "The response to the regid-generate action could be
               'success', or the reason for regid generation failure";
          }
        }
      }
    }
  }
  augment "/ncs:devices/ncs:device-group/ncs:ned-id/ncs:rpc" {
    container rpc-regid-generate {
      tailf:ncs-device-type "netconf";
      tailf:display-when "/ncs:devices/ncs:device[ncs:name=current()/../../../ncs:member]/ncs:module[ncs:name='ciena-local-licensing']";
      tailf:action regid-generate {
        tailf:actionpoint ncsproxy {
          tailf:internal;
        }
        description
          "The regid-generate rpc would trigger the generation of the
           device registration identification file. The path to the file
           is returned as output filepath.";
        output {
          container "device" {
            leaf "name" {
              type string;
            }
            leaf "info" {
              type string;
            }
            container "result" {
              leaf filepath {
                type inet:uri;
                description
                  "This is the path of the generated regid file. The regid
                   file can be upload from the device from this path.";
              }
              leaf response {
                type ncs_rpc_notif_string-max-256;
                description
                  "The response to the regid-generate action could be
                   'success', or the reason for regid generation failure";
              }
            }
          }
        }
      }
    }
  }
}
