module ciena-underlay-binding {
  // Generated by yanger -t ncs
  tailf:mount-id "ciena107-nc-1.0:ciena107-nc-1.0";
  tailf:ncs-device-type "netconf";

  namespace "http://ciena.com/ns/yang/ciena-underlay-binding";
  prefix cn-ub;

  import openconfig-interfaces {
    prefix oc-if;
  }
  import ciena-mef-fd {
    prefix mef-fd;
  }
  import ciena-openconfig-interfaces {
    prefix cn-if;
  }
  import yuma-ncx {
    prefix ncx;
  }
  import tailf-common {
    prefix tailf;
  }
  import tailf-ncs {
    prefix ncs;
  }

  organization
    "Ciena Corporation";
  contact
    "Web URL: http://www.ciena.com/
     E-mail:  yang@ciena.com
     Postal:  7035 Ridge Road
              Hanover, Maryland 21076

              U.S.A.
     Phone:   +1 800-921-1144
     Fax:     +1 410-694-5750";
  description
    "This module contains the Ciena proprietary YANG augmentation
     of the underlay binding YANG module.

     Copyright (c) 2016 Ciena Corporation.  All rights reserved.

     All information contained herein is, and remains
     the property of Ciena Corporation. Dissemination of this
     information or reproduction of this material is strictly
     forbidden unless prior written permission is obtained from
     Ciena Corporation.";

  revision 2021-08-03 {
    description
      "Add evpn vpls as a valid interface fd mode type.";
  }
  revision 2021-03-16 {
    description
      "Added IP point-to-point feature.
       Added support for point-to-point interface.";
  }
  revision 2020-02-17 {
    description
      "Added IP unnumbered feature.
       Added support to restrict FD mode to vpls.";
  }
  revision 2018-02-28 {
    description
      "Initial version";
    reference "";
  }

  grouping ncs_template_underlay-binding-config {
    description
      "Configuration data for underlay binding";
    choice type {
      case fd {
        leaf fd {
          ncx:user-write "create delete";
          type string;
          // NCS drop must statement
        }
      }
    }
  }

  grouping ncs_rpc_notif_underlay-binding-config {
    description
      "Configuration data for underlay binding";
    choice type {
      case fd {
        leaf fd {
          ncx:user-write "create delete";
          type string;
          must "/mef-fd:fds/mef-fd:fd[mef-fd:name=current()]/mef-fd:mode = 'vpls' or /mef-fd:fds/mef-fd:fd[mef-fd:name=current()]/mef-fd:mode = 'evpn-vpls'" {
            tailf:xpath-root 3;
            error-message "Referenced mode is not supported.";
          }
        }
      }
    }
  }

  grouping live_ncs_underlay-binding-config {
    description
      "Configuration data for underlay binding";
    choice type {
      case fd {
        leaf fd {
          ncx:user-write "create delete";
          type leafref {
            path "/ncs:devices/ncs:device/ncs:live-status/mef-fd:fds/mef-fd:fd/mef-fd:name" {
              tailf:xpath-root 3;
            }
          }
          // NCS drop must statement
        }
      }
    }
  }

  grouping underlay-binding-config {
    description
      "Configuration data for underlay binding";
    choice type {
      case fd {
        leaf fd {
          ncx:user-write "create delete";
          type leafref {
            path "/ncs:devices/ncs:device/ncs:config/mef-fd:fds/mef-fd:fd/mef-fd:name" {
              tailf:xpath-root 3;
            }
          }
          must "/mef-fd:fds/mef-fd:fd[mef-fd:name=current()]/mef-fd:mode = 'vpls' or /mef-fd:fds/mef-fd:fd[mef-fd:name=current()]/mef-fd:mode = 'evpn-vpls'" {
            tailf:xpath-root 3;
            error-message "Referenced mode is not supported.";
          }
        }
      }
    }
  }

  augment "/ncs:devices/ncs:template/ncs:ned-id/ncs:config/oc-if:interfaces/oc-if:interface/oc-if:config" {
    // NCS drop when statement
    container underlay-binding {
      description
        "Top-level container for underlay binding interfaces. This
         provides the ability to map to the lower layer objects (like fd) ";
      container config {
        description
          "Configuration data for underlay binding interfaces";
        uses ncs_template_underlay-binding-config;
      }
    }
  }
  augment "/ncs:devices/ncs:device/ncs:live-status/oc-if:interfaces/oc-if:interface/oc-if:config" {
    // NCS drop when statement
    container underlay-binding {
      tailf:ncs-device-type "netconf";
      tailf:display-when "not(../../../../../ncs:module) or ../../../../../ncs:module[ncs:name='ciena-underlay-binding'] or (../../../../../ncs:live-status-protocol[not(ncs:capability)]) or (../../../../../ncs:live-status-protocol/ncs:capability/ncs:module[.='ciena-underlay-binding'])";
      description
        "Top-level container for underlay binding interfaces. This
         provides the ability to map to the lower layer objects (like fd) ";
      container config {
        description
          "Configuration data for underlay binding interfaces";
        uses live_ncs_underlay-binding-config;
      }
    }
  }
  augment "/ncs:devices/ncs:device/ncs:config/oc-if:interfaces/oc-if:interface/oc-if:config" {
    when "cn-if:type[.='ip' or .='ip-unnumbered' or .='point-to-point']" {
      tailf:xpath-root 3;
    }
    container underlay-binding {
      tailf:ncs-device-type "netconf";
      tailf:display-when "not(../../../../../ncs:module) or ../../../../../ncs:module[ncs:name='ciena-underlay-binding']";
      description
        "Top-level container for underlay binding interfaces. This
         provides the ability to map to the lower layer objects (like fd) ";
      container config {
        description
          "Configuration data for underlay binding interfaces";
        uses underlay-binding-config;
      }
    }
  }
}
