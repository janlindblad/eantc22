module ciena-types {
  // Generated by yanger -t ncs
  tailf:mount-id "ciena107-nc-1.0:ciena107-nc-1.0";
  tailf:ncs-device-type "netconf";

  namespace "http://www.ciena.com/ns/yang/ciena-types";
  prefix ciena-types;

  import ietf-inet-types {
    prefix inet;
  }
  import tailf-common {
    prefix tailf;
  }
  import tailf-ncs {
    prefix ncs;
  }

  organization
    "Ciena Corporation";
  contact
    "Web URL: http://www.ciena.com/
     E-mail:  yang@ciena.com
     Postal:  7035 Ridge Road
              Hanover, Maryland 21076
              U.S.A.
     Phone:   +1 800-921-1144
     Fax:     +1 410-694-5750";
  description
    "This YANG module defines Ciena standard types and groupings.

     Copyright (c) 2019 Ciena Corporation.  All rights
     reserved.

     All information contained herein is, and remains
     the property of Ciena Corporation. Dissemination of this
     information or reproduction of this material is strictly
     forbidden unless prior written permission is obtained from
     Ciena Corporation.";

  revision 2021-07-19 {
    description
      "Added filler-mismatch-alarm of the type state";
    reference "";
  }
  revision 2019-11-22 {
    description
      "Adding a date type, taken from the latest openconfig-yang-types.";
  }
  revision 2019-02-09 {
    description
      "Adding up/down enumeration for the state";
  }
  revision 2017-09-12 {
    description
      "Shortened lines and reordered elements of the
       current-secret leaves to be in canonical order to
       comply with yang RFC standards.";
    reference "RFC 6020, Ciena Functional Specification.";
  }
  revision 2017-04-25 {
    description
      "Added preferred source address support.
       Added duration, simple-date, simple-time types.";
    reference "Ciena Functional Specification.";
  }
  revision 2016-05-11 {
    description
      "Initial version";
    reference
      "RFC 6020: YANG - A Data Modeling Language for
       the Network Configuration Protocol (NETCONF).
       No specific reference; standard not available.";
  }

  typedef ncs_template_state {
    type string;
    description
      "The state of the node.";
  }

  typedef ncs_template_status {
    type string;
    description
      "The execution result of operation.";
  }

  typedef ncs_template_admin-state {
    type ncs_template_state;
    description
      "The admin state of the node.";
  }

  typedef ncs_template_filler-mismatch-alarm {
    type ncs_template_state;
    description
      "The filler mismatch alarm state of the node.";
  }

  typedef ncs_template_oper-state {
    type ncs_template_state;
    description
      "The oper state of the node.";
  }

  typedef ncs_template_on-off-state {
    type string;
    description
      "The on / off state.";
  }

  typedef ncs_template_up-down-state {
    type string;
    description
      "The up/down state.";
  }

  typedef ncs_template_event-severity {
    type string;
    description
      "The system event severity.";
  }

  typedef ncs_template_slot-index {
    type string;
    description
      "Chassis slot indexing";
  }

  typedef ncs_template_preferred-source-address {
    type string;
    description
      "The preferred source address.";
  }

  typedef ncs_template_date {
    type string;
    description
      "A full UTC date, expressed in the format described in RFC3339.
       That is to say:
       YYYY-MM-DD
       where YYYY is the year, MM is the month expressed as a two-digit
       month (zero padding if required), DD is the day of the month,
       expressed as a two digit value.";
    reference "RFC3339 - Date and Time on the Internet: full-date";
  }

  typedef ncs_rpc_notif_state {
    type enumeration {
      enum "disabled" {
        description
          "The node is disabled.";
      }
      enum "enabled" {
        description
          "The node is enabled.";
      }
    }
    description
      "The state of the node.";
  }

  typedef ncs_rpc_notif_status {
    type enumeration {
      enum "success" {
        description
          "The execution status is success.";
      }
      enum "failure" {
        description
          "The execution status is failure.";
      }
    }
    description
      "The execution result of operation.";
  }

  typedef ncs_rpc_notif_admin-state {
    type ncs_rpc_notif_state;
    description
      "The admin state of the node.";
  }

  typedef ncs_rpc_notif_filler-mismatch-alarm {
    type ncs_rpc_notif_state;
    description
      "The filler mismatch alarm state of the node.";
  }

  typedef ncs_rpc_notif_oper-state {
    type ncs_rpc_notif_state;
    description
      "The oper state of the node.";
  }

  typedef ncs_rpc_notif_on-off-state {
    type enumeration {
      enum "off" {
        description
          "The off state.";
      }
      enum "on" {
        description
          "The on state.";
      }
    }
    description
      "The on / off state.";
  }

  typedef ncs_rpc_notif_up-down-state {
    type enumeration {
      enum "up" {
        description
          "State is up.";
      }
      enum "down" {
        description
          "State is down.";
      }
    }
    description
      "The up/down state.";
  }

  typedef ncs_rpc_notif_event-severity {
    type enumeration {
      enum "critical" {
        description
          "The critical severity.";
      }
      enum "major" {
        description
          "The major severity.";
      }
      enum "minor" {
        description
          "The minor severity.";
      }
      enum "warning" {
        description
          "The warning severity.";
      }
      enum "config" {
        description
          "The config severity.";
      }
      enum "info" {
        description
          "The info severity.";
      }
      enum "debug" {
        description
          "The debug severity.";
      }
    }
    description
      "The system event severity.";
  }

  typedef ncs_rpc_notif_slot-index {
    type enumeration {
      enum "non-existent" {
        value -1;
        description
          "Non-existent slot.";
      }
      enum "zero" {
        value 0;
        description
          "Reserved slot number.";
      }
      enum "lm1" {
        value 1;
        description
          "Slot LM1.";
      }
      enum "lm2" {
        value 2;
        description
          "Slot LM2.";
      }
      enum "lm3" {
        value 3;
        description
          "Slot LM3.";
      }
      enum "lm4" {
        value 4;
        description
          "Slot LM4.";
      }
      enum "lm5" {
        value 5;
        description
          "Slot LM5.";
      }
      enum "lm6" {
        value 6;
        description
          "Slot LM6.";
      }
      enum "lm7" {
        value 7;
        description
          "Slot LM7.";
      }
      enum "lm8" {
        value 8;
        description
          "Slot LM8.";
      }
      enum "lm9" {
        value 9;
        description
          "Slot LM9.";
      }
      enum "lm10" {
        value 10;
        description
          "Slot LM10.";
      }
      enum "lm11" {
        value 11;
        description
          "Slot LM11.";
      }
      enum "lm12" {
        value 12;
        description
          "Slot LM12.";
      }
      enum "lm13" {
        value 13;
        description
          "Slot LM13.";
      }
      enum "lm14" {
        value 14;
        description
          "Slot LM14.";
      }
      enum "lm15" {
        value 15;
        description
          "Slot LM15.";
      }
      enum "lm16" {
        value 16;
        description
          "Slot LM16.";
      }
      enum "lm17" {
        value 17;
        description
          "Slot LM17.";
      }
      enum "lm18" {
        value 18;
        description
          "Slot LM18.";
      }
      enum "lm19" {
        value 19;
        description
          "Slot LM19.";
      }
      enum "lm20" {
        value 20;
        description
          "Slot LM20.";
      }
      enum "lm21" {
        value 21;
        description
          "Slot LM21.";
      }
      enum "lm22" {
        value 22;
        description
          "Slot LM22.";
      }
      enum "lm23" {
        value 23;
        description
          "Slot LM23.";
      }
      enum "lm24" {
        value 24;
        description
          "Slot LM24.";
      }
      enum "lm25" {
        value 25;
        description
          "Slot LM25.";
      }
      enum "lm26" {
        value 26;
        description
          "Slot LM26.";
      }
      enum "lm27" {
        value 27;
        description
          "Slot LM27.";
      }
      enum "lm28" {
        value 28;
        description
          "Slot LM28.";
      }
      enum "lm29" {
        value 29;
        description
          "Slot LM29.";
      }
      enum "lm30" {
        value 30;
        description
          "Slot LM30.";
      }
      enum "ctm1" {
        value 31;
        description
          "Slot CTM1 (CTX1).";
      }
      enum "ctm2" {
        value 32;
        description
          "Slot CTM2 (CTX2).";
      }
      enum "ctx1" {
        value 33;
        description
          "Slot CTX1. Non-existent alias sometimes used for ctm1.";
      }
      enum "ctx2" {
        value 34;
        description
          "Slot CTX2. Non-existent alias sometimes used for ctm1.";
      }
      enum "sm1" {
        value 35;
        description
          "Slot SM1. May be an alias for CTX1.sm depending on the platform.";
      }
      enum "sm2" {
        value 36;
        description
          "Slot SM2. May be an alias for CTX2.sm depending on the platform.";
      }
      enum "sm3" {
        value 37;
        description
          "Slot SM3. May be an alias for SM depending on the platform.";
      }
      enum "sm4" {
        value 38;
        description
          "Slot SM4.";
      }
      enum "sm5" {
        value 39;
        description
          "Slot SM5.";
      }
      enum "pdu1" {
        value 40;
        description
          "Slot PDU1.  May be PDU-A1 or PDU-A depending of the platform.";
      }
      enum "pdu2" {
        value 41;
        description
          "Slot PDU2.  May be PDU-B1 or PDU-B depending of the platform.";
      }
      enum "pdu3" {
        value 42;
        description
          "Slot PDU3.";
      }
      enum "pdu4" {
        value 43;
        description
          "Slot PDU3.";
      }
      enum "pdu5" {
        value 44;
        description
          "Slot PDU3.";
      }
      enum "pdu6" {
        value 45;
        description
          "Slot PDU3.";
      }
      enum "pdu7" {
        value 46;
        description
          "Slot PDU3.";
      }
      enum "pdu8" {
        value 47;
        description
          "Slot PDU3.";
      }
      enum "cfu1" {
        value 48;
        description
          "Slot CFU1.";
      }
      enum "cfu2" {
        value 49;
        description
          "Slot CFU2.";
      }
      enum "io" {
        value 50;
        description
          "Slot IO.";
      }
      enum "chassis" {
        value 58;
        description
          "Chassis.";
      }
    }
    description
      "Chassis slot indexing";
  }

  typedef ncs_rpc_notif_preferred-source-address {
    type enumeration {
      enum "default" {
        description
          "The default address for the device.";
      }
      enum "loopback" {
        description
          "The loopback address configured on the device.";
      }
    }
    description
      "The preferred source address.";
  }

  typedef ncs_rpc_notif_date {
    type string {
      pattern '\d{4}\-\d{2}\-\d{2}';
    }
    description
      "A full UTC date, expressed in the format described in RFC3339.
       That is to say:
       YYYY-MM-DD
       where YYYY is the year, MM is the month expressed as a two-digit
       month (zero padding if required), DD is the day of the month,
       expressed as a two digit value.";
    reference "RFC3339 - Date and Time on the Internet: full-date";
  }

  typedef live_ncs_state {
    type enumeration {
      enum "disabled" {
        description
          "The node is disabled.";
      }
      enum "enabled" {
        description
          "The node is enabled.";
      }
    }
    description
      "The state of the node.";
  }

  typedef live_ncs_status {
    type enumeration {
      enum "success" {
        description
          "The execution status is success.";
      }
      enum "failure" {
        description
          "The execution status is failure.";
      }
    }
    description
      "The execution result of operation.";
  }

  typedef live_ncs_admin-state {
    type live_ncs_state;
    description
      "The admin state of the node.";
  }

  typedef live_ncs_filler-mismatch-alarm {
    type live_ncs_state;
    description
      "The filler mismatch alarm state of the node.";
  }

  typedef live_ncs_oper-state {
    type live_ncs_state;
    description
      "The oper state of the node.";
  }

  typedef live_ncs_on-off-state {
    type enumeration {
      enum "off" {
        description
          "The off state.";
      }
      enum "on" {
        description
          "The on state.";
      }
    }
    description
      "The on / off state.";
  }

  typedef live_ncs_up-down-state {
    type enumeration {
      enum "up" {
        description
          "State is up.";
      }
      enum "down" {
        description
          "State is down.";
      }
    }
    description
      "The up/down state.";
  }

  typedef live_ncs_event-severity {
    type enumeration {
      enum "critical" {
        description
          "The critical severity.";
      }
      enum "major" {
        description
          "The major severity.";
      }
      enum "minor" {
        description
          "The minor severity.";
      }
      enum "warning" {
        description
          "The warning severity.";
      }
      enum "config" {
        description
          "The config severity.";
      }
      enum "info" {
        description
          "The info severity.";
      }
      enum "debug" {
        description
          "The debug severity.";
      }
    }
    description
      "The system event severity.";
  }

  typedef live_ncs_slot-index {
    type enumeration {
      enum "non-existent" {
        value -1;
        description
          "Non-existent slot.";
      }
      enum "zero" {
        value 0;
        description
          "Reserved slot number.";
      }
      enum "lm1" {
        value 1;
        description
          "Slot LM1.";
      }
      enum "lm2" {
        value 2;
        description
          "Slot LM2.";
      }
      enum "lm3" {
        value 3;
        description
          "Slot LM3.";
      }
      enum "lm4" {
        value 4;
        description
          "Slot LM4.";
      }
      enum "lm5" {
        value 5;
        description
          "Slot LM5.";
      }
      enum "lm6" {
        value 6;
        description
          "Slot LM6.";
      }
      enum "lm7" {
        value 7;
        description
          "Slot LM7.";
      }
      enum "lm8" {
        value 8;
        description
          "Slot LM8.";
      }
      enum "lm9" {
        value 9;
        description
          "Slot LM9.";
      }
      enum "lm10" {
        value 10;
        description
          "Slot LM10.";
      }
      enum "lm11" {
        value 11;
        description
          "Slot LM11.";
      }
      enum "lm12" {
        value 12;
        description
          "Slot LM12.";
      }
      enum "lm13" {
        value 13;
        description
          "Slot LM13.";
      }
      enum "lm14" {
        value 14;
        description
          "Slot LM14.";
      }
      enum "lm15" {
        value 15;
        description
          "Slot LM15.";
      }
      enum "lm16" {
        value 16;
        description
          "Slot LM16.";
      }
      enum "lm17" {
        value 17;
        description
          "Slot LM17.";
      }
      enum "lm18" {
        value 18;
        description
          "Slot LM18.";
      }
      enum "lm19" {
        value 19;
        description
          "Slot LM19.";
      }
      enum "lm20" {
        value 20;
        description
          "Slot LM20.";
      }
      enum "lm21" {
        value 21;
        description
          "Slot LM21.";
      }
      enum "lm22" {
        value 22;
        description
          "Slot LM22.";
      }
      enum "lm23" {
        value 23;
        description
          "Slot LM23.";
      }
      enum "lm24" {
        value 24;
        description
          "Slot LM24.";
      }
      enum "lm25" {
        value 25;
        description
          "Slot LM25.";
      }
      enum "lm26" {
        value 26;
        description
          "Slot LM26.";
      }
      enum "lm27" {
        value 27;
        description
          "Slot LM27.";
      }
      enum "lm28" {
        value 28;
        description
          "Slot LM28.";
      }
      enum "lm29" {
        value 29;
        description
          "Slot LM29.";
      }
      enum "lm30" {
        value 30;
        description
          "Slot LM30.";
      }
      enum "ctm1" {
        value 31;
        description
          "Slot CTM1 (CTX1).";
      }
      enum "ctm2" {
        value 32;
        description
          "Slot CTM2 (CTX2).";
      }
      enum "ctx1" {
        value 33;
        description
          "Slot CTX1. Non-existent alias sometimes used for ctm1.";
      }
      enum "ctx2" {
        value 34;
        description
          "Slot CTX2. Non-existent alias sometimes used for ctm1.";
      }
      enum "sm1" {
        value 35;
        description
          "Slot SM1. May be an alias for CTX1.sm depending on the platform.";
      }
      enum "sm2" {
        value 36;
        description
          "Slot SM2. May be an alias for CTX2.sm depending on the platform.";
      }
      enum "sm3" {
        value 37;
        description
          "Slot SM3. May be an alias for SM depending on the platform.";
      }
      enum "sm4" {
        value 38;
        description
          "Slot SM4.";
      }
      enum "sm5" {
        value 39;
        description
          "Slot SM5.";
      }
      enum "pdu1" {
        value 40;
        description
          "Slot PDU1.  May be PDU-A1 or PDU-A depending of the platform.";
      }
      enum "pdu2" {
        value 41;
        description
          "Slot PDU2.  May be PDU-B1 or PDU-B depending of the platform.";
      }
      enum "pdu3" {
        value 42;
        description
          "Slot PDU3.";
      }
      enum "pdu4" {
        value 43;
        description
          "Slot PDU3.";
      }
      enum "pdu5" {
        value 44;
        description
          "Slot PDU3.";
      }
      enum "pdu6" {
        value 45;
        description
          "Slot PDU3.";
      }
      enum "pdu7" {
        value 46;
        description
          "Slot PDU3.";
      }
      enum "pdu8" {
        value 47;
        description
          "Slot PDU3.";
      }
      enum "cfu1" {
        value 48;
        description
          "Slot CFU1.";
      }
      enum "cfu2" {
        value 49;
        description
          "Slot CFU2.";
      }
      enum "io" {
        value 50;
        description
          "Slot IO.";
      }
      enum "chassis" {
        value 58;
        description
          "Chassis.";
      }
    }
    description
      "Chassis slot indexing";
  }

  typedef live_ncs_preferred-source-address {
    type enumeration {
      enum "default" {
        description
          "The default address for the device.";
      }
      enum "loopback" {
        description
          "The loopback address configured on the device.";
      }
    }
    description
      "The preferred source address.";
  }

  typedef live_ncs_date {
    type string {
      pattern '\d{4}\-\d{2}\-\d{2}';
    }
    description
      "A full UTC date, expressed in the format described in RFC3339.
       That is to say:
       YYYY-MM-DD
       where YYYY is the year, MM is the month expressed as a two-digit
       month (zero padding if required), DD is the day of the month,
       expressed as a two digit value.";
    reference "RFC3339 - Date and Time on the Internet: full-date";
  }

  typedef state {
    type enumeration {
      enum "disabled" {
        description
          "The node is disabled.";
      }
      enum "enabled" {
        description
          "The node is enabled.";
      }
    }
    description
      "The state of the node.";
  }

  typedef status {
    type enumeration {
      enum "success" {
        description
          "The execution status is success.";
      }
      enum "failure" {
        description
          "The execution status is failure.";
      }
    }
    description
      "The execution result of operation.";
  }

  typedef admin-state {
    type state;
    description
      "The admin state of the node.";
  }

  typedef filler-mismatch-alarm {
    type state;
    description
      "The filler mismatch alarm state of the node.";
  }

  typedef oper-state {
    type state;
    description
      "The oper state of the node.";
  }

  typedef on-off-state {
    type enumeration {
      enum "off" {
        description
          "The off state.";
      }
      enum "on" {
        description
          "The on state.";
      }
    }
    description
      "The on / off state.";
  }

  typedef up-down-state {
    type enumeration {
      enum "up" {
        description
          "State is up.";
      }
      enum "down" {
        description
          "State is down.";
      }
    }
    description
      "The up/down state.";
  }

  typedef event-severity {
    type enumeration {
      enum "critical" {
        description
          "The critical severity.";
      }
      enum "major" {
        description
          "The major severity.";
      }
      enum "minor" {
        description
          "The minor severity.";
      }
      enum "warning" {
        description
          "The warning severity.";
      }
      enum "config" {
        description
          "The config severity.";
      }
      enum "info" {
        description
          "The info severity.";
      }
      enum "debug" {
        description
          "The debug severity.";
      }
    }
    description
      "The system event severity.";
  }

  typedef slot-index {
    type enumeration {
      enum "non-existent" {
        value -1;
        description
          "Non-existent slot.";
      }
      enum "zero" {
        value 0;
        description
          "Reserved slot number.";
      }
      enum "lm1" {
        value 1;
        description
          "Slot LM1.";
      }
      enum "lm2" {
        value 2;
        description
          "Slot LM2.";
      }
      enum "lm3" {
        value 3;
        description
          "Slot LM3.";
      }
      enum "lm4" {
        value 4;
        description
          "Slot LM4.";
      }
      enum "lm5" {
        value 5;
        description
          "Slot LM5.";
      }
      enum "lm6" {
        value 6;
        description
          "Slot LM6.";
      }
      enum "lm7" {
        value 7;
        description
          "Slot LM7.";
      }
      enum "lm8" {
        value 8;
        description
          "Slot LM8.";
      }
      enum "lm9" {
        value 9;
        description
          "Slot LM9.";
      }
      enum "lm10" {
        value 10;
        description
          "Slot LM10.";
      }
      enum "lm11" {
        value 11;
        description
          "Slot LM11.";
      }
      enum "lm12" {
        value 12;
        description
          "Slot LM12.";
      }
      enum "lm13" {
        value 13;
        description
          "Slot LM13.";
      }
      enum "lm14" {
        value 14;
        description
          "Slot LM14.";
      }
      enum "lm15" {
        value 15;
        description
          "Slot LM15.";
      }
      enum "lm16" {
        value 16;
        description
          "Slot LM16.";
      }
      enum "lm17" {
        value 17;
        description
          "Slot LM17.";
      }
      enum "lm18" {
        value 18;
        description
          "Slot LM18.";
      }
      enum "lm19" {
        value 19;
        description
          "Slot LM19.";
      }
      enum "lm20" {
        value 20;
        description
          "Slot LM20.";
      }
      enum "lm21" {
        value 21;
        description
          "Slot LM21.";
      }
      enum "lm22" {
        value 22;
        description
          "Slot LM22.";
      }
      enum "lm23" {
        value 23;
        description
          "Slot LM23.";
      }
      enum "lm24" {
        value 24;
        description
          "Slot LM24.";
      }
      enum "lm25" {
        value 25;
        description
          "Slot LM25.";
      }
      enum "lm26" {
        value 26;
        description
          "Slot LM26.";
      }
      enum "lm27" {
        value 27;
        description
          "Slot LM27.";
      }
      enum "lm28" {
        value 28;
        description
          "Slot LM28.";
      }
      enum "lm29" {
        value 29;
        description
          "Slot LM29.";
      }
      enum "lm30" {
        value 30;
        description
          "Slot LM30.";
      }
      enum "ctm1" {
        value 31;
        description
          "Slot CTM1 (CTX1).";
      }
      enum "ctm2" {
        value 32;
        description
          "Slot CTM2 (CTX2).";
      }
      enum "ctx1" {
        value 33;
        description
          "Slot CTX1. Non-existent alias sometimes used for ctm1.";
      }
      enum "ctx2" {
        value 34;
        description
          "Slot CTX2. Non-existent alias sometimes used for ctm1.";
      }
      enum "sm1" {
        value 35;
        description
          "Slot SM1. May be an alias for CTX1.sm depending on the platform.";
      }
      enum "sm2" {
        value 36;
        description
          "Slot SM2. May be an alias for CTX2.sm depending on the platform.";
      }
      enum "sm3" {
        value 37;
        description
          "Slot SM3. May be an alias for SM depending on the platform.";
      }
      enum "sm4" {
        value 38;
        description
          "Slot SM4.";
      }
      enum "sm5" {
        value 39;
        description
          "Slot SM5.";
      }
      enum "pdu1" {
        value 40;
        description
          "Slot PDU1.  May be PDU-A1 or PDU-A depending of the platform.";
      }
      enum "pdu2" {
        value 41;
        description
          "Slot PDU2.  May be PDU-B1 or PDU-B depending of the platform.";
      }
      enum "pdu3" {
        value 42;
        description
          "Slot PDU3.";
      }
      enum "pdu4" {
        value 43;
        description
          "Slot PDU3.";
      }
      enum "pdu5" {
        value 44;
        description
          "Slot PDU3.";
      }
      enum "pdu6" {
        value 45;
        description
          "Slot PDU3.";
      }
      enum "pdu7" {
        value 46;
        description
          "Slot PDU3.";
      }
      enum "pdu8" {
        value 47;
        description
          "Slot PDU3.";
      }
      enum "cfu1" {
        value 48;
        description
          "Slot CFU1.";
      }
      enum "cfu2" {
        value 49;
        description
          "Slot CFU2.";
      }
      enum "io" {
        value 50;
        description
          "Slot IO.";
      }
      enum "chassis" {
        value 58;
        description
          "Chassis.";
      }
    }
    description
      "Chassis slot indexing";
  }

  typedef preferred-source-address {
    type enumeration {
      enum "default" {
        description
          "The default address for the device.";
      }
      enum "loopback" {
        description
          "The loopback address configured on the device.";
      }
    }
    description
      "The preferred source address.";
  }

  typedef date {
    type string {
      pattern '\d{4}\-\d{2}\-\d{2}';
    }
    description
      "A full UTC date, expressed in the format described in RFC3339.
       That is to say:
       YYYY-MM-DD
       where YYYY is the year, MM is the month expressed as a two-digit
       month (zero padding if required), DD is the day of the month,
       expressed as a two digit value.";
    reference "RFC3339 - Date and Time on the Internet: full-date";
  }

  grouping ncs_template_security-password {
    description
      "Reusable grouping for security passwords and secrets.";
    choice security {
      description
        "Leafs for password or secret input.  These leafs will
         update the current-secret and may not return any data.";
      leaf password {
        type string;
        description
          "The string used for the clear text password.  No data will
           be returned from this leaf. This leaf will update the contents
           of the current-secret leaf.";
      }
      leaf secret {
        type string;
        description
          "The string used for the cipher text which may
           be encrypted or hashed. This leaf will update
           the contents of the current-secret leaf.";
      }
    }
    // NCS drop config false leaf 'current-secret'
  }

  grouping ncs_template_security-key {
    description
      "Reusable grouping for security keys and secrets.";
    choice security {
      description
        "Leafs for key or secret input.  These leafs will
         update the current-secret and may not return any data.";
      leaf key {
        type string;
        description
          "The string used for the clear text key.  No data will
           be returned from this leaf.
           This leaf will update the contents of the current-secret leaf.";
      }
      leaf secret {
        type string;
        description
          "The string used for the cipher text which may
           be encrypted or hashed. This leaf will update
           the contents of the current-secret leaf.";
      }
    }
    // NCS drop config false leaf 'current-secret'
  }

  grouping ncs_template_resolved-address {
    description
      ".";
    leaf hostname {
      type string;
      description
        "Hostname of the device.";
    }
    leaf address {
      type string;
      description
        "Resolved IP address of the device.";
    }
  }

  grouping ncs_rpc_notif_security-password {
    description
      "Reusable grouping for security passwords and secrets.";
    choice security {
      description
        "Leafs for password or secret input.  These leafs will
         update the current-secret and may not return any data.";
      leaf password {
        type string;
        description
          "The string used for the clear text password.  No data will
           be returned from this leaf. This leaf will update the contents
           of the current-secret leaf.";
      }
      leaf secret {
        type string;
        description
          "The string used for the cipher text which may
           be encrypted or hashed. This leaf will update
           the contents of the current-secret leaf.";
      }
    }
    leaf current-secret {
      type string;
      config false;
      description
        "The current string used for the cipher
         text which may be encrypted or hashed.";
    }
  }

  grouping ncs_rpc_notif_security-key {
    description
      "Reusable grouping for security keys and secrets.";
    choice security {
      description
        "Leafs for key or secret input.  These leafs will
         update the current-secret and may not return any data.";
      leaf key {
        type string;
        description
          "The string used for the clear text key.  No data will
           be returned from this leaf.
           This leaf will update the contents of the current-secret leaf.";
      }
      leaf secret {
        type string;
        description
          "The string used for the cipher text which may
           be encrypted or hashed. This leaf will update
           the contents of the current-secret leaf.";
      }
    }
    leaf current-secret {
      type string;
      config false;
      description
        "The current string used for the cipher text
         which may be encrypted or hashed.";
    }
  }

  grouping ncs_rpc_notif_resolved-address {
    description
      ".";
    leaf hostname {
      type inet:host;
      description
        "Hostname of the device.";
    }
    leaf address {
      type inet:ip-address;
      description
        "Resolved IP address of the device.";
    }
  }

  grouping live_ncs_security-password {
    description
      "Reusable grouping for security passwords and secrets.";
    choice security {
      description
        "Leafs for password or secret input.  These leafs will
         update the current-secret and may not return any data.";
      leaf password {
        type string;
        description
          "The string used for the clear text password.  No data will
           be returned from this leaf. This leaf will update the contents
           of the current-secret leaf.";
      }
      leaf secret {
        type string;
        description
          "The string used for the cipher text which may
           be encrypted or hashed. This leaf will update
           the contents of the current-secret leaf.";
      }
    }
    leaf current-secret {
      type string;
      description
        "The current string used for the cipher
         text which may be encrypted or hashed.";
    }
  }

  grouping live_ncs_security-key {
    description
      "Reusable grouping for security keys and secrets.";
    choice security {
      description
        "Leafs for key or secret input.  These leafs will
         update the current-secret and may not return any data.";
      leaf key {
        type string;
        description
          "The string used for the clear text key.  No data will
           be returned from this leaf.
           This leaf will update the contents of the current-secret leaf.";
      }
      leaf secret {
        type string;
        description
          "The string used for the cipher text which may
           be encrypted or hashed. This leaf will update
           the contents of the current-secret leaf.";
      }
    }
    leaf current-secret {
      type string;
      description
        "The current string used for the cipher text
         which may be encrypted or hashed.";
    }
  }

  grouping live_ncs_resolved-address {
    description
      ".";
    leaf hostname {
      type inet:host;
      description
        "Hostname of the device.";
    }
    leaf address {
      type inet:ip-address;
      description
        "Resolved IP address of the device.";
    }
  }

  grouping security-password {
    description
      "Reusable grouping for security passwords and secrets.";
    choice security {
      description
        "Leafs for password or secret input.  These leafs will
         update the current-secret and may not return any data.";
      leaf password {
        type string;
        description
          "The string used for the clear text password.  No data will
           be returned from this leaf. This leaf will update the contents
           of the current-secret leaf.";
      }
      leaf secret {
        type string;
        description
          "The string used for the cipher text which may
           be encrypted or hashed. This leaf will update
           the contents of the current-secret leaf.";
      }
    }
    // NCS drop config false leaf 'current-secret'
  }

  grouping security-key {
    description
      "Reusable grouping for security keys and secrets.";
    choice security {
      description
        "Leafs for key or secret input.  These leafs will
         update the current-secret and may not return any data.";
      leaf key {
        type string;
        description
          "The string used for the clear text key.  No data will
           be returned from this leaf.
           This leaf will update the contents of the current-secret leaf.";
      }
      leaf secret {
        type string;
        description
          "The string used for the cipher text which may
           be encrypted or hashed. This leaf will update
           the contents of the current-secret leaf.";
      }
    }
    // NCS drop config false leaf 'current-secret'
  }

  grouping resolved-address {
    description
      ".";
    leaf hostname {
      type inet:host;
      description
        "Hostname of the device.";
    }
    leaf address {
      type inet:ip-address;
      description
        "Resolved IP address of the device.";
    }
  }

  feature benchmark-non-fpga-generator {
    description
      "This feature string is returned by the netconf
       server if the benchmark non-FPGA generator feature is supported.";
  }

  feature benchmark-non-fpga-reflector {
    description
      "This feature string is returned by the netconf
       server if the benchmark non-FPGA reflector feature is supported.";
  }

  feature benchmark-generator {
    description
      "This feature string is returned by the netconf
       server if the benchmark generator feature is supported.";
  }

  feature benchmark-reflector {
    description
      "This feature string is returned by the netconf
       server if the benchmark reflector feature is supported.";
  }

  feature benchmark {
    description
      "This feature string is returned by the netconf
       server if the benchmark feature is supported.";
  }

  feature ptp-timing {
    description
      "This feature string is returned by the netconf
       server if ptp timing is supported.";
  }

  feature gps-timing {
    description
      "This feature string is returned by the netconf
       server if gps timing is supported.";
  }

  feature bits-timing {
    description
      "This feature string is returned by the netconf
       server if bits timing is supported.";
  }

  feature network-sync {
    description
      "This feature string is returned by the netconf
       server if network sync is supported.";
  }

  feature raps {
    description
      "This feature string is returned by the netconf
       server if ring protection is supported.";
  }

  feature max-queue-groups {
    description
      "This feature string is returned by the netconf
       server if max queue groups are supported.";
  }

  feature max-vc-l2xforms {
    description
      "This feature string is returned by the netconf
       server if max VC L2 transforms are supported.";
  }

  feature mpls {
    description
      "This feature string is returned by the netconf
       server if MPLS is supported.";
  }

  feature pbt {
    description
      "This feature string is returned by the netconf
       server if PBT is supported.";
  }

  feature vpls-fpga {
    description
      "This feature string is returned by the netconf
       server if the VPLS FPGA is supported.";
  }

  feature pwe-module {
    description
      "This feature string is returned by the netconf
       server if the PWE module is supported.";
  }

  feature protocol-filters {
    description
      "This feature string is returned by the netconf
       server if protocol filters are supported.";
  }

  feature pm {
    description
      "This feature string is returned by the netconf
       server if PM is supported.";
  }

  feature saos-8x {
    description
      "This feature string is returned by the
       netconf server if running on a 8.x device.";
  }

  feature saos-6x {
    description
      "This feature string is returned by the
       netconf server if running on a 6.x device.";
  }
}
