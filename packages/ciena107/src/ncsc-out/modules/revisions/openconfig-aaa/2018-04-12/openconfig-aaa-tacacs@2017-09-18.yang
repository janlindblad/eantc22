submodule openconfig-aaa-tacacs {
  // Generated by yanger -t ncs
  tailf:mount-id "ciena107-nc-1.0:ciena107-nc-1.0";

  yang-version 1;
  belongs-to openconfig-aaa {
    prefix oc-aaa;
  }

  import openconfig-inet-types {
    prefix oc-inet;
  }
  import openconfig-extensions {
    prefix oc-ext;
  }
  import openconfig-aaa-types {
    prefix oc-aaa-types;
  }
  import openconfig-types {
    prefix oc-types;
  }
  import tailf-common {
    prefix tailf;
  }
  import tailf-ncs {
    prefix ncs;
  }

  organization
    "OpenConfig working group";
  contact
    "OpenConfig working group
     www.openconfig.net";
  description
    "This module defines configuration and operational state data
     related to the TACACS+ protocol for authentication,
     authorization, and accounting.";
  oc-ext:openconfig-version "0.3.0";

  revision 2017-09-18 {
    description
      "Updated to use OpenConfig types modules";
    reference "0.3.0";
  }
  revision 2017-07-06 {
    description
      "Move to oc-inet types, add IETF attribution, add RADIUS
       counters, changed password leaf names to indicate hashed";
    reference "0.2.0";
  }
  revision 2017-01-29 {
    description
      "Initial public release";
    reference "0.1.0";
  }

  grouping ncs_template_aaa-tacacs-server-config {
    description
      "Configuration data for a TACACS+ server";
    leaf port {
      type oc-inet:ncs_template_port-number;
      // NCS drop default statement
      description
        "The port number on which to contact the TACACS server";
    }
    leaf secret-key {
      type oc-types:ncs_template_routing-password;
      description
        "The unencrypted shared key used between the authentication
         server and the device.";
    }
    leaf source-address {
      type oc-inet:ncs_template_ip-address;
      description
        "Source IP address to use in messages to the TACACS server";
    }
  }

  grouping ncs_template_aaa-tacacs-server-state {
    description
      "Operational state data for a TACACS+ server";
  }

  grouping ncs_template_aaa-tacacs-server-top {
    description
      "Top-level grouping for TACACS+ sever data";
    container tacacs {
      description
        "Top-level container for TACACS+ server data";
      container config {
        description
          "Configuration data for TACACS+ server";
        uses ncs_template_aaa-tacacs-server-config;
      }
      // NCS drop config false container state
    }
  }

  grouping ncs_rpc_notif_aaa-tacacs-server-config {
    description
      "Configuration data for a TACACS+ server";
    leaf port {
      type oc-inet:ncs_rpc_notif_port-number;
      default "49";
      description
        "The port number on which to contact the TACACS server";
    }
    leaf secret-key {
      type oc-types:ncs_rpc_notif_routing-password;
      description
        "The unencrypted shared key used between the authentication
         server and the device.";
    }
    leaf source-address {
      type oc-inet:ncs_rpc_notif_ip-address;
      description
        "Source IP address to use in messages to the TACACS server";
    }
  }

  grouping ncs_rpc_notif_aaa-tacacs-server-state {
    description
      "Operational state data for a TACACS+ server";
  }

  grouping ncs_rpc_notif_aaa-tacacs-server-top {
    description
      "Top-level grouping for TACACS+ sever data";
    container tacacs {
      description
        "Top-level container for TACACS+ server data";
      container config {
        description
          "Configuration data for TACACS+ server";
        uses ncs_rpc_notif_aaa-tacacs-server-config;
      }
      container state {
        config false;
        description
          "Operational state data for TACACS+ server";
        uses ncs_rpc_notif_aaa-tacacs-server-config;
        uses ncs_rpc_notif_aaa-tacacs-server-state;
      }
    }
  }

  grouping live_ncs_aaa-tacacs-server-config {
    description
      "Configuration data for a TACACS+ server";
    leaf port {
      type oc-inet:live_ncs_port-number;
      // NCS drop default statement
      description
        "The port number on which to contact the TACACS server";
    }
    leaf secret-key {
      type oc-types:live_ncs_routing-password;
      description
        "The unencrypted shared key used between the authentication
         server and the device.";
    }
    leaf source-address {
      type oc-inet:live_ncs_ip-address;
      description
        "Source IP address to use in messages to the TACACS server";
    }
  }

  grouping live_ncs_aaa-tacacs-server-state {
    description
      "Operational state data for a TACACS+ server";
  }

  grouping live_ncs_aaa-tacacs-server-top {
    description
      "Top-level grouping for TACACS+ sever data";
    container tacacs {
      description
        "Top-level container for TACACS+ server data";
      container config {
        description
          "Configuration data for TACACS+ server";
        uses live_ncs_aaa-tacacs-server-config;
      }
      container state {
        description
          "Operational state data for TACACS+ server";
        uses live_ncs_aaa-tacacs-server-config;
        uses live_ncs_aaa-tacacs-server-state;
      }
    }
  }

  grouping aaa-tacacs-server-config {
    description
      "Configuration data for a TACACS+ server";
    leaf port {
      type oc-inet:port-number;
      default "49";
      description
        "The port number on which to contact the TACACS server";
    }
    leaf secret-key {
      type oc-types:routing-password;
      description
        "The unencrypted shared key used between the authentication
         server and the device.";
    }
    leaf source-address {
      type oc-inet:ip-address;
      description
        "Source IP address to use in messages to the TACACS server";
    }
  }

  grouping aaa-tacacs-server-state {
    description
      "Operational state data for a TACACS+ server";
  }

  grouping aaa-tacacs-server-top {
    description
      "Top-level grouping for TACACS+ sever data";
    container tacacs {
      description
        "Top-level container for TACACS+ server data";
      container config {
        description
          "Configuration data for TACACS+ server";
        uses aaa-tacacs-server-config;
      }
      // NCS drop config false container state
    }
  }

  identity TACACS {
    base oc-aaa-types:AAA_SERVER_TYPE;
    description
      "Terminal Access Controller Access Control System (TACACS+)
       AAA server";
    reference
      "The TACACS+ Protocol (draft-ietf-opsawg-tacacs-05)
       RFC 1492 - An Access Control Protocol, Sometimes Called
       TACACS";
  }
}
