module ciena-subsystem-resource {
  // Generated by yanger -t ncs
  tailf:mount-id "ciena107-nc-1.0:ciena107-nc-1.0";
  tailf:ncs-device-type "netconf";

  namespace "http://www.ciena.com/ns/yang/ciena-subsystem-resource";
  prefix ciena-res;

  import tailf-common {
    prefix tailf;
  }
  import tailf-ncs {
    prefix ncs;
  }

  organization
    "Ciena Corporation";
  contact
    "Web URL: http://www.ciena.com/
     E-mail:  yang@ciena.com
     Postal:  7035 Ridge Road
             Hanover, Maryland 21076
             U.S.A.
     Phone:   +1 800-921-1144
     Fax:     +1 410-694-5750";
  description
    "This YANG module controls the resources assigned to
     various software subsystems.

     Copyright (c) 2019 Ciena Corporation.  All rights
     reserved.

     All information contained herein is, and remains
     the property of Ciena Corporation. Dissemination of this
     information or reproduction of this material is strictly
     forbidden unless prior written permission is obtained from
     Ciena Corporation.";

  revision 2020-03-04 {
    description
      "Added worker thread configuration and state information.
       Added subsystem restart RPC.";
  }
  revision 2019-04-03 {
    description
      "Initial version.
       Add switch-subsystem-profile rpc";
    reference
      "RFC 6020: YANG - A Data Modeling Language for
       the Network Configuration Protocol (NETCONF).
       No specific reference; standard not available.";
  }

  typedef ncs_template_subsystem-name {
    description
      "Name of subsystem";
    type string;
  }

  typedef ncs_template_cpu-profile-type {
    description
      "The profile type for cpu resource allocation";
    type string;
  }

  typedef ncs_rpc_notif_subsystem-name {
    description
      "Name of subsystem";
    type enumeration {
      enum "virtual-forwarding-plane" {
        description
          "Virtual forwarding plane subsystem.";
      }
    }
  }

  typedef ncs_rpc_notif_cpu-profile-type {
    description
      "The profile type for cpu resource allocation";
    type enumeration {
      enum "default-profile" {
        description
          "The default cpu resource profile";
      }
      enum "performance-profile" {
        description
          "The cpu resource profile aims for high-performance";
      }
    }
  }

  typedef live_ncs_subsystem-name {
    description
      "Name of subsystem";
    type enumeration {
      enum "virtual-forwarding-plane" {
        description
          "Virtual forwarding plane subsystem.";
      }
    }
  }

  typedef live_ncs_cpu-profile-type {
    description
      "The profile type for cpu resource allocation";
    type enumeration {
      enum "default-profile" {
        description
          "The default cpu resource profile";
      }
      enum "performance-profile" {
        description
          "The cpu resource profile aims for high-performance";
      }
    }
  }

  typedef subsystem-name {
    description
      "Name of subsystem";
    type enumeration {
      enum "virtual-forwarding-plane" {
        description
          "Virtual forwarding plane subsystem.";
      }
    }
  }

  typedef cpu-profile-type {
    description
      "The profile type for cpu resource allocation";
    type enumeration {
      enum "default-profile" {
        description
          "The default cpu resource profile";
      }
      enum "performance-profile" {
        description
          "The cpu resource profile aims for high-performance";
      }
    }
  }

  grouping ncs_template_cpu-resource-state {
    description
      "Operation data for CPU resource.";
    leaf profile {
      description
        "The profile used by susbsytem cpu resource allocation";
      type ncs_template_cpu-profile-type;
    }
    list socket {
      // NCS patched for predictable order
      ordered-by user;
      description
        "List of CPU sockets";
      key "socket-id";
      leaf socket-id {
        description
          "CPU socket ID";
        type string;
      }
      leaf-list cpu-id {
        // NCS patched for predictable order
        ordered-by user;
        description
          "List of CPU IDs";
        type string;
      }
    }
  }

  grouping ncs_rpc_notif_cpu-resource-state {
    description
      "Operation data for CPU resource.";
    leaf profile {
      description
        "The profile used by susbsytem cpu resource allocation";
      type ncs_rpc_notif_cpu-profile-type;
    }
    list socket {
      description
        "List of CPU sockets";
      key "socket-id";
      leaf socket-id {
        description
          "CPU socket ID";
        type uint32;
      }
      leaf-list cpu-id {
        description
          "List of CPU IDs";
        type uint32;
      }
    }
  }

  grouping live_ncs_cpu-resource-state {
    description
      "Operation data for CPU resource.";
    leaf profile {
      description
        "The profile used by susbsytem cpu resource allocation";
      type live_ncs_cpu-profile-type;
    }
    list socket {
      description
        "List of CPU sockets";
      key "socket-id";
      leaf socket-id {
        description
          "CPU socket ID";
        type uint32;
      }
      leaf-list cpu-id {
        description
          "List of CPU IDs";
        type uint32;
      }
    }
  }

  grouping cpu-resource-state {
    description
      "Operation data for CPU resource.";
    leaf profile {
      description
        "The profile used by susbsytem cpu resource allocation";
      type cpu-profile-type;
    }
    list socket {
      description
        "List of CPU sockets";
      key "socket-id";
      leaf socket-id {
        description
          "CPU socket ID";
        type uint32;
      }
      leaf-list cpu-id {
        description
          "List of CPU IDs";
        type uint32;
      }
    }
  }

  augment "/ncs:devices/ncs:device/ncs:rpc" {
    container rpc-subsystem-restart {
      tailf:ncs-device-type "netconf";
      tailf:display-when "not(../../ncs:module) or ../../ncs:module[ncs:name='ciena-subsystem-resource']";
      tailf:action subsystem-restart {
        tailf:actionpoint ncsproxy {
          tailf:internal;
        }
        description
          "Request to restart the subsystem.";
        input {
          leaf name {
            type string;
            mandatory true;
            description
              "The name of the subsystem to be restarted.";
          }
        }
        output {
          leaf status {
            type string;
            description
              "Status of the restart operation.";
          }
        }
      }
    }
  }
  augment "/ncs:devices/ncs:device-group/ncs:ned-id/ncs:rpc" {
    container rpc-subsystem-restart {
      tailf:ncs-device-type "netconf";
      tailf:display-when "/ncs:devices/ncs:device[ncs:name=current()/../../../ncs:member]/ncs:module[ncs:name='ciena-subsystem-resource']";
      tailf:action subsystem-restart {
        tailf:actionpoint ncsproxy {
          tailf:internal;
        }
        description
          "Request to restart the subsystem.";
        input {
          leaf name {
            type string;
            mandatory true;
            description
              "The name of the subsystem to be restarted.";
          }
        }
        output {
          container "device" {
            leaf "name" {
              type string;
            }
            leaf "info" {
              type string;
            }
            container "result" {
              leaf status {
                type string;
                description
                  "Status of the restart operation.";
              }
            }
          }
        }
      }
    }
  }
  augment "/ncs:devices/ncs:device/ncs:config" {
    container subsystems {
      tailf:ncs-device-type "netconf";
      tailf:display-when "not(../../ncs:module) or ../../ncs:module[ncs:name='ciena-subsystem-resource']";
      description
        "Resource configuration for subsystems.";
      list subsystem {
        key "name";
        description
          "List of subsystems";
        leaf name {
          description
            "Name of subsystem";
          type subsystem-name;
        }
        container cpu-resource {
          description
            "CPU resource configuration";
          list socket {
            description
              "List of CPU sockets";
            key "socket-id";
            leaf socket-id {
              description
                "CPU socket ID";
              type uint32;
            }
            container cpu {
              description
                "CPU configuration";
              leaf num-of-cores {
                description
                  "Number of CPU cores assigned.";
                type uint32;
              }
            }
          }
        }
        container cpu-profile {
          description
            "CPU profile configuration";
          leaf profile {
            description
              "The profile type for CPU profile configuration";
            type cpu-profile-type;
          }
        }
        container worker-threads {
          description
            "Worker thread configuration";
          list worker-thread {
            description
              "List of worker threads";
            key "thread-name";
            leaf thread-name {
              description
                "Worker thread name.";
              type string {
                length "1..128";
              }
            }
            leaf-list cpu-id {
              when "../../../name != 'virtual-forwarding-plane'" {
                tailf:xpath-root 3;
              }
              description
                "List of CPU IDs";
              type uint8;
            }
          }
        }
      }
    }
    // NCS drop config false container 'subsystems-state'
  }
  augment "/ncs:devices/ncs:device/ncs:live-status" {
    container subsystems {
      tailf:ncs-device-type "netconf";
      tailf:display-when "not(../../ncs:module) or ../../ncs:module[ncs:name='ciena-subsystem-resource'] or (../../ncs:live-status-protocol[not(ncs:capability)]) or (../../ncs:live-status-protocol/ncs:capability/ncs:module[.='ciena-subsystem-resource'])";
      description
        "Resource configuration for subsystems.";
      list subsystem {
        key "name";
        description
          "List of subsystems";
        leaf name {
          description
            "Name of subsystem";
          type live_ncs_subsystem-name;
        }
        container cpu-resource {
          description
            "CPU resource configuration";
          list socket {
            description
              "List of CPU sockets";
            key "socket-id";
            leaf socket-id {
              description
                "CPU socket ID";
              type uint32;
            }
            container cpu {
              description
                "CPU configuration";
              leaf num-of-cores {
                description
                  "Number of CPU cores assigned.";
                type uint32;
              }
            }
          }
        }
        container cpu-profile {
          description
            "CPU profile configuration";
          leaf profile {
            description
              "The profile type for CPU profile configuration";
            type live_ncs_cpu-profile-type;
          }
        }
        container worker-threads {
          description
            "Worker thread configuration";
          list worker-thread {
            description
              "List of worker threads";
            key "thread-name";
            leaf thread-name {
              description
                "Worker thread name.";
              type string {
                length "1..128";
              }
            }
            leaf-list cpu-id {
              // NCS drop when statement
              description
                "List of CPU IDs";
              type uint8;
            }
          }
        }
      }
    }
    container subsystems-state {
      tailf:ncs-device-type "netconf";
      tailf:display-when "not(../../ncs:module) or ../../ncs:module[ncs:name='ciena-subsystem-resource'] or (../../ncs:live-status-protocol[not(ncs:capability)]) or (../../ncs:live-status-protocol/ncs:capability/ncs:module[.='ciena-subsystem-resource'])";
      description
        "Operation data for subsystem resource configuration";
      list subsystem {
        key "name";
        leaf name {
          description
            "Name of subsystem";
          type leafref {
            path "../../../subsystems/subsystem/name";
          }
        }
        leaf config-pending {
          description
            "Status of subsystem resource configuration. When true, the
             system has outstanding configuration changes that require
             a restart of the subsystem to activate";
          type boolean;
        }
        container cpu {
          description
            "Operation data for CPU resource configuration.";
          container active {
            description
              "CPU resource configuration in active use.";
            uses live_ncs_cpu-resource-state;
          }
          container pending {
            description
              "CPU resource configuration that will be activated after a reboot.";
            uses live_ncs_cpu-resource-state;
          }
        }
        container worker-threads {
          description
            "Operational data for worker thread configuration.";
          list worker-thread {
            description
              "List of worker threads that are in active use.";
            key "thread-name";
            leaf thread-name {
              description
                "Worker thread name.";
              type string;
            }
            leaf-list cpu-id {
              description
                "List of CPU IDs.";
              type uint8;
            }
          }
        }
      }
    }
  }
  augment "/ncs:devices/ncs:template/ncs:ned-id/ncs:config" {
    container subsystems {
      description
        "Resource configuration for subsystems.";
      list subsystem {
        // NCS patched for predictable order
        ordered-by user;
        key "name";
        description
          "List of subsystems";
        leaf name {
          description
            "Name of subsystem";
          type ncs_template_subsystem-name;
        }
        container cpu-resource {
          description
            "CPU resource configuration";
          list socket {
            // NCS patched for predictable order
            ordered-by user;
            description
              "List of CPU sockets";
            key "socket-id";
            leaf socket-id {
              description
                "CPU socket ID";
              type string;
            }
            container cpu {
              description
                "CPU configuration";
              leaf num-of-cores {
                description
                  "Number of CPU cores assigned.";
                type string;
              }
            }
          }
        }
        container cpu-profile {
          description
            "CPU profile configuration";
          leaf profile {
            description
              "The profile type for CPU profile configuration";
            type ncs_template_cpu-profile-type;
          }
        }
        container worker-threads {
          description
            "Worker thread configuration";
          list worker-thread {
            // NCS patched for predictable order
            ordered-by user;
            description
              "List of worker threads";
            key "thread-name";
            leaf thread-name {
              description
                "Worker thread name.";
              type string;
            }
            leaf-list cpu-id {
              // NCS patched for predictable order
              ordered-by user;
              // NCS drop when statement
              description
                "List of CPU IDs";
              type string;
            }
          }
        }
      }
    }
    // NCS drop config false container 'subsystems-state'
  }
}
