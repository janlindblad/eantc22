module ciena-ieee-rstp-deviation {
  // Generated by yanger -t ncs
  tailf:mount-id "ciena107-nc-1.0:ciena107-nc-1.0";
  tailf:ncs-device-type "netconf";

  namespace "urn:ciena:params:xml:ns:yang:ciena-pn:ciena-ieee-rstp-deviation";
  prefix ciena-ieee-rstp-dev;

  import ciena-ieee-rstp {
    prefix ieee-rstp;
  }
  import ciena-mef-logical-port {
    prefix mef-logical-port;
  }
  import tailf-common {
    prefix tailf;
  }
  import tailf-ncs {
    prefix ncs;
  }

  revision 2019-09-05 {
    description
      "Added loopback to port role.";
  }
  revision 2018-05-05 {
    description
      "Initial revision.";
  }

  deviation "/ncs:devices/ncs:template/ncs:ned-id/ncs:config/ieee-rstp:rstp/ieee-rstp:config/ieee-rstp:bridge-priority" {
    deviate replace {
      // NCS drop default statement
      type string;
    }
  }
  deviation "/ncs:devices/ncs:device/ncs:live-status/ieee-rstp:rstp/ieee-rstp:config/ieee-rstp:bridge-priority" {
    deviate replace {
      // NCS drop default statement
      type uint8 {
        range "0..15";
      }
    }
  }
  deviation "/ncs:devices/ncs:device/ncs:config/ieee-rstp:rstp/ieee-rstp:config/ieee-rstp:bridge-priority" {
    deviate replace {
      default "8";
      type uint8 {
        range "0..15";
      }
    }
  }
  deviation "/ncs:devices/ncs:template/ncs:ned-id/ncs:config/mef-logical-port:logical-ports/mef-logical-port:logical-port/ieee-rstp:rstp-port-config/ieee-rstp:port-priority" {
    deviate replace {
      // NCS drop default statement
      type string;
    }
  }
  deviation "/ncs:devices/ncs:device/ncs:live-status/mef-logical-port:logical-ports/mef-logical-port:logical-port/ieee-rstp:rstp-port-config/ieee-rstp:port-priority" {
    deviate replace {
      // NCS drop default statement
      type uint8 {
        range "0..15";
      }
    }
  }
  deviation "/ncs:devices/ncs:device/ncs:config/mef-logical-port:logical-ports/mef-logical-port:logical-port/ieee-rstp:rstp-port-config/ieee-rstp:port-priority" {
    deviate replace {
      default "8";
      type uint8 {
        range "0..15";
      }
    }
  }
  deviation "/ncs:devices/ncs:device/ncs:live-status/mef-logical-port:logical-port-oper-status/mef-logical-port:logical-port-status/ieee-rstp:rstp-port-oper-data/ieee-rstp:port-role" {
    deviate replace {
      type enumeration {
        enum "disabled" {
          description
            "The port is not operational or is excluded from the active
             topology by management.";
        }
        enum "root" {
          description
            "The port that receives the best BPDU on a bridge is the
             root port.";
        }
        enum "designated" {
          description
            "A port is designated if it can send the best BPDU on the
             segment to which it is connected.";
        }
        enum "alternate" {
          description
            "An alternate port receives more useful BPDUs from another
             bridge and is a port blocked.";
        }
        enum "backup" {
          description
            "A backup port receives more useful BPDUs from the same
             bridge it is on and is a port blocked.";
        }
        enum "loopback" {
          description
            "A port that receives its own transmitted BPDUs is the
             loopback port and is a blocked port.";
        }
      }
    }
  }
}
